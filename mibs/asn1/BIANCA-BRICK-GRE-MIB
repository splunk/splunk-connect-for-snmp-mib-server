-- This file is corresponding to Release 9.1.10.101 from 2014/08/11 00:00:00


-- (C)opyright 1991-2014 bintec elmeg GmbH, All Rights Reserved

BIANCA-BRICK-GRE-MIB DEFINITIONS ::= BEGIN

        IMPORTS
            IpAddress, Counter, enterprises
                FROM RFC1155-SMI

            DisplayString
                FROM RFC1158-MIB
 
            OBJECT-TYPE
                FROM RFC-1212;

    bintec 	OBJECT IDENTIFIER ::= { enterprises 272 }
    bibo	OBJECT IDENTIFIER ::= { bintec 4 }
    vpn		OBJECT IDENTIFIER
	::= { bibo 23 }

    -- GRE

    -- Management Information for GRE MPR virtual interfaces

	greIfTable OBJECT-TYPE
	    SYNTAX  SEQUENCE OF GreIfEntry
	    ACCESS  not-accessible
	    STATUS  mandatory
	    DESCRIPTION
		"This Table contains configuration information for GRE 
		interfaces. Each time a new entry is created here, a corresponding
		entry is created in the ifTable and biboAdmDeviceTable."
	::= { vpn 5 }

	greIfEntry OBJECT-TYPE
	    SYNTAX  GreIfEntry
	    ACCESS  not-accessible
	    STATUS  mandatory
	    DESCRIPTION
		"Entries in this table are created by defining a new value for
		the field greDstIpAddr. Entries may be deleted by setting the
		field greUseKey to 'delete'."
	    INDEX   { greDstIpAddr }
	::= { greIfTable 1 }

	GreIfEntry ::=
	    SEQUENCE {
		greIfIndex				INTEGER,
		greIfDescr				DisplayString,
		greIfMtu				INTEGER,
		greDstIpAddr				IpAddress,
		greKey					INTEGER,
		greUseKey				INTEGER,
		greSrcIpAddr				IpAddress
	}

	greIfIndex OBJECT-TYPE
	    SYNTAX  INTEGER
	    ACCESS  read-only
	    STATUS  mandatory
	    DESCRIPTION
		"The index of the virtual interface. This object identifies
		 a row in the ifTable."
	    DEFVAL  { 0 }
	::= { greIfEntry 1 }

	greIfDescr OBJECT-TYPE
            SYNTAX  DisplayString (SIZE (0..255))
	    ACCESS  read-write
	    STATUS  mandatory
	    DESCRIPTION
		"The name of the virtual interface. The same name will be
		 assigned to the corresponding ifDescr in the ifTable."
	::= { greIfEntry 2 }

	greIfMtu OBJECT-TYPE
	    SYNTAX  INTEGER (1..8192)
	    ACCESS  read-write
	    STATUS  mandatory
	    DESCRIPTION
                "Determines size of the largest datagram which can be
	         sent on the interface, specified in octets (see ifMtu)."
	    DEFVAL { 1500 }
	::= { greIfEntry 3 }

	greDstIpAddr OBJECT-TYPE
	    SYNTAX  IpAddress
	    ACCESS  read-write
	    STATUS  mandatory
	    DESCRIPTION
		"The IP address of the GRE remote partner."
	::= { greIfEntry 4 }
	
	greKey OBJECT-TYPE
	    SYNTAX  INTEGER
	    ACCESS  read-write
	    STATUS  mandatory
	    DESCRIPTION
		"The optional 32-bit key for this GRE tunnel. Multiple
		tunnels can be used simultaneously between the two same
		GRE partners provided each tunnel uses a different key."
	    DEFVAL  { 0 }
	::= { greIfEntry 5 }

	greUseKey OBJECT-TYPE
	    SYNTAX  INTEGER {
	    	delete(1), yes(2), no(3)
	    }

	    ACCESS  read-write
	    STATUS  mandatory
	    DESCRIPTION
		"This object indicates, whether the key value specified in
		greKey should be processed in GRE headers."
	    DEFVAL  { no }
	::= { greIfEntry 6 }

	greSrcIpAddr OBJECT-TYPE
	    SYNTAX  IpAddress
	    ACCESS  read-write
	    STATUS  mandatory
	    DESCRIPTION
		"The source IP address used when sending GRE packets. 
		If this value is set to 0.0.0.0, the IP address of the 
		interface used to route packets towards the remote partner 
		will be automatically selected for this purpose."
	::= { greIfEntry 7 }
	
END
