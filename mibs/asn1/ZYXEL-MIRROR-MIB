-- ZyXEL Communications Corporation
-- Private Enterprise MIB definition 
  
-- This file describes the ZyXEL Communications Corporation Enterprise MIB.
-- It contains ZyXEL products OIDs, and common managed objects.

-- $Log: ZYXEL-MIRROR-MIB.mib $ 
-- Revision 1.5  2013/12/06 07:07:25  ccho 
-- remove uncessary imports 
-- Revision 1.4  2012/09/19 07:41:08  Kevin 
-- if it's leaf node, revise the vender name from zyxel to zy 
-- Revision 1.3  2012/08/22 09:47:27  Kevin 
-- clean warning for SNMPc 
-- Revision 1.2  2012/07/05 06:23:39  Kevin 
-- 1. upgrade from SNMP to SNMPv2  
-- 2. clean warning 
-- Revision 1.1  2012/05/30 07:49:49  Kevin 
-- Initial revision 

ZYXEL-MIRROR-MIB DEFINITIONS ::= BEGIN

    IMPORTS
	OBJECT-TYPE
		FROM SNMPv2-SMI			-- RFC2578	
		
	MODULE-IDENTITY
		FROM SNMPv2-SMI
	
	EnabledStatus
		FROM  P-BRIDGE-MIB

	dot1dBasePort
       	FROM BRIDGE-MIB

	esMgmt			
		FROM ZYXEL-ES-SMI;

	zyxelMirror MODULE-IDENTITY
		LAST-UPDATED	"201207010000Z"    
		ORGANIZATION "Enterprise Solution ZyXEL"     
		CONTACT-INFO
			""	   
		DESCRIPTION
			"The subtree for mirror"
		::= { esMgmt 65 }

	zyxelMirrorSetup    	OBJECT IDENTIFIER ::= { zyxelMirror 1 }
  
-- *******************************************************************
-- *
-- * zyxelMirrorSetup
-- *
-- *******************************************************************

-- zyxelMirrorState
		zyMirrorState OBJECT-TYPE
        SYNTAX  EnabledStatus
        MAX-ACCESS  read-write
        STATUS  current
        DESCRIPTION
                    "Enable/Disable mirror for the switch."
        ::= { zyxelMirrorSetup 1 }

-- zyxelMirrorMonitorPort
		zyMirrorMonitorPort OBJECT-TYPE
        SYNTAX  INTEGER
        MAX-ACCESS  read-write
        STATUS  current
        DESCRIPTION
                    "The monitor port is the port you copy the traffic to in order to examine it in more detail 
                    without interfering with the traffic flow on the original port(s). Type the port number of the 
                    monitor port. "
        ::= { zyxelMirrorSetup 2 }

-- zyxelMirrorTable
        zyxelMirrorTable OBJECT-TYPE
        SYNTAX	SEQUENCE OF ZyxelMirrorEntry
        MAX-ACCESS  not-accessible
        STATUS  current
        DESCRIPTION
                 	"The table contains mirror port configuration."
        ::= { zyxelMirrorSetup 3 }
        
		zyxelMirrorEntry OBJECT-TYPE
        SYNTAX	ZyxelMirrorEntry
        MAX-ACCESS	not-accessible
        STATUS	current
        DESCRIPTION    	
					"An entry contains mirror port configuration."
        INDEX          	{ dot1dBasePort }
        ::= { zyxelMirrorTable 1 }

        ZyxelMirrorEntry ::=
           SEQUENCE {
        	zyMirrorMirroredState	EnabledStatus,
        	zyMirrorDirection		INTEGER
           }

        zyMirrorMirroredState OBJECT-TYPE
        SYNTAX  EnabledStatus
        MAX-ACCESS  read-write
        STATUS  current
        DESCRIPTION
                      	"Enable/Disable mirror on the specified port."
        ::= { zyxelMirrorEntry 1 }

        zyMirrorDirection OBJECT-TYPE
        SYNTAX  INTEGER {
        	ingress(0),
        	egress(1),
        	both(2)
        }
        MAX-ACCESS  read-write
        STATUS  current
        DESCRIPTION
			"Specify the direction of the traffic to mirror. 
			Choices are Egress (outgoing), Ingress (incoming) and Both. "
        ::= { zyxelMirrorEntry 2 }
		
END
