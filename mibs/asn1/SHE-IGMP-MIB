--
-- she-igmp-mib.mib
-- MIB generated by MG-SOFT Visual MIB Builder Version 6.0  Build 88
-- Wednesday, September 17, 2008 at 13:51:43
--

-- Start of ClearCase branch-information of current release:
-- she-igmp-mib.mib   /main/she_r2.8_grf/5
-- End of ClearCase branch-information.

	SHE-IGMP-MIB DEFINITIONS ::= BEGIN
 
		IMPORTS
			she			
				FROM AN-MIB			
			sheBridgePortIndex, sheIgmpGroupIndex			
				FROM SHE-BRIDGE-MIB			
			SheControlStatusType			
				FROM SHE-TC-MIB			
			SnmpAdminString			
				FROM SNMP-FRAMEWORK-MIB			
			OBJECT-GROUP, MODULE-COMPLIANCE, NOTIFICATION-GROUP			
				FROM SNMPv2-CONF			
			TimeTicks, IpAddress, Unsigned32, Gauge32, OBJECT-TYPE, 
			MODULE-IDENTITY, NOTIFICATION-TYPE			
				FROM SNMPv2-SMI			
			TruthValue, DateAndTime			
				FROM SNMPv2-TC;
	
	
		sheIgmpMib MODULE-IDENTITY 
			LAST-UPDATED "200809171000Z"		-- September 17, 2008 at 10:00 GMT
			ORGANIZATION 
				"Nokia Siemens Networks"
			CONTACT-INFO 
				"COO BBA
				Siemens Building in Beijing
				
				jie.shen@nsn.com
				guo.xiaofeng@nsn.com
				ti.liu@nsn.com
				######################
				gerd.barchmann@nsn.com"
			DESCRIPTION 
				"The MIB module is to describe managed objects supporting additional IGMP features."
			REVISION "200509211455Z"		-- September 21, 2005 at 14:55 GMT
			DESCRIPTION 
				"Change the sheIgmpNotifications to sheIgmpNotification. The
				first name is duplicated with the object defined in she-bridge-mib"
			REVISION "200803190834Z"		-- March 19, 2008 at 08:34 GMT
			DESCRIPTION 
				"Bring them to common SHE MIB package with R2.8."
			REVISION "200804081543Z"		-- April 08, 2008 at 15:43 GMT
			DESCRIPTION 
				"Correct description for sheIgmpPreviewPackageChannelList.
				Correct index values for sheIgmpSubscriberTable."
			REVISION "200805200953Z"		-- May 20, 2008 at 09:53 GMT
			DESCRIPTION 
				"Correct description of RateLimit parameters."
			REVISION "200807080840Z"		-- July 08, 2008 at 08:40 GMT
			DESCRIPTION 
				"Update for SHE R2.8. 
				Add controlrequest and controlgroup parameter for set sheIgmpLongTimeOnlineTime."
			REVISION "200807240901Z"		-- July 24, 2008 at 09:01 GMT
			DESCRIPTION 
				"Correct description for sheIgmpParaV2CDRTime."
			REVISION "200809171347Z"		-- September 17, 2008 at 13:47 GMT
			DESCRIPTION 
				"Modify some ranges."
			::= { she 35 }

		
	
--
-- Type definitions
--
	
-- -----------------------------------------------------------------
-- Types definitions
-- -----------------------------------------------------------------
		SheIgmpControlRequestType ::= INTEGER
			{
			noRequest(1),
			setIgmpParameters(2),
			setFtpParameters(3),
			createPreviewPackage(4),
			deletePreviewPackage(5),
			modifyPreviewPackage(6),
			addChannel2PreviewPackage(7),
			deleteChannelFromPreviewPackage(8),
			setIgmpPacketRateLimitUplink(9),
			setSubscriberPreviewPackage(10),
			deleteSubscriberPreviewPackage(11),
			resetSubscriberPreviewRemainsCount(12),
			resetSubscriberPreviewCountAll(13),
			manuallyUploadLog(14),
			setIgmpPacketRateLimitSubscriber(15),
			setIgmpLongTimeOnlineTime(16),
			setIgmpEthernetAccessEnable(17),
			setIgmpCDRTime(18),
			setIgmpSetMulticastChannelV2Para(19),
			setIgmpPreviewAutoResetTimeEnable(21)
			}

		SheIgmpControlRequestResultType ::= INTEGER
			{
			noRequest(1),
			wrongIpAddress(2),
			wrongUserPassword(3),
			permissionDenied(4),
			comExecStarted(30),
			paramFaulty(31),
			requestBusy(32),
			setDataFailed(34),
			aswTimeout(35),
			commandFailed(36),
			commandSucceeded(37)
			}

--   user command results are defined between 2 - 29
-- The following are the error codes of enabling upload command.
-- All happened at the phase to check and create the RootDir and
-- subdirs.
-- IP address of FTP servre is incorrect
-- The user name or password is wrong
-- The user name has no permission to create dir/file
-- end of user command results
		SheIgmpUploadStatusType ::= INTEGER
			{
			uploadSuccess(1),
			uploadFail(2)
			}

		SheIgmpPreviewAutoResetTimeUnitType ::= INTEGER
			{
			day(1),
			week(2),
			month(3)
			}

		SheIgmpCACStatusType ::= INTEGER
			{
			accept(1),
			deny(2)
			}

		SheIgmpMulticastGroupModeType ::= INTEGER
			{
			normal(1),
			static(2)
			}

	
	
--
-- Node definitions
--
	
-- ----------------------------------------------------------------
-- Global Parameters
-- -----------------------------------------------------------------
-- 1.3.6.1.4.1.231.7.1.2.2.1.35.1
		sheIgmpSystem OBJECT IDENTIFIER ::= { sheIgmpMib 1 }

		
--  1.3.6.1.4.1.231.7.1.2.2.1.35.1.1
		sheIgmpProgramPreviewEnable OBJECT-TYPE
			SYNTAX TruthValue
			MAX-ACCESS read-only
			STATUS current
			DESCRIPTION
				"Indicates whether to enable the program preview functionality."
			DEFVAL { false }
			::= { sheIgmpSystem 1 }

		
--  1.3.6.1.4.1.231.7.1.2.2.1.35.1.2
		sheIgmpLogEnable OBJECT-TYPE
			SYNTAX TruthValue
			MAX-ACCESS read-only
			STATUS current
			DESCRIPTION
				"Whether the NE should keep the IGMP log."
			DEFVAL { false }
			::= { sheIgmpSystem 2 }

		
--  1.3.6.1.4.1.231.7.1.2.2.1.35.1.3
		sheIgmpUploadEnable OBJECT-TYPE
			SYNTAX TruthValue
			MAX-ACCESS read-only
			STATUS current
			DESCRIPTION
				"Whether the NE should upload the log files to FTP server."
			DEFVAL { false }
			::= { sheIgmpSystem 3 }

		
--  1.3.6.1.4.1.231.7.1.2.2.1.35.1.4
		sheIgmpFtpRootDir OBJECT-TYPE
			SYNTAX SnmpAdminString
			MAX-ACCESS read-only
			STATUS current
			DESCRIPTION
				"The root directory name on FTP server that stores the
				IGMP log data of this DSLAM. It is the relative path to
				the ftproot, eg. 'hix5635/v1.5/dslam1/igmp'
				The directory structure looks like:
				ftproot            <-- the upmost ftp root
				|- %FtpRootDir%    <-- this value, specifies the DSLAM
				"
			::= { sheIgmpSystem 4 }

		
--  1.3.6.1.4.1.231.7.1.2.2.1.35.1.5
		sheIgmpFtpIp OBJECT-TYPE
			SYNTAX IpAddress
			MAX-ACCESS read-only
			STATUS current
			DESCRIPTION
				"FTP server's IP address."
			::= { sheIgmpSystem 5 }

		
--  1.3.6.1.4.1.231.7.1.2.2.1.35.1.6
		sheIgmpFtpUser OBJECT-TYPE
			SYNTAX SnmpAdminString
			MAX-ACCESS read-only
			STATUS current
			DESCRIPTION
				"FTP user name. Write permission is required for this user."
			::= { sheIgmpSystem 6 }

		
--  1.3.6.1.4.1.231.7.1.2.2.1.35.1.7
		sheIgmpFtpPassword OBJECT-TYPE
			SYNTAX OCTET STRING (SIZE (0..128))
			MAX-ACCESS read-only
			STATUS current
			DESCRIPTION
				"FTP server access password. To protect the password, the string
				of this object in the GetResponse PDU is encrypted."
			::= { sheIgmpSystem 7 }

		
--  1.3.6.1.4.1.231.7.1.2.2.1.35.1.8
		sheIgmpFtpUploadInterval OBJECT-TYPE
			SYNTAX Unsigned32 (1..4294967295)
			UNITS "minutes"
			MAX-ACCESS read-only
			STATUS current
			DESCRIPTION
				"The interval that IGMP log data is uploaded to FTP server.
				"
			DEFVAL { 30 }
			::= { sheIgmpSystem 8 }

		
--  1.3.6.1.4.1.231.7.1.2.2.1.35.1.9
		sheIgmpPacketRateLimitUplink OBJECT-TYPE
			SYNTAX INTEGER (-1..2147483647)
			MAX-ACCESS read-only
			STATUS current
			DESCRIPTION
				"IGMP packets received from the uplink port is only allowed to be processed 
				by the IGMP proxy with a limit of this value per minute.
				-1 is a special value means no limit."
			DEFVAL { -1 }
			::= { sheIgmpSystem 9 }

		
--  1.3.6.1.4.1.231.7.1.2.2.1.35.1.10
		sheIgmpPacketRateLimitSubscriber OBJECT-TYPE
			SYNTAX INTEGER (-1..2147483647)
			MAX-ACCESS read-only
			STATUS current
			DESCRIPTION
				"IGMP packets received from the DSL subscriber port is only allowed to be processed
				by the IGMP proxy with a limit of this value per minute.
				-1 is a special value means no limit."
			DEFVAL { -1 }
			::= { sheIgmpSystem 10 }

		
--  1.3.6.1.4.1.231.7.1.2.2.1.35.1.11
		sheIgmpLongTimeOnlineTime OBJECT-TYPE
			SYNTAX INTEGER (0..2147483647)
			MAX-ACCESS read-only
			STATUS current
			DESCRIPTION
				"For every time interval of this value, there should be a log entry sent 
				to the FTP server for those subscribers who have joined a multicast group 
				for more than this time interval.
				"
			::= { sheIgmpSystem 11 }

		
--  1.3.6.1.4.1.231.7.1.2.2.1.35.1.12
		sheIgmpEthernetAccessEnable OBJECT-TYPE
			SYNTAX TruthValue
			MAX-ACCESS read-only
			STATUS current
			DESCRIPTION
				"When sheIgmpEthernetAccessEnable is true, if ethernet port of the CxU is configured as aggregate, 
				multicast traffic could be accessed only if there's IGMP report sent from it.
				
				When sheIgmpEthernetAccessEnable is false, if ethernet port of the CxU is configured as aggregate, 
				multicast traffic could be accessed without IGMP report."
			DEFVAL { false }
			::= { sheIgmpSystem 12 }

		
--   -----------------------------------------------------------------
-- Control group
-- -----------------------------------------------------------------
-- 1.3.6.1.4.1.231.7.1.2.2.1.35.1.13
		sheIgmpControl OBJECT IDENTIFIER ::= { sheIgmpSystem 13 }

		
--  1.3.6.1.4.1.231.7.1.2.2.1.35.1.13.1
		sheIgmpControlRequest OBJECT-TYPE
			SYNTAX SheIgmpControlRequestType
			MAX-ACCESS read-write
			STATUS current
			DESCRIPTION
				"Command to configure global system parameters.
				It must be the last member in the varBindList of the SNMP set request.
				The parameters for different commands are listed below:
				    setIgmpParameters:
				        (optional, but at least one of them should be there)
				        sheIgmpControlProgramPreviewEnable
				        sheIgmpControlLogEnable
				        sheIgmpControlUploadEnable
				    setFtpParameters:
				        sheIgmpControlFtpRootDir
				        sheIgmpControlFtpIp
				        sheIgmpControlFtpUser
				        sheIgmpControlFtpPassword
				        sheIgmpControlFtpUploadInterval
				    setIgmpPacketRateLimitUplink:
				        sheIgmpControlPacketRateLimitUplink
				    setIgmpPacketRateLimitSubscriber:
				        sheIgmpControlPacketRateLimitSubscriber
				    setIgmpLongTimeOnlineTime:
				        sheIgmpControlLongTimeOnlineTime
				    setIgmpEthernetAccessEnable:
				        sheIgmpControlEthernetAccessEnable
				    resetSubscriberPreviewCountAll:
				    manuallyUploadLog:
				       (no parameter)
				
				Notifications:
				  sheIgmpControlResult at the command ending in case of long running command.
				  The long running command refers to the case that sheIgmpUploadEnable
				is changed from disable to enable. NE will verify the FTP connection at the
				enabling moment. Besides, the RootDir is created if they do not exist yet.
				  EM should GET sheIgmpControlReqResult when the Response of the SET PDU
				is received, and the error status is noError. If the value of
				sheIgmpControlReqResult is comExecStarted(30), which means the SET operation
				is a long running command, EM must issue another GET operation on
				sheIgmpControlTimer. A timer should start on EM with the expire time equals
				to the value of sheIgmpControlTimer. The sheIgmpControlResult trap is expected
				to reach EM within the specified time.
				  When the trap is received by EM, EM can optionally GET
				sheIgmpControlReqResult, sheIgmpControlStatus, and sheIgmpControlTimeStamp.
				"
			::= { sheIgmpControl 1 }

		
--  1.3.6.1.4.1.231.7.1.2.2.1.35.1.13.2
		sheIgmpControlStatus OBJECT-TYPE
			SYNTAX Unsigned32
			MAX-ACCESS read-only
			STATUS current
			DESCRIPTION
				"The status of a control request."
			::= { sheIgmpControl 2 }

		
--  1.3.6.1.4.1.231.7.1.2.2.1.35.1.13.3
		sheIgmpControlTimer OBJECT-TYPE
			SYNTAX Unsigned32
			MAX-ACCESS read-only
			STATUS current
			DESCRIPTION
				"The maximum wait time for the manager for command ending.
				For long running commands.
				The manager reads this value from the SHE."
			::= { sheIgmpControl 3 }

		
--  1.3.6.1.4.1.231.7.1.2.2.1.35.1.13.4
		sheIgmpControlReqResult OBJECT-TYPE
			SYNTAX SheIgmpControlRequestResultType
			MAX-ACCESS read-only
			STATUS current
			DESCRIPTION
				"The result of the last user command."
			::= { sheIgmpControl 4 }

		
--  1.3.6.1.4.1.231.7.1.2.2.1.35.1.13.5
		sheIgmpControlTimeStamp OBJECT-TYPE
			SYNTAX Unsigned32
			UNITS "sec"
			MAX-ACCESS read-only
			STATUS current
			DESCRIPTION
				"The time stamp of the last command (end of command)."
			::= { sheIgmpControl 5 }

		
--  1.3.6.1.4.1.231.7.1.2.2.1.35.1.13.6
		sheIgmpControlProgramPreviewEnable OBJECT-TYPE
			SYNTAX TruthValue
			MAX-ACCESS read-write
			STATUS current
			DESCRIPTION
				"Indicates whether to enable the program preview functionality."
			DEFVAL { false }
			::= { sheIgmpControl 6 }

		
--  1.3.6.1.4.1.231.7.1.2.2.1.35.1.13.7
		sheIgmpControlLogEnable OBJECT-TYPE
			SYNTAX TruthValue
			MAX-ACCESS read-write
			STATUS current
			DESCRIPTION
				"Whether the NE should keep the IGMP log.
				Change the value of sheIgmpLogEnable."
			DEFVAL { false }
			::= { sheIgmpControl 7 }

		
--  1.3.6.1.4.1.231.7.1.2.2.1.35.1.13.8
		sheIgmpControlUploadEnable OBJECT-TYPE
			SYNTAX TruthValue
			MAX-ACCESS read-write
			STATUS current
			DESCRIPTION
				"Whether the FTP upload process is enabled.
				Change the value of sheIgmpUploadEnable.
				If the sheIgmpUploadEnable is changed from disable to enable,
				FTP connection will be verified at the enabling moment. Besides,
				the RootDir is created if they do not exist yet. The command in
				this case is a long running command.
				sheIgmpControlResult trap will be sent to EM to notify the command result.
				"
			DEFVAL { false }
			::= { sheIgmpControl 8 }

		
--  1.3.6.1.4.1.231.7.1.2.2.1.35.1.13.9
		sheIgmpControlFtpRootDir OBJECT-TYPE
			SYNTAX SnmpAdminString
			MAX-ACCESS read-write
			STATUS current
			DESCRIPTION
				"The root directory name on FTP server that stores the
				IGMP log data of this DSLAM. Change the value of sheIgmpFtpRootDir."
			::= { sheIgmpControl 9 }

		
--  1.3.6.1.4.1.231.7.1.2.2.1.35.1.13.10
		sheIgmpControlFtpIp OBJECT-TYPE
			SYNTAX IpAddress
			MAX-ACCESS read-write
			STATUS current
			DESCRIPTION
				"FTP server's IP address. Change the value of sheIgmpFtpIp."
			::= { sheIgmpControl 10 }

		
--  1.3.6.1.4.1.231.7.1.2.2.1.35.1.13.11
		sheIgmpControlFtpUser OBJECT-TYPE
			SYNTAX SnmpAdminString
			MAX-ACCESS read-write
			STATUS current
			DESCRIPTION
				"FTP user name.  Change the value of sheIgmpFtpUser."
			::= { sheIgmpControl 11 }

		
--  1.3.6.1.4.1.231.7.1.2.2.1.35.1.13.12
		sheIgmpControlFtpPassword OBJECT-TYPE
			SYNTAX OCTET STRING (SIZE (0..128))
			MAX-ACCESS read-write
			STATUS current
			DESCRIPTION
				"FTP server access password. To protect the password, the string
				of this object in the GetResponse PDU is encrypted."
			::= { sheIgmpControl 12 }

		
--  1.3.6.1.4.1.231.7.1.2.2.1.35.1.13.13
		sheIgmpControlFtpUploadInterval OBJECT-TYPE
			SYNTAX Unsigned32 (1..4294967295)
			UNITS "minutes"
			MAX-ACCESS read-write
			STATUS current
			DESCRIPTION
				"The interval that IGMP log data is uploaded to FTP server.
				Change the value of sheIgmpFtpUploadInterval."
			::= { sheIgmpControl 13 }

		
--  1.3.6.1.4.1.231.7.1.2.2.1.35.1.13.14
		sheIgmpControlPacketRateLimitSubscriber OBJECT-TYPE
			SYNTAX INTEGER (-1..2147483647)
			MAX-ACCESS read-write
			STATUS current
			DESCRIPTION
				"IGMP packets received from the DSL subscriber port is only allowed to be processed
				by the IGMP proxy with a limit of this value per minute.
				-1 is a special value means no limit."
			::= { sheIgmpControl 14 }

		
--  1.3.6.1.4.1.231.7.1.2.2.1.35.1.13.15
		sheIgmpControlPacketRateLimitUplink OBJECT-TYPE
			SYNTAX INTEGER (-1..2147483647)
			MAX-ACCESS read-write
			STATUS current
			DESCRIPTION
				"IGMP packets received from the uplink port is only allowed to be processed 
				by the IGMP proxy with a limit of this value per minute.
				-1 is a special value means no limit."
			::= { sheIgmpControl 15 }

		
--   1.3.6.1.4.1.231.7.1.2.2.1.35.1.13.16
		sheIgmpControlLongTimeOnlineTime OBJECT-TYPE
			SYNTAX INTEGER (0..2147483647)
			MAX-ACCESS read-write
			STATUS current
			DESCRIPTION
				"For every time interval of this value, there should be a log entry sent 
				to the FTP server for those subscribers who have joined a multicast group 
				for more than this time interval.
				"
			::= { sheIgmpControl 16 }

		
--  1.3.6.1.4.1.231.7.1.2.2.1.35.1.13.17
		sheIgmpControlEthernetAccessEnable OBJECT-TYPE
			SYNTAX TruthValue
			MAX-ACCESS read-write
			STATUS current
			DESCRIPTION
				"When sheIgmpEthernetAccessEnable is true, if ethernet port of the CxU is configured as aggregate, 
				multicast traffic could be accessed only if there's IGMP report sent from it.
				
				When sheIgmpEthernetAccessEnable is false, if ethernet port of the CxU is configured as aggregate, 
				multicast traffic could be accessed without IGMP report."
			::= { sheIgmpControl 17 }

		
--  1.3.6.1.4.1.231.7.1.2.2.1.35.2
		sheIgmpPreviewPackageTable OBJECT-TYPE
			SYNTAX SEQUENCE OF SheIgmpPreviewPackageEntry
			MAX-ACCESS not-accessible
			STATUS current
			DESCRIPTION
				"This table contains information of preview packages. Each
				entry defines a preview package."
			::= { sheIgmpMib 2 }

		
--  1.3.6.1.4.1.231.7.1.2.2.1.35.2.1
		sheIgmpPreviewPackageEntry OBJECT-TYPE
			SYNTAX SheIgmpPreviewPackageEntry
			MAX-ACCESS not-accessible
			STATUS current
			DESCRIPTION
				"Entry of the table."
			INDEX { sheIgmpPreviewPackageIndex }
			::= { sheIgmpPreviewPackageTable 1 }

		
		SheIgmpPreviewPackageEntry ::=
			SEQUENCE { 
				sheIgmpPreviewPackageIndex
					Unsigned32,
				sheIgmpPreviewPackageDescription
					SnmpAdminString,
				sheIgmpPreviewPackageLastingPeriod
					Unsigned32,
				sheIgmpPreviewPackageIntervalBetweenPreviews
					Unsigned32,
				sheIgmpPreviewPackageMaxPreviewsNum
					Unsigned32,
				sheIgmpPreviewPackageChannelList
					OCTET STRING
			 }

--  1.3.6.1.4.1.231.7.1.2.2.1.35.2.1.1
		sheIgmpPreviewPackageIndex OBJECT-TYPE
			SYNTAX Unsigned32 (1..32)
			MAX-ACCESS read-only
			STATUS current
			DESCRIPTION
				"The index of the preview package."
			::= { sheIgmpPreviewPackageEntry 1 }

		
--  1.3.6.1.4.1.231.7.1.2.2.1.35.2.1.2
		sheIgmpPreviewPackageDescription OBJECT-TYPE
			SYNTAX SnmpAdminString
			MAX-ACCESS read-only
			STATUS current
			DESCRIPTION
				"The description of this preview package."
			::= { sheIgmpPreviewPackageEntry 2 }

		
--  1.3.6.1.4.1.231.7.1.2.2.1.35.2.1.3
		sheIgmpPreviewPackageLastingPeriod OBJECT-TYPE
			SYNTAX Unsigned32
			UNITS "minutes"
			MAX-ACCESS read-only
			STATUS current
			DESCRIPTION
				"The duration (in minutes) for each preview period."
			::= { sheIgmpPreviewPackageEntry 3 }

		
--  1.3.6.1.4.1.231.7.1.2.2.1.35.2.1.4
		sheIgmpPreviewPackageIntervalBetweenPreviews OBJECT-TYPE
			SYNTAX Unsigned32
			UNITS "minutes"
			MAX-ACCESS read-only
			STATUS current
			DESCRIPTION
				"The time that a user must wait before starting next preview."
			::= { sheIgmpPreviewPackageEntry 4 }

		
--  1.3.6.1.4.1.231.7.1.2.2.1.35.2.1.5
		sheIgmpPreviewPackageMaxPreviewsNum OBJECT-TYPE
			SYNTAX Unsigned32
			MAX-ACCESS read-only
			STATUS current
			DESCRIPTION
				"How many previews are allowed on a subscriber."
			::= { sheIgmpPreviewPackageEntry 5 }

		
--  1.3.6.1.4.1.231.7.1.2.2.1.35.2.1.6
		sheIgmpPreviewPackageChannelList OBJECT-TYPE
			SYNTAX OCTET STRING (SIZE (0..8192))
			MAX-ACCESS read-only
			STATUS current
			DESCRIPTION
				"The list of pairs of octets each identifying a corresponding
				index of the sheIgmpGroupTable (sheIgmpGroupIndex). It shows
				the channels that are members of this preview package.
				The least significant byte is the second octet.
				"
			::= { sheIgmpPreviewPackageEntry 6 }

		
--  1.3.6.1.4.1.231.7.1.2.2.1.35.3
		sheIgmpPreviewPackageControl OBJECT IDENTIFIER ::= { sheIgmpMib 3 }

		
--  1.3.6.1.4.1.231.7.1.2.2.1.35.3.1
		sheIgmpPreviewPackageControlRequest OBJECT-TYPE
			SYNTAX SheIgmpControlRequestType
			MAX-ACCESS read-write
			STATUS current
			DESCRIPTION
				"Command to configure preview package.
				It must be the last member in the varBindList of the SNMP set request.
				The parameters for different commands are listed below:
				    createPreviewPackage:
				        sheIgmpPreviewPackageControlLastingPeriod
				        sheIgmpPreviewPackageControlIntervalBetweenPreviews
				        sheIgmpPreviewPackageControlMaxPreviewsNum
				        (optional)
				        sheIgmpPreviewPackageControlDescription
				    deletePreviewPackage:
				        sheIgmpPreviewPackageControlIndex
				    modifyPreviewPackage:
				        (must)
				        sheIgmpPreviewPackageControlIndex
				        (optional, but at least one of them should be there)
				        sheIgmpPreviewPackageControlLastingPeriod
				        sheIgmpPreviewPackageControlIntervalBetweenPreviews
				        sheIgmpPreviewPackageControlMaxPreviewsNum
				        sheIgmpPreviewPackageControlDescription
				    addChannel2PreviewPackage:
				    deleteChannelFromPreviewPackage:
				        sheIgmpPreviewPackageControlIndex
				        sheIgmpPreviewPackageControlChannelIndex
				"
			::= { sheIgmpPreviewPackageControl 1 }

		
--  1.3.6.1.4.1.231.7.1.2.2.1.35.3.2
		sheIgmpPreviewPackageControlStatus OBJECT-TYPE
			SYNTAX SheControlStatusType
			MAX-ACCESS read-only
			STATUS current
			DESCRIPTION
				"The status of a user command."
			::= { sheIgmpPreviewPackageControl 2 }

		
--  1.3.6.1.4.1.231.7.1.2.2.1.35.3.3
		sheIgmpPreviewPackageControlTimer OBJECT-TYPE
			SYNTAX Gauge32
			MAX-ACCESS read-only
			STATUS current
			DESCRIPTION
				"The maximum wait time for the manager for a long running user command."
			::= { sheIgmpPreviewPackageControl 3 }

		
--  1.3.6.1.4.1.231.7.1.2.2.1.35.3.4
		sheIgmpPreviewPackageControlReqResult OBJECT-TYPE
			SYNTAX SheIgmpControlRequestResultType
			MAX-ACCESS read-only
			STATUS current
			DESCRIPTION
				"The result of the last user command."
			::= { sheIgmpPreviewPackageControl 4 }

		
--  1.3.6.1.4.1.231.7.1.2.2.1.35.3.5
		sheIgmpPreviewPackageControlTimeStamp OBJECT-TYPE
			SYNTAX Unsigned32
			UNITS "sec"
			MAX-ACCESS read-only
			STATUS current
			DESCRIPTION
				"The time stamp of the last command (end of command)."
			::= { sheIgmpPreviewPackageControl 5 }

		
--  1.3.6.1.4.1.231.7.1.2.2.1.35.3.6
		sheIgmpPreviewPackageControlIndex OBJECT-TYPE
			SYNTAX Unsigned32 (1..32)
			MAX-ACCESS read-write
			STATUS current
			DESCRIPTION
				"The index of the preview package."
			::= { sheIgmpPreviewPackageControl 6 }

		
--  1.3.6.1.4.1.231.7.1.2.2.1.35.3.7
		sheIgmpPreviewPackageControlDescription OBJECT-TYPE
			SYNTAX SnmpAdminString
			MAX-ACCESS read-write
			STATUS current
			DESCRIPTION
				"The description of preview package."
			::= { sheIgmpPreviewPackageControl 7 }

		
--  1.3.6.1.4.1.231.7.1.2.2.1.35.3.8
		sheIgmpPreviewPackageControlLastingPeriod OBJECT-TYPE
			SYNTAX Unsigned32
			UNITS "minutes"
			MAX-ACCESS read-write
			STATUS current
			DESCRIPTION
				"The duration (in minutes) for each preview period."
			::= { sheIgmpPreviewPackageControl 8 }

		
--  1.3.6.1.4.1.231.7.1.2.2.1.35.3.9
		sheIgmpPreviewPackageControlIntervalBetweenPreviews OBJECT-TYPE
			SYNTAX Unsigned32
			UNITS "minutes"
			MAX-ACCESS read-write
			STATUS current
			DESCRIPTION
				"The time that a user must wait before starting next preview."
			::= { sheIgmpPreviewPackageControl 9 }

		
--  1.3.6.1.4.1.231.7.1.2.2.1.35.3.10
		sheIgmpPreviewPackageControlMaxPreviewsNum OBJECT-TYPE
			SYNTAX Unsigned32
			MAX-ACCESS read-write
			STATUS current
			DESCRIPTION
				"How many previews are allowed on a subscriber."
			::= { sheIgmpPreviewPackageControl 10 }

		
--  1.3.6.1.4.1.231.7.1.2.2.1.35.3.11
		sheIgmpPreviewPackageControlChannelIndex OBJECT-TYPE
			SYNTAX Unsigned32 (1..1000)
			MAX-ACCESS read-write
			STATUS current
			DESCRIPTION
				"The channel index that will be added to or deleted from the preview package. 
				The value will be equal to an existing sheIgmpGroupIndex from sheBridgeMib, which
				represent an IgmpChannel."
			::= { sheIgmpPreviewPackageControl 11 }

		
--  1.3.6.1.4.1.231.7.1.2.2.1.35.4
		sheIgmpSubscriberTable OBJECT-TYPE
			SYNTAX SEQUENCE OF SheIgmpSubscriberEntry
			MAX-ACCESS not-accessible
			STATUS current
			DESCRIPTION
				"Each entry in this table defines the multicast parameters for
				a subscriber."
			::= { sheIgmpMib 4 }

		
--  1.3.6.1.4.1.231.7.1.2.2.1.35.4.1
		sheIgmpSubscriberEntry OBJECT-TYPE
			SYNTAX SheIgmpSubscriberEntry
			MAX-ACCESS not-accessible
			STATUS current
			DESCRIPTION
				"Entry of the table indeced by sheBridgePortIndex.
				The sheBridgePortIndex is an external index defined in she-bridge-mib."
			INDEX { sheBridgePortIndex }
			::= { sheIgmpSubscriberTable 1 }

		
		SheIgmpSubscriberEntry ::=
			SEQUENCE { 
				sheIgmpSubscriberPreviewPackageIndex
					Unsigned32,
				sheIgmpSubscriberPreviewRemains
					Unsigned32
			 }

--  1.3.6.1.4.1.231.7.1.2.2.1.35.4.1.4
		sheIgmpSubscriberPreviewPackageIndex OBJECT-TYPE
			SYNTAX Unsigned32 (0 | 1..32)
			MAX-ACCESS read-only
			STATUS current
			DESCRIPTION
				"The index of the preview package that is applied on this subscriber.
				0 means no package assigned."
			DEFVAL { 0 }
			::= { sheIgmpSubscriberEntry 4 }

		
--  1.3.6.1.4.1.231.7.1.2.2.1.35.4.1.5
		sheIgmpSubscriberPreviewRemains OBJECT-TYPE
			SYNTAX Unsigned32
			MAX-ACCESS read-only
			STATUS current
			DESCRIPTION
				"The number of previews that are still available on this subscriber
				currently. The initial value of this object equals to
				sheIgmpPreviewPackageMaxPreviewsNum. It decreases by 1 each time when
				the subscriber starts a preview. If this number reaches 0, this
				subscriber cannot preview any more, unless this counter is reset by EM."
			DEFVAL { 0 }
			::= { sheIgmpSubscriberEntry 5 }

		
--  1.3.6.1.4.1.231.7.1.2.2.1.35.5
		sheIgmpSubscriberControl OBJECT IDENTIFIER ::= { sheIgmpMib 5 }

		
--  1.3.6.1.4.1.231.7.1.2.2.1.35.5.1
		sheIgmpSubscriberControlRequest OBJECT-TYPE
			SYNTAX SheIgmpControlRequestType
			MAX-ACCESS read-write
			STATUS current
			DESCRIPTION
				"Command to configure subscriber parameters.
				It must be the last member in the varBindList of the SNMP set request.
				The parameters for different commands are listed below:
				        (must)
				        sheIgmpSubscriberControlIndex
				    setSubscriberPreviewPackage:
				        sheIgmpSubscriberControlPreviewPackageIndex
				    deleteSubscriberPreviewPackage:
				    resetSubscriberPreviewRemainsCount:
				        (no additional parameters)
				"
			::= { sheIgmpSubscriberControl 1 }

		
--  1.3.6.1.4.1.231.7.1.2.2.1.35.5.2
		sheIgmpSubscriberControlStatus OBJECT-TYPE
			SYNTAX SheControlStatusType
			MAX-ACCESS read-only
			STATUS current
			DESCRIPTION
				"The status of a user command."
			::= { sheIgmpSubscriberControl 2 }

		
--  1.3.6.1.4.1.231.7.1.2.2.1.35.5.3
		sheIgmpSubscriberControlTimer OBJECT-TYPE
			SYNTAX Gauge32
			MAX-ACCESS read-only
			STATUS current
			DESCRIPTION
				"The maximum wait time for the manager for a long running user command."
			::= { sheIgmpSubscriberControl 3 }

		
--  1.3.6.1.4.1.231.7.1.2.2.1.35.5.4
		sheIgmpSubscriberControlReqResult OBJECT-TYPE
			SYNTAX SheIgmpControlRequestResultType
			MAX-ACCESS read-only
			STATUS current
			DESCRIPTION
				"The result of the last user command."
			::= { sheIgmpSubscriberControl 4 }

		
--  1.3.6.1.4.1.231.7.1.2.2.1.35.5.5
		sheIgmpSubscriberControlTimeStamp OBJECT-TYPE
			SYNTAX Unsigned32
			UNITS "sec"
			MAX-ACCESS read-only
			STATUS current
			DESCRIPTION
				"The time stamp of the last command (end of command)."
			::= { sheIgmpSubscriberControl 5 }

		
--  1.3.6.1.4.1.231.7.1.2.2.1.35.5.6
		sheIgmpSubscriberControlIndex OBJECT-TYPE
			SYNTAX Unsigned32 (1..65535)
			MAX-ACCESS read-write
			STATUS current
			DESCRIPTION
				"The sheBridgePortIndex to identify a subscriber."
			::= { sheIgmpSubscriberControl 6 }

		
--  1.3.6.1.4.1.231.7.1.2.2.1.35.5.9
		sheIgmpSubscriberControlPreviewPackageIndex OBJECT-TYPE
			SYNTAX Unsigned32 (1..32)
			MAX-ACCESS read-write
			STATUS current
			DESCRIPTION
				"The index of the preview package that is applied on this subscriber."
			::= { sheIgmpSubscriberControl 9 }

		
--   -----------------------------------------------------------------
-- FTP Upload Information
-- -----------------------------------------------------------------
-- 1.3.6.1.4.1.231.7.1.2.2.1.35.7
		sheIgmpUploadInfo OBJECT IDENTIFIER ::= { sheIgmpMib 7 }

		
--  1.3.6.1.4.1.231.7.1.2.2.1.35.7.1
		sheIgmpLastUploadStatus OBJECT-TYPE
			SYNTAX SheIgmpUploadStatusType
			MAX-ACCESS read-only
			STATUS current
			DESCRIPTION
				"The status of last FTP upload operation.
				It could be uploadSuccess(1) or uploadFail(2)."
			::= { sheIgmpUploadInfo 1 }

		
--  1.3.6.1.4.1.231.7.1.2.2.1.35.7.2
		sheIgmpLastUploadTimeStamp OBJECT-TYPE
			SYNTAX TimeTicks
			MAX-ACCESS read-only
			STATUS current
			DESCRIPTION
				"The time stamp of the last FTP upload operation (end of operation)."
			::= { sheIgmpUploadInfo 2 }

		
--  1.3.6.1.4.1.231.7.1.2.2.1.35.7.3
		sheIgmpLastUploadFileName OBJECT-TYPE
			SYNTAX SnmpAdminString
			MAX-ACCESS read-only
			STATUS current
			DESCRIPTION
				"The file name of last FTP upload operation."
			::= { sheIgmpUploadInfo 3 }

		
--  1.3.6.1.4.1.231.7.1.2.2.1.35.7.4
		sheIgmpLastUploadErrorString OBJECT-TYPE
			SYNTAX SnmpAdminString
			MAX-ACCESS read-only
			STATUS current
			DESCRIPTION
				"The text that describes the FTP upload failure. If upload succeeded, this string is empty."
			::= { sheIgmpUploadInfo 4 }

		
--   -----------------------------------------------------------------
-- Trap definitions
-- -----------------------------------------------------------------
-- 1.3.6.1.4.1.231.7.1.2.2.1.35.8
		sheIgmpNotification OBJECT IDENTIFIER ::= { sheIgmpMib 8 }

		
--  1.3.6.1.4.1.231.7.1.2.2.1.35.8.1
		sheIgmpEvents OBJECT IDENTIFIER ::= { sheIgmpNotification 1 }

		
--  1.3.6.1.4.1.231.7.1.2.2.1.35.8.1.1
		sheIgmpControlResult NOTIFICATION-TYPE
			OBJECTS { sheIgmpControlTimeStamp, sheIgmpControlRequest, sheIgmpControlReqResult }
			STATUS current
			DESCRIPTION 
				"Notification sent at the end of long running command.
				The possible values of sheIgmpControlReqResult are:
				    wrongIpAddress(2),      -- IP address of FTP server is incorrect
				    wrongUserPassword(3),   -- The user name or password is wrong
				    permissionDenied(4),    -- The user name has no permission to create dir/file
				    commandSucceeded(37),
				    commandFailed(36)
				"
			::= { sheIgmpEvents 1 }

		
--  1.3.6.1.4.1.231.7.1.2.2.1.35.8.1.2
		sheIgmpUploadFailedTrap NOTIFICATION-TYPE
			OBJECTS { sheIgmpLastUploadStatus, sheIgmpLastUploadTimeStamp, sheIgmpLastUploadFileName, sheIgmpLastUploadErrorString }
			STATUS current
			DESCRIPTION 
				"Indicates that an FTP upload failure occurred."
			::= { sheIgmpEvents 2 }

		
--  1.3.6.1.4.1.231.7.1.2.2.1.35.8.1.3
		sheIgmpPreviewPackageControlResult NOTIFICATION-TYPE
			OBJECTS { sheIgmpPreviewPackageControlIndex, sheIgmpPreviewPackageControlTimeStamp, sheIgmpPreviewPackageControlReqResult, sheIgmpPreviewPackageControlRequest }
			STATUS current
			DESCRIPTION 
				"Notification sent at the end of preview package command."
			::= { sheIgmpEvents 3 }

		
--   -----------------------------------------------------------------
-- The following definition is for IPTV v2.0
-- IPTV v2.0 includes CAC,Static Multicast Stream,Auto Reset Preview Time,
-- CDR Recognition Time and CDR file format enhancement
-- -----------------------------------------------------------------
-- -----------------------------------------------------------------
-- v2 General Parameters
-- 
-- -----------------------------------------------------------------
-- 1.3.6.1.4.1.231.7.1.2.2.1.35.9
		sheIgmpParaV2 OBJECT IDENTIFIER ::= { sheIgmpMib 9 }

		
--  1.3.6.1.4.1.231.7.1.2.2.1.35.9.1
		sheIgmpParaV2CDRTime OBJECT-TYPE
			SYNTAX Unsigned32 (0 | 1..30)
			UNITS "sec"
			MAX-ACCESS read-only
			STATUS current
			DESCRIPTION
				"This attribute indicates the value of CDR Recognition Time.
				Value 0 means user doesn't configure IGMP Log CDR Time and IGMP Log CDR process
				doesn't take effect."
			DEFVAL { 0 }
			::= { sheIgmpParaV2 1 }

		
--   -----------------------------------------------------------------
-- V2 :  Para Control Group
-- -----------------------------------------------------------------
-- 1.3.6.1.4.1.231.7.1.2.2.1.35.10
		sheIgmpParaV2Control OBJECT IDENTIFIER ::= { sheIgmpMib 10 }

		
--  1.3.6.1.4.1.231.7.1.2.2.1.35.10.1
		sheIgmpParaV2ControlRequest OBJECT-TYPE
			SYNTAX SheIgmpControlRequestType
			MAX-ACCESS read-write
			STATUS current
			DESCRIPTION
				"It must be the last member in the varBindList of the SNMP set request.
				The commands:
				    setIgmpCDRTime
				       The parameter for this command is sheIgmpParaV2ControlCDRTime."
			::= { sheIgmpParaV2Control 1 }

		
--  1.3.6.1.4.1.231.7.1.2.2.1.35.10.2
		sheIgmpParaV2ControlStatus OBJECT-TYPE
			SYNTAX Unsigned32
			MAX-ACCESS read-only
			STATUS current
			DESCRIPTION
				"The status of a control request."
			::= { sheIgmpParaV2Control 2 }

		
--  1.3.6.1.4.1.231.7.1.2.2.1.35.10.3
		sheIgmpParaV2ControlTimer OBJECT-TYPE
			SYNTAX Unsigned32
			MAX-ACCESS read-only
			STATUS current
			DESCRIPTION
				"The maximum wait time for the manager for command ending.
				For long running commands.
				The manager reads this value from the SHE."
			::= { sheIgmpParaV2Control 3 }

		
--  1.3.6.1.4.1.231.7.1.2.2.1.35.10.4
		sheIgmpParaV2ControlReqResult OBJECT-TYPE
			SYNTAX SheIgmpControlRequestResultType
			MAX-ACCESS read-only
			STATUS current
			DESCRIPTION
				"The result of the last user command."
			::= { sheIgmpParaV2Control 4 }

		
--  1.3.6.1.4.1.231.7.1.2.2.1.35.10.5
		sheIgmpParaV2ControlTimeStamp OBJECT-TYPE
			SYNTAX Unsigned32
			UNITS "sec"
			MAX-ACCESS read-only
			STATUS current
			DESCRIPTION
				"The time stamp of the last command (end of command)."
			::= { sheIgmpParaV2Control 5 }

		
--  1.3.6.1.4.1.231.7.1.2.2.1.35.10.6
		sheIgmpParaV2ControlCDRTime OBJECT-TYPE
			SYNTAX Unsigned32 (0 | 1..30)
			UNITS "sec"
			MAX-ACCESS read-write
			STATUS current
			DESCRIPTION
				"This attribute indicates the value of CDR recognition time. 
				Value 0 means user doesn't configure IGMP Log CDR Time and IGMP Log CDR process
				doesn't take effect."
			::= { sheIgmpParaV2Control 6 }

		
--   -----------------------------------------------------------------
-- Multicast Group Configure Table V2
-- -----------------------------------------------------------------
-- 1.3.6.1.4.1.231.7.1.2.2.1.35.11
		sheIgmpMulticastChannelTable OBJECT-TYPE
			SYNTAX SEQUENCE OF SheIgmpMulticastChannelEntry
			MAX-ACCESS not-accessible
			STATUS current
			DESCRIPTION
				"This table contains information for the Bandwidth
				assigned to every Multicast Group."
			::= { sheIgmpMib 11 }

		
--  1.3.6.1.4.1.231.7.1.2.2.1.35.11.1
		sheIgmpMulticastChannelEntry OBJECT-TYPE
			SYNTAX SheIgmpMulticastChannelEntry
			MAX-ACCESS not-accessible
			STATUS current
			DESCRIPTION
				"Each entry contains the configured bandwidth value of a Multicast Group.
				The sheIgmpGroupIndex is an external index defined in she-bridge-mib."
			INDEX { sheIgmpGroupIndex }
			::= { sheIgmpMulticastChannelTable 1 }

		
		SheIgmpMulticastChannelEntry ::=
			SEQUENCE { 
				sheIgmpMulticastChannelDelayLeaveTime
					Unsigned32
			 }

--  1.3.6.1.4.1.231.7.1.2.2.1.35.11.1.1
		sheIgmpMulticastChannelDelayLeaveTime OBJECT-TYPE
			SYNTAX Unsigned32
			MAX-ACCESS read-only
			STATUS current
			DESCRIPTION
				"Time interval for which the IGMP proxy 's host will delay to send 
				a leave to the Router side when no membership is in a multicast channel."
			::= { sheIgmpMulticastChannelEntry 1 }

		
--   -----------------------------------------------------------------
-- Multicast Group Configure Table V2
--         Control Group
-- -----------------------------------------------------------------
-- 1.3.6.1.4.1.231.7.1.2.2.1.35.12
		sheIgmpMulticastChannelControl OBJECT IDENTIFIER ::= { sheIgmpMib 12 }

		
--  1.3.6.1.4.1.231.7.1.2.2.1.35.12.1
		sheIgmpMulticastChannelControlRequest OBJECT-TYPE
			SYNTAX SheIgmpControlRequestType
			MAX-ACCESS read-write
			STATUS current
			DESCRIPTION
				"Command to set multicast channel delay leave time.
				It must be the last member in the varBindList of the SNMP set request.
				The commands:
				    setIgmpSetMulticastChannelV2Para
				       The Parameters of this command are
				           sheIgmpMulticastChannelControlChannelIndex
				           sheIgmpMulticastChannelControlDelayLeaveTime"
			::= { sheIgmpMulticastChannelControl 1 }

		
--  1.3.6.1.4.1.231.7.1.2.2.1.35.12.2
		sheIgmpMulticastChannelControlStatus OBJECT-TYPE
			SYNTAX Unsigned32
			MAX-ACCESS read-only
			STATUS current
			DESCRIPTION
				"The status of a control request."
			::= { sheIgmpMulticastChannelControl 2 }

		
--  1.3.6.1.4.1.231.7.1.2.2.1.35.12.3
		sheIgmpMulticastChannelControlReqResult OBJECT-TYPE
			SYNTAX SheIgmpControlRequestResultType
			MAX-ACCESS read-only
			STATUS current
			DESCRIPTION
				"The result of the last user command."
			::= { sheIgmpMulticastChannelControl 3 }

		
--  1.3.6.1.4.1.231.7.1.2.2.1.35.12.4
		sheIgmpMulticastChannelControlTimeStamp OBJECT-TYPE
			SYNTAX Unsigned32
			UNITS "sec"
			MAX-ACCESS read-only
			STATUS current
			DESCRIPTION
				"The time stamp of the last command (end of command)."
			::= { sheIgmpMulticastChannelControl 4 }

		
--  1.3.6.1.4.1.231.7.1.2.2.1.35.12.5
		sheIgmpMulticastChannelControlChannelIndex OBJECT-TYPE
			SYNTAX Unsigned32 (1..1000)
			MAX-ACCESS read-write
			STATUS current
			DESCRIPTION
				"This attribute indicates the index of the multicast group being configured."
			::= { sheIgmpMulticastChannelControl 5 }

		
--  1.3.6.1.4.1.231.7.1.2.2.1.35.12.6
		sheIgmpMulticastChannelControlDelayLeaveTime OBJECT-TYPE
			SYNTAX Unsigned32
			MAX-ACCESS read-write
			STATUS current
			DESCRIPTION
				"Time interval for which the IGMP proxy 's host will delay to send 
				a leave to the Router side when no membership is in a multicast channel."
			::= { sheIgmpMulticastChannelControl 6 }

		
--   --------------------------------------------------------------------
-- Preview ART:  Preview Auto Reset Time
-- 1.3.6.1.4.1.231.7.1.2.2.1.35.13
		sheIgmpPreviewV2Para OBJECT IDENTIFIER ::= { sheIgmpMib 13 }

		
--  1.3.6.1.4.1.231.7.1.2.2.1.35.13.1
		sheIgmpPreviewV2ParaARTEnable OBJECT-TYPE
			SYNTAX TruthValue
			MAX-ACCESS read-only
			STATUS current
			DESCRIPTION
				"This attribute indicates whether the preview auto reset time functionlaity is enabled."
			DEFVAL { false }
			::= { sheIgmpPreviewV2Para 1 }

		
--  1.3.6.1.4.1.231.7.1.2.2.1.35.13.2
		sheIgmpPreviewV2ParaARTStartTime OBJECT-TYPE
			SYNTAX DateAndTime
			MAX-ACCESS read-only
			STATUS current
			DESCRIPTION
				"This attribute indicates the start time of auto reset timer. "
			::= { sheIgmpPreviewV2Para 2 }

		
--  1.3.6.1.4.1.231.7.1.2.2.1.35.13.3
		sheIgmpPreviewV2ParaARTUnit OBJECT-TYPE
			SYNTAX SheIgmpPreviewAutoResetTimeUnitType
			MAX-ACCESS read-only
			STATUS current
			DESCRIPTION
				"This attribute indicates the unit of the timer."
			DEFVAL { day }
			::= { sheIgmpPreviewV2Para 3 }

		
--  1.3.6.1.4.1.231.7.1.2.2.1.35.13.4
		sheIgmpPreviewV2ParaARTValue OBJECT-TYPE
			SYNTAX Unsigned32
			MAX-ACCESS read-only
			STATUS current
			DESCRIPTION
				"This attribute indicates the configured value of the preview auto reset timer.
				The timer value will be decided together by sheIgmpPreviewAutoResetTimeValue
				and the sheIgmpPreviewAutoResetTimeUnit.
				e.g. if the sheIgmpPreviewAutoResetTimeUnit is day(1)
				and the sheIgmpPreviewAutoResetTimeValue is 30
				then the value of auto reset timer is 30 days."
			DEFVAL { 30 }
			::= { sheIgmpPreviewV2Para 4 }

		
--   --------------------------------------------------------------------
-- Preview Auto Reset Time
--     Control Group
-- 1.3.6.1.4.1.231.7.1.2.2.1.35.14
		sheIgmpPreviewV2ParaControl OBJECT IDENTIFIER ::= { sheIgmpMib 14 }

		
--  1.3.6.1.4.1.231.7.1.2.2.1.35.14.1
		sheIgmpPreviewV2ParaControlRequest OBJECT-TYPE
			SYNTAX SheIgmpControlRequestType
			MAX-ACCESS read-write
			STATUS current
			DESCRIPTION
				"Command related to the preview auto reset time.
				It must be the last member in the varBindList of the SNMP set request.
				The commands:
				  setIgmpPreviewAutoResetTimeEnable
				    The parameters for this command are
				            sheIgmpPreviewV2ParaControlARTStartTime
				            sheIgmpPreviewV2ParaControlARTEnable
				            sheIgmpPreviewV2ParaControlARTUnit
				            sheIgmpPreviewV2ParaControlARTValue
				              "
			::= { sheIgmpPreviewV2ParaControl 1 }

		
--  1.3.6.1.4.1.231.7.1.2.2.1.35.14.2
		sheIgmpPreviewV2ParaControlStatus OBJECT-TYPE
			SYNTAX Unsigned32
			MAX-ACCESS read-only
			STATUS current
			DESCRIPTION
				"The status of a control request."
			::= { sheIgmpPreviewV2ParaControl 2 }

		
--  1.3.6.1.4.1.231.7.1.2.2.1.35.14.3
		sheIgmpPreviewV2ParaControlReqResult OBJECT-TYPE
			SYNTAX SheIgmpControlRequestResultType
			MAX-ACCESS read-only
			STATUS current
			DESCRIPTION
				"The result of the last user command."
			::= { sheIgmpPreviewV2ParaControl 3 }

		
--  1.3.6.1.4.1.231.7.1.2.2.1.35.14.4
		sheIgmpPreviewV2ParaControlTimeStamp OBJECT-TYPE
			SYNTAX Unsigned32
			UNITS "sec"
			MAX-ACCESS read-only
			STATUS current
			DESCRIPTION
				"The time stamp of the last command (end of command)."
			::= { sheIgmpPreviewV2ParaControl 4 }

		
--  1.3.6.1.4.1.231.7.1.2.2.1.35.14.5
		sheIgmpPreviewV2ParaControlARTEnable OBJECT-TYPE
			SYNTAX TruthValue
			MAX-ACCESS read-write
			STATUS current
			DESCRIPTION
				"This attribute indicates whether the preview auto reset is enabled"
			::= { sheIgmpPreviewV2ParaControl 5 }

		
--  1.3.6.1.4.1.231.7.1.2.2.1.35.14.6
		sheIgmpPreviewV2ParaControlARTStartTime OBJECT-TYPE
			SYNTAX DateAndTime
			MAX-ACCESS read-write
			STATUS current
			DESCRIPTION
				"This attribute indicates the start time of the auto reset timer"
			::= { sheIgmpPreviewV2ParaControl 6 }

		
--  1.3.6.1.4.1.231.7.1.2.2.1.35.14.7
		sheIgmpPreviewV2ParaControlARTUnit OBJECT-TYPE
			SYNTAX SheIgmpPreviewAutoResetTimeUnitType
			MAX-ACCESS read-write
			STATUS current
			DESCRIPTION
				"This attribute indicates the unit of the preview auto reset timer"
			::= { sheIgmpPreviewV2ParaControl 7 }

		
--  1.3.6.1.4.1.231.7.1.2.2.1.35.14.8
		sheIgmpPreviewV2ParaControlARTValue OBJECT-TYPE
			SYNTAX Unsigned32
			MAX-ACCESS read-write
			STATUS current
			DESCRIPTION
				"This attribute indicates the value of the preview auto reset timer"
			::= { sheIgmpPreviewV2ParaControl 8 }

		
		sheIgmpMibConformance OBJECT IDENTIFIER ::= { sheIgmpMib 100 }

		
		sheIgmpMibCompliances OBJECT IDENTIFIER ::= { sheIgmpMibConformance 1 }

		
		sheIgmpMibCompliance MODULE-COMPLIANCE
			STATUS current
			DESCRIPTION 
				"Description."
			MODULE -- this module
				MANDATORY-GROUPS { sheIgmpMibGroup, sheIgmpMibControlGroup, sheIgmpMibNotificationGroup }
			::= { sheIgmpMibCompliances 1 }

		
		sheIgmpMibGroups OBJECT IDENTIFIER ::= { sheIgmpMibConformance 2 }

		
		sheIgmpMibGroup OBJECT-GROUP
			OBJECTS { sheIgmpPreviewPackageIndex, sheIgmpPreviewPackageDescription, sheIgmpPreviewPackageLastingPeriod, sheIgmpPreviewPackageIntervalBetweenPreviews, sheIgmpPreviewPackageMaxPreviewsNum, 
				sheIgmpPreviewPackageChannelList, sheIgmpSubscriberPreviewPackageIndex, sheIgmpSubscriberPreviewRemains, sheIgmpPreviewV2ParaARTEnable, sheIgmpPreviewV2ParaARTStartTime, 
				sheIgmpPreviewV2ParaARTUnit, sheIgmpPreviewV2ParaARTValue, sheIgmpLastUploadStatus, sheIgmpLastUploadTimeStamp, sheIgmpLastUploadFileName, 
				sheIgmpLastUploadErrorString, sheIgmpParaV2CDRTime, sheIgmpMulticastChannelDelayLeaveTime, sheIgmpProgramPreviewEnable, sheIgmpLogEnable, 
				sheIgmpUploadEnable, sheIgmpFtpRootDir, sheIgmpFtpIp, sheIgmpFtpUser, sheIgmpFtpPassword, 
				sheIgmpFtpUploadInterval, sheIgmpPacketRateLimitUplink, sheIgmpPacketRateLimitSubscriber, sheIgmpLongTimeOnlineTime, sheIgmpEthernetAccessEnable
				 }
			STATUS current
			DESCRIPTION 
				"Description."
			::= { sheIgmpMibGroups 1 }

		
		sheIgmpMibControlGroup OBJECT-GROUP
			OBJECTS { sheIgmpControlRequest, sheIgmpControlStatus, sheIgmpControlTimer, sheIgmpControlReqResult, sheIgmpControlTimeStamp, 
				sheIgmpControlProgramPreviewEnable, sheIgmpControlLogEnable, sheIgmpControlUploadEnable, sheIgmpControlFtpRootDir, sheIgmpControlFtpIp, 
				sheIgmpControlFtpUser, sheIgmpControlFtpPassword, sheIgmpControlFtpUploadInterval, sheIgmpControlPacketRateLimitSubscriber, sheIgmpControlPacketRateLimitUplink, 
				sheIgmpControlLongTimeOnlineTime, sheIgmpControlEthernetAccessEnable, sheIgmpPreviewPackageControlRequest, sheIgmpPreviewPackageControlStatus, sheIgmpPreviewPackageControlTimer, 
				sheIgmpPreviewPackageControlReqResult, sheIgmpPreviewPackageControlTimeStamp, sheIgmpPreviewPackageControlIndex, sheIgmpPreviewPackageControlDescription, sheIgmpPreviewPackageControlLastingPeriod, 
				sheIgmpPreviewPackageControlIntervalBetweenPreviews, sheIgmpPreviewPackageControlMaxPreviewsNum, sheIgmpPreviewPackageControlChannelIndex, sheIgmpSubscriberControlRequest, sheIgmpSubscriberControlStatus, 
				sheIgmpSubscriberControlTimer, sheIgmpSubscriberControlReqResult, sheIgmpSubscriberControlTimeStamp, sheIgmpSubscriberControlPreviewPackageIndex, sheIgmpParaV2ControlRequest, 
				sheIgmpParaV2ControlStatus, sheIgmpParaV2ControlTimer, sheIgmpParaV2ControlReqResult, sheIgmpParaV2ControlTimeStamp, sheIgmpParaV2ControlCDRTime, 
				sheIgmpMulticastChannelControlRequest, sheIgmpMulticastChannelControlStatus, sheIgmpMulticastChannelControlReqResult, sheIgmpMulticastChannelControlTimeStamp, sheIgmpMulticastChannelControlChannelIndex, 
				sheIgmpMulticastChannelControlDelayLeaveTime, sheIgmpPreviewV2ParaControlRequest, sheIgmpPreviewV2ParaControlStatus, sheIgmpPreviewV2ParaControlReqResult, sheIgmpPreviewV2ParaControlTimeStamp, 
				sheIgmpPreviewV2ParaControlARTEnable, sheIgmpPreviewV2ParaControlARTStartTime, sheIgmpPreviewV2ParaControlARTUnit, sheIgmpPreviewV2ParaControlARTValue, sheIgmpSubscriberControlIndex
				 }
			STATUS current
			DESCRIPTION 
				"Description."
			::= { sheIgmpMibGroups 2 }

		
		sheIgmpMibNotificationGroup NOTIFICATION-GROUP
			NOTIFICATIONS { sheIgmpControlResult, sheIgmpUploadFailedTrap, sheIgmpPreviewPackageControlResult }
			STATUS current
			DESCRIPTION 
				"Description."
			::= { sheIgmpMibGroups 3 }

		
	
	END

--
-- she-igmp-mib.mib
--
