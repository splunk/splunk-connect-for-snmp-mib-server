-- Enterprise MIB for CC Traps

-- Author: Raritan
--
-- Raritan CC Enterprise MIB.
-- Copyright (C) 2007 Raritan 
-- Raritan Private Enterprise is registered with IANA organization 
-- SNMP V2 MIBS


RARITANCCv2-MIB DEFINITIONS ::= BEGIN
	IMPORTS
                MODULE-IDENTITY, OBJECT-TYPE, Counter32, Counter64, Unsigned32, NOTIFICATION-TYPE
                         FROM SNMPv2-SMI
		NetworkAddress
			 FROM RFC1155-SMI
                mgmt, internet, IpAddress, TimeTicks, enterprises
			 FROM SNMPv2-SMI
		OBJECT-TYPE
			 FROM RFC-1212

		DisplayString
			 FROM SNMPv2-TC;		
			
-- Raritan is registered with IANA for an enterprise MIB 


raritan MODULE-IDENTITY
    LAST-UPDATED "201104111108Z"
    ORGANIZATION "Raritan Inc."
    CONTACT-INFO
            "        Derek Finch
		     Raritan Inc.
		     400 Cottontail Lane
		     Somerset New Jersey, 08873
		     E-mail: derekf@raritan.com"
    DESCRIPTION
            "The MIB modules representing Raritan Inc.'
	    implementation of enterprise specific MIBs 
	    supported by a single SNMP agent."
    REVISION "201104111108Z"
    DESCRIPTION
        "The  version of this MIB module modified for release 5.2.0."

    ::= { enterprises 13742 }


products OBJECT IDENTIFIER ::= { raritan 1 }
enterpriseManagement  OBJECT IDENTIFIER ::= { products 1 }
commandCenter  OBJECT IDENTIFIER ::= { enterpriseManagement 1 }
ccObject OBJECT IDENTIFIER ::= { commandCenter  0 }
ccNotify OBJECT IDENTIFIER ::= { commandCenter  1 }



-- Define Traps for CC
-- 
-- Define all the Trap ASN variables
-- 


ccObjectName OBJECT-TYPE
	SYNTAX	DisplayString
	MAX-ACCESS   read-write
	STATUS	current
	DESCRIPTION
		 " Object class name - CC "
	::= { ccObject 1 }


ccObjectInstance OBJECT-TYPE
	SYNTAX	DisplayString
	MAX-ACCESS   read-write
	STATUS	current
	DESCRIPTION
		 " Object class instance - datacenter- CC1  "
	::= { ccObject 2}


ccUserName OBJECT-TYPE
	SYNTAX	DisplayString
	MAX-ACCESS   read-write
	STATUS	current
	DESCRIPTION
		 " User Name  "
	::= { ccObject 3}



ccUserSessionId OBJECT-TYPE
	SYNTAX	DisplayString
	MAX-ACCESS   read-write
	STATUS	current
	DESCRIPTION
		 " User name session ID  "
	::= { ccObject 4}



ccUserNameInitiated OBJECT-TYPE
	SYNTAX	DisplayString
	MAX-ACCESS   read-write
	STATUS	current
	DESCRIPTION
		 " User Name, who initiated the session termination  "
	::= { ccObject 5 }



ccUserNameTerminated OBJECT-TYPE
	SYNTAX	DisplayString
	MAX-ACCESS   read-write
	STATUS	current
	DESCRIPTION
		 " User Name, whose session got terminated  "
	::= { ccObject 6 }



ccImageType OBJECT-TYPE
	SYNTAX	DisplayString
	MAX-ACCESS   read-write
	STATUS	current
	DESCRIPTION
		 " Image Type to tftp  "
	::= { ccObject 7 }



ccImageVersion OBJECT-TYPE
	SYNTAX	DisplayString
	MAX-ACCESS   read-write
	STATUS	current
	DESCRIPTION
		 " Image version "
	::= { ccObject 8}


ccImageVersionStatus OBJECT-TYPE
	SYNTAX	INTEGER {
			success(1),
			failure(2)
			}
	MAX-ACCESS   read-write
	STATUS	current
	DESCRIPTION
		 " Download image status "
	::= { ccObject 9 }



ccUserWhoAdded OBJECT-TYPE
	SYNTAX	DisplayString
	MAX-ACCESS   read-write
	STATUS	current
	DESCRIPTION
		 " CC User who added an User to the system"
	::= { ccObject 10}



ccUserWhoDeleted  OBJECT-TYPE
	SYNTAX	DisplayString
	MAX-ACCESS   read-write
	STATUS	current
	DESCRIPTION
		 " CC User who Deleted an User to the system"
	::= { ccObject 11}



ccUserWhoModified OBJECT-TYPE
	SYNTAX	DisplayString
	MAX-ACCESS   read-write
	STATUS	current
	DESCRIPTION
		 " CC User who added an User to the system"
	::= { ccObject 12}


ccNodeName  OBJECT-TYPE
	SYNTAX	DisplayString
	MAX-ACCESS   read-write
	STATUS	current
	DESCRIPTION
		 "CC Leaf Node Name  "
	::= { ccObject 13}


ccLanCard OBJECT-TYPE
	SYNTAX	INTEGER {
			 primary(1),
			 backup(2)
			}
	MAX-ACCESS   read-write
	STATUS	current
	DESCRIPTION
		 "CC Lan Card "
	::= { ccObject 14}


ccHardDisk  OBJECT-TYPE
	SYNTAX	INTEGER {
			 primary(1),
			 backup(2)
			}
	MAX-ACCESS   read-write
	STATUS	current
	DESCRIPTION
		 "CC Disk "
	::= { ccObject 15}


ccSessionType OBJECT-TYPE
	SYNTAX	INTEGER {
			 serial(1),
			 kvm(2),
			 powerOutlet(3),
			 admin(4),
			 diagnostics(5)
			 
			}
	MAX-ACCESS   read-write
	STATUS	current
	DESCRIPTION
		 "CC Lan Card "
	::= { ccObject 16}



ccClusterState OBJECT-TYPE
	SYNTAX	INTEGER {
			 primary(1),
			 secondary(2),
			 standAlone(3)
			 }
	MAX-ACCESS   read-write
	STATUS	current
	DESCRIPTION
		 "CC Cluster State "
	::= { ccObject 17}



ccLeafNodeName  OBJECT-TYPE
	SYNTAX	DisplayString
	MAX-ACCESS   read-write
	STATUS	current
	DESCRIPTION
		 "CC Leaf Node Name  "
	::= { ccObject 18}



ccLeafNodeIPAddress OBJECT-TYPE
	SYNTAX	DisplayString
	MAX-ACCESS   read-write
	STATUS	current
	DESCRIPTION
		 "CC Leaf Node IP address  "
	::= { ccObject 19}


ccLeafNodeFirmwareVersion OBJECT-TYPE
	SYNTAX	DisplayString
	MAX-ACCESS   read-write
	STATUS	current
	DESCRIPTION
		 "CC Leaf Node Firmware Version  "
	::= { ccObject 20}


-- CC 3.0 Trap ASN Variables


ccScheduledTaskDescription OBJECT-TYPE
	SYNTAX	DisplayString
	MAX-ACCESS   read-write
	STATUS	current
	DESCRIPTION
		 "CC Scheduled Task Description  "
	::= { ccObject 21}

ccScheduledTaskFailureReason OBJECT-TYPE
	SYNTAX	DisplayString
	MAX-ACCESS   read-write
	STATUS	current
	DESCRIPTION
		 "CC Scheduled Task Failure Reason  "
	::= { ccObject 22}

ccDiagnosticConsoleMAX-ACCESSLevel OBJECT-TYPE
	SYNTAX	DisplayString
	MAX-ACCESS   read-write
	STATUS	current
	DESCRIPTION
		 "CC Diagnostic Console MAX-ACCESS Level "
	::= { ccObject 23}

ccDeviceName OBJECT-TYPE
	SYNTAX	DisplayString
	MAX-ACCESS   read-write
	STATUS	current
	DESCRIPTION
		 " Device Name  "
	::= { ccObject 24}


-- CC 3.1 Trap ASN Variables


ccUserGroupName OBJECT-TYPE
	SYNTAX	DisplayString
	MAX-ACCESS   read-write
	STATUS	current
	DESCRIPTION
		 " User Group Name  "
	::= { ccObject 25}

ccBannerChanges OBJECT-TYPE
	SYNTAX	INTEGER {
			 enabled(1),
			 disabled(2),
			 modified(3)
			 }
	MAX-ACCESS   read-write
	STATUS	current
	DESCRIPTION
		 "CC Banner Changes "
	::= { ccObject 26}
	
ccMOTDChanges OBJECT-TYPE
	SYNTAX	INTEGER {
			 enabled(1),
			 disabled(2),
			 modified(3)
			 }
	MAX-ACCESS   read-write
	STATUS	current
	DESCRIPTION
		 "CC MOTD Changes "
	::= { ccObject 27}


-- CC 4.0 Trap ASN Variables


ccOldNumberOfOutlets OBJECT-TYPE
	SYNTAX	DisplayString
	MAX-ACCESS   read-write
	STATUS	current
	DESCRIPTION
		 " Old number of outlets "
	::= { ccObject 28}
	
ccNewNumberOfOutlets OBJECT-TYPE
	SYNTAX	DisplayString
	MAX-ACCESS   read-write
	STATUS	current
	DESCRIPTION
		 " New number of outlets "
	::= { ccObject 29}		

ccSystemMonitorNotificationLevel OBJECT-TYPE
	SYNTAX	DisplayString
	MAX-ACCESS   read-write
	STATUS	current
	DESCRIPTION
		 " Notification Level  "
	::= { ccObject 30}
	
ccSystemMonitorNotificationMessage OBJECT-TYPE
	SYNTAX	DisplayString
	MAX-ACCESS   read-write
	STATUS	current
	DESCRIPTION
		 " Notification message  "
	::= { ccObject 31}	


-- CC 4.1 Trap ASN Variables


ccDominionPXFirmwareVersion OBJECT-TYPE
	SYNTAX	DisplayString
	MAX-ACCESS   read-write
	STATUS	current
	DESCRIPTION
		 " Dominion PX Firmware Version  "
	::= { ccObject 32}


ccClusterPeer OBJECT-TYPE
	SYNTAX	DisplayString
	MAX-ACCESS   read-write
	STATUS	current
	DESCRIPTION
		 " Cluster peer  "
	::= { ccObject 33}


ccClusterOperation OBJECT-TYPE
	SYNTAX	DisplayString
	MAX-ACCESS   read-write
	STATUS	current
	DESCRIPTION
		 " Cluster operation  "
	::= { ccObject 34}


ccClusterOperationStatus OBJECT-TYPE
	SYNTAX	INTEGER {
			success(1),
			failure(2)
			}
	MAX-ACCESS   read-write
	STATUS	current
	DESCRIPTION
		 " Cluster operation status "
	::= { ccObject 35 }


-- CC 4.2 Trap ASN Variables

ccTransferOperation OBJECT-TYPE
	SYNTAX	INTEGER {
			export(1),
			import(2)
			}
	MAX-ACCESS   read-write
	STATUS	current
	DESCRIPTION
		 " File Transfer Action "
	::= { ccObject 36 }

ccFileType OBJECT-TYPE
    SYNTAX      DisplayString
    MAX-ACCESS  read-write
    STATUS      current
    DESCRIPTION
         "CSV File Type"
    ::= { ccObject  37}

-- CC 5.0 Trap ASN Variables

ccLicensedFeature  OBJECT-TYPE
	SYNTAX 		DisplayString
	MAX-ACCESS	read-write
	STATUS		current
	DESCRIPTION	
			" Licensed Feature  "
	::= { ccObject 38}

	
ccLicenseServer  OBJECT-TYPE
	SYNTAX		DisplayString
	MAX-ACCESS   	read-write
	STATUS		current
	DESCRIPTION
		 " License Server  "
	::= { ccObject 39}

ccPortName OBJECT-TYPE
	SYNTAX	DisplayString
	MAX-ACCESS   read-write
	STATUS	current
	DESCRIPTION
		 " Name of a port  "
	::= { ccObject 41}


-- CC 5.0.5 Trap ASN Variables

ccLicenseTerminatedReason OBJECT-TYPE
	SYNTAX	DisplayString
	MAX-ACCESS   read-write
	STATUS	current
	DESCRIPTION
		 "CC License Terminated Reason "
	::= { ccObject 40}

-- Start v2 the Traps 



ccUnavailable		NOTIFICATION-TYPE
		OBJECTS	{ccObjectName,
			 ccObjectInstance,
			 ccUserName,
                         ccClusterState
			 }
		 STATUS current
	DESCRIPTION
		"CC Application is unavailable"
	::= { ccNotify 1 }



ccAvailable 	NOTIFICATION-TYPE
		OBJECTS	{ccObjectName,
			 ccObjectInstance,
			 ccUserName,
                         ccClusterState
			 }
		STATUS current
                      DESCRIPTION
		"CC Application is Available "
	::= { ccNotify 2 }



ccUserLogin 		NOTIFICATION-TYPE
		OBJECTS	{ccObjectName,
			 ccObjectInstance,
			 ccUserName
			 }
		STATUS current
 
	DESCRIPTION
		"CC User Log in "
	::= { ccNotify 3 }


ccUserLogout 		NOTIFICATION-TYPE
		OBJECTS	{ccObjectName,
			 ccObjectInstance,
			 ccUserName
			 }
		STATUS current
	
	DESCRIPTION
		"CC User Log out "
	::= { ccNotify 4 }


-- A sesssion can be Serial/KVM/power supply

ccSPortConnectionStarted  	NOTIFICATION-TYPE
		OBJECTS	{ccObjectName,
			 ccObjectInstance,
			 ccUserName,
			 ccSessionType,
			 ccUserSessionId,
			 ccNodeName,
			 ccPortName
			 }

		STATUS current

	DESCRIPTION
		"CC  Session started "
	::= { ccNotify 5 }


ccPortConnectionStopped 	NOTIFICATION-TYPE
		OBJECTS	{ccObjectName,
			 ccObjectInstance,
			 ccUserName,
			 ccSessionType,
			 ccUserSessionId,
			 ccNodeName,
			 ccPortName
			 }
STATUS current

			 
	DESCRIPTION
		"CC  Session stopped "
	::= { ccNotify 6 }


ccPortConnectionTerminated 	NOTIFICATION-TYPE
		OBJECTS	{ccObjectName,
			 ccObjectInstance,
			 ccUserNameInitiated,
			 ccUserNameTerminated,
			 ccSessionType,
			 ccUserSessionId,
			 ccNodeName,
			 ccPortName
			 }
STATUS current

	DESCRIPTION
		"CC  Session Terminated "
	::= { ccNotify 7 }


ccImageUpgradeStarted	 NOTIFICATION-TYPE
		OBJECTS	{ccObjectName,
			 ccObjectInstance,
			 ccUserName,
			 ccImageType,
			 ccImageVersion
			 }
STATUS current

	DESCRIPTION
		"CC Image Upgrade started "
	::= { ccNotify 8 }


ccImageUpgradeResults 	NOTIFICATION-TYPE
		OBJECTS	{ccObjectName,
			 ccObjectInstance,
			 ccUserName,
			 ccImageType,
			 ccImageVersion,
			 ccImageVersionStatus
			 }
STATUS current

	DESCRIPTION
		"CC Image Upgrade results"
	::= { ccNotify 9 }


ccUserAdded		NOTIFICATION-TYPE
		OBJECTS	{ccObjectName,
			 ccObjectInstance,
			 ccUserName,
			 ccUserWhoAdded

			 }
	STATUS current

	DESCRIPTION
		"CC - A new user added "
	::= { ccNotify 10 }


ccUserDeleted		 NOTIFICATION-TYPE
		OBJECTS	{ccObjectName,
			 ccObjectInstance,
			 ccUserName,
			 ccUserWhoDeleted
			 }
	STATUS current

	DESCRIPTION
		"CC - A user deleted "
	::= { ccNotify 11 }


ccUserModified  		NOTIFICATION-TYPE

		OBJECTS	{ccObjectName,
			 ccObjectInstance,
			 ccUserName,
			 ccUserWhoModified
			 }
STATUS current

			 
	DESCRIPTION
		"CC user modified "
	::= { ccNotify 12 }


ccUserAuthenticationFailure	NOTIFICATION-TYPE
		OBJECTS	{ccObjectName,
			 ccObjectInstance,
			 ccUserName
			 }
STATUS current

	DESCRIPTION
		"CC user authentication failure "
	::= { ccNotify 13 }






ccRootPasswordChanged	NOTIFICATION-TYPE
		OBJECTS	{ccObjectName,
			 ccObjectInstance,
			 ccUserWhoModified
			 }
STATUS current

	DESCRIPTION
		"CC root password changed "
	::= { ccNotify 14 }
 


-- Added Cluster State attribute for Hard disk failure and Lan Card failure 
-- CC Lan Card - Primary/Backup information

ccLanCardFailure 	NOTIFICATION-TYPE
	
	OBJECTS		{ccObjectName,
			 ccObjectInstance,
			 ccLanCard,
			 ccClusterState
			 }
STATUS current
	DESCRIPTION
		"CC detected a Lan Card Failure"
	::= { ccNotify 15 }


ccHardDiskFailure	NOTIFICATION-TYPE
	
	OBJECTS		{ccObjectName,
			 ccObjectInstance,
			 ccHardDisk,
			 ccClusterState
			 }
STATUS current
	DESCRIPTION
		"CC detected a Hard Disk Failure"
	::= { ccNotify 16 }


ccLeafNodeUnavailable 	NOTIFICATION-TYPE
	
	OBJECTS		{ccObjectName,
			 ccObjectInstance,
			 ccLeafNodeName,
			 ccLeafNodeIPAddress
			 }
STATUS current

	DESCRIPTION
		"CC detected a connection failure to a leaf node"
	::= { ccNotify 17}


ccLeafNodeAvailable 	NOTIFICATION-TYPE
	
	OBJECTS		{ccObjectName,
			 ccObjectInstance,
			 ccLeafNodeName,
			 ccLeafNodeIPAddress
			 }
STATUS current

	DESCRIPTION
		"CC detected  leaf node reachable "
	::= { ccNotify 18  }


ccIncompatibleDeviceFirmware 	NOTIFICATION-TYPE
	
	OBJECTS		{ccObjectName,
			 ccObjectInstance,
			 ccUserName,
			 ccLeafNodeIPAddress,
                         ccLeafNodeFirmwareVersion
			 }
STATUS current

	DESCRIPTION
		"CC detected  device with incompatible firmware "
	::= { ccNotify 19  }


ccDeviceUpgrade 	NOTIFICATION-TYPE
	
	OBJECTS		{ccObjectName,
			 ccObjectInstance,
			 ccUserName,
			 ccLeafNodeIPAddress,
                         ccLeafNodeFirmwareVersion,
                         ccImageVersionStatus
			 }
STATUS current

	DESCRIPTION
		"CC has upgraded the firmware on a device "
	::= { ccNotify 20  }


-- CC 3.0 Traps

ccEnterMaintenanceMode 	NOTIFICATION-TYPE
	
	OBJECTS		{ccObjectName,
			 ccObjectInstance,
			 ccUserName
			 }
STATUS current

	DESCRIPTION
		"CC entered maintenance mode "
	::= { ccNotify 21  }


ccExitMaintenanceMode 	NOTIFICATION-TYPE
	
	OBJECTS		{ccObjectName,
			 ccObjectInstance,
			 ccUserName
			 }
STATUS current

	DESCRIPTION
		"CC exited maintenance mode "
	::= { ccNotify 22  }


ccUserLockedOut 	NOTIFICATION-TYPE
	
	OBJECTS		{ccObjectName,
			 ccObjectInstance,
			 ccUserName
			 }
STATUS current

	DESCRIPTION
		"CC user has been locked out "
	::= { ccNotify 23  }


ccDeviceAddedAfterCCNOCNotification 	NOTIFICATION-TYPE
	
	OBJECTS		{ccObjectName,
			 ccObjectInstance,
			 ccDeviceName,
			 ccLeafNodeIPAddress
			 }
STATUS current

	DESCRIPTION
		"CC has added a Generic Device after receiving a notification from CC-NOCupgraded the firmware on a device "
	::= { ccNotify 24  }

ccScheduledTaskExecutionFailure 	NOTIFICATION-TYPE
	
	OBJECTS		{ccObjectName,
			 ccObjectInstance,
			 ccScheduledTaskDescription,
			 ccScheduledTaskFailureReason
			 }
STATUS current

	DESCRIPTION
		"The reason why the execution of a scheduled task failed. "
	::= { ccNotify 25  }

ccDiagnosticConsoleLogin 	NOTIFICATION-TYPE
	
	OBJECTS		{ccObjectName,
			 ccObjectInstance,
			 ccUserName,
                         ccDiagnosticConsoleMAX-ACCESSLevel
			 }
STATUS current

	DESCRIPTION
		" User has logged into the CC Diagnostic Console "
	::= { ccNotify 26  }


ccDiagnosticConsoleLogout 	NOTIFICATION-TYPE
	
	OBJECTS		{ccObjectName,
			 ccObjectInstance,
			 ccUserName,
                         ccDiagnosticConsoleMAX-ACCESSLevel
			 }
STATUS current

	DESCRIPTION
		" User has logged out of the CC Diagnostic Console "
	::= { ccNotify 27  }



ccNOCAvailable 	NOTIFICATION-TYPE
	
	OBJECTS		{ccObjectName,
			 ccObjectInstance,
                         ccLeafNodeIPAddress
			 }
STATUS current

	DESCRIPTION
		" CC has detected that CC-NOC is available "
	::= { ccNotify 28  }


ccNOCUnavailable 	NOTIFICATION-TYPE
	
	OBJECTS		{ccObjectName,
			 ccObjectInstance,
                         ccLeafNodeIPAddress
			 }
STATUS current

	DESCRIPTION
		" CC has detected that CC-NOC is unavailable "
	::= { ccNotify 29  }


-- CC 3.1 Traps

ccUserGroupAdded		NOTIFICATION-TYPE
		OBJECTS	{ccObjectName,
			 ccObjectInstance,
			 ccUserGroupName,
			 ccUserWhoAdded

			 }
	STATUS current

	DESCRIPTION
		"CC-SG  - A new user group has been added "
	::= { ccNotify 30 }


ccUserGroupDeleted		 NOTIFICATION-TYPE
		OBJECTS	{ccObjectName,
			 ccObjectInstance,
			 ccUserGroupName,
			 ccUserWhoDeleted
			 }
	STATUS current

	DESCRIPTION
		"CC-SG - A user group has been deleted "
	::= { ccNotify 31 }


ccUserGroupModified  		NOTIFICATION-TYPE

		OBJECTS	{ccObjectName,
			 ccObjectInstance,
			 ccUserGroupName,
			 ccUserWhoModified
			 }
	STATUS current

	DESCRIPTION
		"CC-SG - A user group has been modified "
	::= { ccNotify 32 }


ccSuperuserNameChanged	NOTIFICATION-TYPE
		OBJECTS	{ccObjectName,
			 ccObjectInstance,
			 ccUserWhoModified
			 }
	STATUS current

	DESCRIPTION
		"CC-SG Superuser name has changed "
	::= { ccNotify 33 }

ccSuperuserPasswordChanged	NOTIFICATION-TYPE
		OBJECTS	{ccObjectName,
			 ccObjectInstance,
			 ccUserWhoModified
			 }
	STATUS current

	DESCRIPTION
		"CC-SG Superuser password has changed "
	::= { ccNotify 34 }

ccLoginBannerChanged	NOTIFICATION-TYPE
		OBJECTS	{ccObjectName,
			 ccObjectInstance,
			 ccUserWhoModified,
                         ccBannerChanges
			 }
	STATUS current

	DESCRIPTION
		"CC-SG Login Banner has changed "
	::= { ccNotify 35 }


ccMOTDChanged	NOTIFICATION-TYPE
		OBJECTS	{ccObjectName,
			 ccObjectInstance,
			 ccUserWhoModified,
                         ccMOTDChanges
			 }
	STATUS current

	DESCRIPTION
		"CC-SG Messsage of the Day (MOTD) has changed "
	::= { ccNotify 36 }


-- CC 4.0 Traps


ccDominionPXReplaced	NOTIFICATION-TYPE
		OBJECTS	{ccObjectName,
			 ccObjectInstance,
			 ccOldNumberOfOutlets,
			 ccNewNumberOfOutlets
			 }
	STATUS current

	DESCRIPTION
		"CC-SG - A Dominion PX has been replaced "
	::= { ccNotify 37 }


ccSystemMonitorNotification	NOTIFICATION-TYPE
		OBJECTS	{ccObjectName,
			 ccObjectInstance,
			 ccSystemMonitorNotificationLevel,
			 ccSystemMonitorNotificationMessage
			 }
	STATUS current

	DESCRIPTION
		"CC-SG SystemMonitor notification"
	::= { ccNotify 38 }


-- CC 4.1 Traps


ccNeighborhoodActivated	NOTIFICATION-TYPE
		OBJECTS	{ccObjectName,
			 ccObjectInstance
			 }
	STATUS current

	DESCRIPTION
		"CC-SG - Network neighborhood has been activated "
	::= { ccNotify 39 }


ccNeighborhoodUpdated	NOTIFICATION-TYPE
		OBJECTS	{ccObjectName,
			 ccObjectInstance
			 }
	STATUS current

	DESCRIPTION
		"CC-SG - Network neighborhood has been updated "
	::= { ccNotify 40 }


ccDominionPXFirmwareChanged	NOTIFICATION-TYPE
		OBJECTS	{
			 ccObjectName,
			 ccObjectInstance,
			 ccDominionPXFirmwareVersion
			 }
	STATUS current

	DESCRIPTION
		"CC-SG - A Dominion PX firmware version has been changed "
	::= { ccNotify 41 }


ccClusterFailover	NOTIFICATION-TYPE
		OBJECTS	{
			 ccObjectName,
			 ccObjectInstance,
			 ccClusterPeer
			 }
	STATUS current

	DESCRIPTION
		"CC-SG - The Primary has failed and the Backup is now operational as the new Primary "
	::= { ccNotify 42 }


ccClusterBackupFailed	NOTIFICATION-TYPE
		OBJECTS	{
			 ccObjectName,
			 ccObjectInstance,
			 ccClusterPeer
			 }
	STATUS current

	DESCRIPTION
		"CC-SG - The Backup has failed  "
	::= { ccNotify 43 }


ccClusterWaitingPeerDetected	NOTIFICATION-TYPE
		OBJECTS	{
			 ccObjectName,
			 ccObjectInstance,
			 ccClusterPeer
			 }
	STATUS current

	DESCRIPTION
		"CC-SG - The Primary detected a peer in Waiting mode "
	::= { ccNotify 44 }


ccClusterAction	NOTIFICATION-TYPE
		OBJECTS	{
			 ccObjectName,
			 ccObjectInstance,
			 ccClusterOperation,
			 ccClusterOperationStatus
			 }
	STATUS current

	DESCRIPTION
		"CC-SG - A cluster operation has been executed "
	::= { ccNotify 45 }

-- CC 4.2 Traps

ccCSVFileTransferred	NOTIFICATION-TYPE
		OBJECTS	{
			 ccObjectName,
			 ccObjectInstance,
			 ccUserName,
                         ccFileType,
			 ccTransferOperation
			 }
	STATUS current

	DESCRIPTION
		"CC-SG - CSV File Transferred "
	::= { ccNotify 46 }


-- CC 4.3 Traps

ccPIQUnavailable 	NOTIFICATION-TYPE
	
	OBJECTS		{ccObjectName,
			 ccObjectInstance,
			 ccLeafNodeName,
			 ccLeafNodeIPAddress
			 }
STATUS current

	DESCRIPTION
		"CC-SG has detected that Power IQ is unavailable"
	::= { ccNotify 47}


ccPIQAvailable 	NOTIFICATION-TYPE
	
	OBJECTS		{ccObjectName,
			 ccObjectInstance,
			 ccLeafNodeName,
			 ccLeafNodeIPAddress
			 }
STATUS current

	DESCRIPTION
		"CC-SG has detected that Power IQ is available"
	::= { ccNotify 48  }


-- CC 5.0 Traps

ccLicenseServerUnavailable  NOTIFICATION-TYPE
	OBJECTS		{ccObjectName,
				ccObjectInstance,
			 	ccLicenseServer 
			 	}
	STATUS 		current
	DESCRIPTION
		"CC-SG License Server Unavailable notification"
	::= { ccNotify 49 }

ccLicenseServerFailover  NOTIFICATION-TYPE
	OBJECTS		{ccObjectName,
			 	ccObjectInstance,
			 	ccLicenseServer 
			 	}
	STATUS 		current
	DESCRIPTION
		"CC-SG License Server Fail-Over notification"
	::= { ccNotify 50 }

ccLicenseServerAvailable  NOTIFICATION-TYPE
	OBJECTS		{ccObjectName,
			 	ccObjectInstance,
				ccLicenseServer 
			 	}
	STATUS 		current
	DESCRIPTION
		"CC-SG License Server Available notification"
	::= { ccNotify 51 }

ccLicenseTerminated  NOTIFICATION-TYPE
	OBJECTS		{ccObjectName,
			     ccObjectInstance
			 	}
	STATUS 		current
	DESCRIPTION
		"CC-SG License Terminated notification"
	::= { ccNotify 52 }
	
ccAddLicenseFailure  NOTIFICATION-TYPE
	OBJECTS		{ccObjectName,
			 ccObjectInstance
			 }
	STATUS 		current
	DESCRIPTION
		"Add CC-SG License Failed"
	::= { ccNotify 53 }

ccAddFeatureFailure  NOTIFICATION-TYPE
	OBJECTS		{ccObjectName,
			 ccObjectInstance,
			 ccLicensedFeature
			 }
	STATUS 		current
	DESCRIPTION
		"CC-SG Licensed Feature Check-out Failed"
	::= { ccNotify 54 }

-- CC 5.0.5 Traps

ccLicenseTerminatedWithReason NOTIFICATION-TYPE
	
	OBJECTS		{ccObjectName,
			 ccObjectInstance,
			 ccLicenseTerminatedReason
			 }
	STATUS current
	DESCRIPTION
		"The reason why CC-SG Licenses were terminated. "
	::= { ccNotify 55}

-- CC 6.0 Traps

ccUserPasswordChanged	NOTIFICATION-TYPE
		OBJECTS	{ccObjectName,
			 ccObjectInstance,
			 ccUserName,
			 ccUserWhoModified
			 }
STATUS current

	DESCRIPTION
		"CC user password changed "
	::= { ccNotify 56 }
 


END
