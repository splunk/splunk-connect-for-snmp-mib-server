-- -----------------------------------------------------------------------------
-- MIB NAME : Eltex MES Spanning Tree Multiprocess
-- FILE NAME: eltStpMulti.mib
-- DATE     : 2013/10/25
-- VERSION  : 1.00
-- PURPOSE  : MIB structure for Spanning Tree Multiprocess extension.
-- -----------------------------------------------------------------------------


ELTEX-MES-BRIDGE-STP-MULTIPROCESS-MIB DEFINITIONS ::= BEGIN

    IMPORTS
			MODULE-IDENTITY, OBJECT-TYPE, TimeTicks, Counter32
			    FROM SNMPv2-SMI
			RowStatus,MacAddress,TruthValue
			    FROM SNMPv2-TC
			VlanIdOrNone, PortList
				FROM Q-BRIDGE-MIB
			Counter
				FROM RFC1155-SMI
			BridgeId, Timeout, dot1dBasePort
				FROM BRIDGE-MIB
            InterfaceIndex, ifIndex
            	FROM IF-MIB
			eltMesBridgeExtMIBObjects
				FROM ELTEX-MES-BRIDGE-EXT-MIB;

    eltMesStpMultiProcessMIB MODULE-IDENTITY
        LAST-UPDATED "1310250000Z"
        ORGANIZATION "Eltex Ltd."
        CONTACT-INFO
            "http://www.eltex.nsk.ru"
        DESCRIPTION
            "The MIB module for managing STP multiprocess extension."
        ::= { eltMesBridgeExtMIBObjects 2 }

eltMesDot1dStpMultiProcess   OBJECT IDENTIFIER ::= { eltMesStpMultiProcessMIB 1 }
eltMesDot1sMstpMultiProcess  OBJECT IDENTIFIER ::= { eltMesStpMultiProcessMIB 2 }

eltdot1dStpMultiProcessTable OBJECT-TYPE
    SYNTAX  SEQUENCE OF Eltdot1dStpMultiProcessEntry
    MAX-ACCESS  not-accessible
    STATUS  current
    DESCRIPTION
            "A table that contains per-process Stp specific information
            for the Spanning Tree Protocol."
    ::= { eltMesDot1dStpMultiProcess 1 }

eltdot1dStpMultiProcessEntry OBJECT-TYPE
    SYNTAX  Eltdot1dStpMultiProcessEntry
    MAX-ACCESS  not-accessible
    STATUS  current
    DESCRIPTION
        "A list of information maintained by every instance
         about the multiple Spanning Tree Protocol state for
         that instance."
    INDEX   { eltdot1dStpMultiProcessId }
    ::= { eltdot1dStpMultiProcessTable 1 }

Eltdot1dStpMultiProcessEntry ::= SEQUENCE {
	eltdot1dStpMultiProcessId                       INTEGER,
	eltdot1dStpMultiProcessPriority                 INTEGER,
	eltdot1dStpMultiProcessBridgeMaxAge             Timeout,
	eltdot1dStpMultiProcessBridgeHelloTime          Timeout,
	eltdot1dStpMultiProcessBridgeForwardDelay       Timeout,
	eltdot1dStpMultiProcessVersion                  INTEGER,
	eltdot1dStpMultiProcessTimeSinceTopologyChange  TimeTicks,
	eltdot1dStpMultiProcessTopChanges               Counter,
	eltdot1dStpMultiProcessDesignatedRoot           BridgeId,
	eltdot1dStpMultiProcessRootCost                 INTEGER,
	eltdot1dStpMultiProcessRootPort                 INTEGER,
	eltdot1dStpMultiProcessMaxAge                   Timeout,
	eltdot1dStpMultiProcessHelloTime                Timeout,
	eltdot1dStpMultiProcessHoldTime                 INTEGER,
	eltdot1dStpMultiProcessForwardDelay             Timeout,
	eltdot1dStpMultiProcessRowStatus                RowStatus,
    eltdot1dStpMultiProcessLastTopologyChangePort   INTEGER
}

eltdot1dStpMultiProcessId OBJECT-TYPE
    SYNTAX  INTEGER (1..31)
    MAX-ACCESS  read-only
    STATUS  current
    DESCRIPTION
        "The Process index."
    ::= { eltdot1dStpMultiProcessEntry 1 }

eltdot1dStpMultiProcessPriority OBJECT-TYPE
    SYNTAX  INTEGER (0..65535)
    MAX-ACCESS  read-write
    STATUS  current
    DESCRIPTION
            "The value of the write-able portion of the Bridge
            ID, i.e., the first two octets of the (8 octet
            long) Bridge ID.  The other (last) 6 octets of the
            Bridge ID are given by the value of
            dot1dBaseBridgeAddress."
    REFERENCE
            "IEEE 802.1D-1990: Section 4.5.3.7"
    ::= { eltdot1dStpMultiProcessEntry 2 }

eltdot1dStpMultiProcessBridgeMaxAge OBJECT-TYPE
    SYNTAX  Timeout (600..4000)
    MAX-ACCESS  read-write
    STATUS  current
    DESCRIPTION
            "The value that all bridges use for MaxAge when
            this bridge is acting as the root.  Note that
            802.1D-1990 specifies that the range for this
            parameter is related to the value of
            eltdot1dStpMultiProcessBridgeHelloTime. The granularity of this
            timer is specified by 802.1D-1990 to be 1 second.
            An agent may return a badValue error if a set is
            attempted to a value which is not a whole number
            of seconds."
    REFERENCE
            "IEEE 802.1D-1990: Section 4.5.3.8"
    ::= { eltdot1dStpMultiProcessEntry 3 }

eltdot1dStpMultiProcessBridgeHelloTime OBJECT-TYPE
    SYNTAX  Timeout (100..1000)
    MAX-ACCESS  read-write
    STATUS  current
    DESCRIPTION
            "The value that all bridges use for HelloTime when
            this bridge is acting as the root.  The
            granularity of this timer is specified by 802.1D-
            1990 to be 1 second.  An agent may return a
            badValue error if a set is attempted to a value
            which is not a whole number of seconds."
    REFERENCE
            "IEEE 802.1D-1990: Section 4.5.3.9"
    ::= { eltdot1dStpMultiProcessEntry 4 }

eltdot1dStpMultiProcessBridgeForwardDelay OBJECT-TYPE
    SYNTAX  Timeout (400..3000)
    MAX-ACCESS  read-write
    STATUS  current
    DESCRIPTION
            "The value that all bridges use for ForwardDelay
            when this bridge is acting as the root.  Note that
            802.1D-1990 specifies that the range for this
            parameter is related to the value of
            eltdot1dStpMultiProcessBridgeMaxAge.  The granularity of this
            timer is specified by 802.1D-1990 to be 1 second.
            An agent may return a badValue error if a set is
            attempted to a value which is not a whole number
            of seconds."
    REFERENCE
            "IEEE 802.1D-1990: Section 4.5.3.10"
    ::= { eltdot1dStpMultiProcessEntry 5 }

eltdot1dStpMultiProcessVersion OBJECT-TYPE
    SYNTAX      INTEGER {
                    stpCompatible(0),
                    rstp(2),
                    mstp(3)
                }
    MAX-ACCESS  read-write
    STATUS      current
    DESCRIPTION
        "The version of Spanning Tree Protocol the bridge is
         currently running.  The value 'stpCompatible(0)'
         indicates the Spanning Tree Protocol specified in
         IEEE 802.1D and 'rstp(2)' indicates the Rapid Spanning
         Tree Protocol specified in IEEE 802.1w.  New value may
         be defined as future versions of the protocol become
         available."
    REFERENCE
        "IEEE 802.1w clause 14.8.1, 17.12, 17.16.1"
    DEFVAL      { rstp }
    ::= { eltdot1dStpMultiProcessEntry 6 }

eltdot1dStpMultiProcessTimeSinceTopologyChange OBJECT-TYPE
    SYNTAX  TimeTicks
    MAX-ACCESS  read-only
    STATUS  current
    DESCRIPTION
            "The time (in hundredths of a second) since the
            last time a topology change was detected by the
            bridge entity."
    REFERENCE
            "IEEE 802.1D-1990: Section 6.8.1.1.3"
    ::= { eltdot1dStpMultiProcessEntry 7 }

eltdot1dStpMultiProcessTopChanges OBJECT-TYPE
    SYNTAX  Counter
    MAX-ACCESS  read-only
    STATUS  current
    DESCRIPTION
            "The total number of topology changes detected by
            this bridge since the management entity was last
            reset or initialized."
    REFERENCE
            "IEEE 802.1D-1990: Section 6.8.1.1.3"
    ::= { eltdot1dStpMultiProcessEntry 8 }

eltdot1dStpMultiProcessDesignatedRoot OBJECT-TYPE
    SYNTAX  BridgeId
    MAX-ACCESS  read-only
    STATUS  current
    DESCRIPTION
            "The bridge identifier of the root of the spanning
            tree as determined by the Spanning Tree Protocol
            as executed by this node.  This value is used as
            the Root Identifier parameter in all Configuration
            Bridge PDUs originated by this node."
    REFERENCE
            "IEEE 802.1D-1990: Section 4.5.3.1"
    ::= { eltdot1dStpMultiProcessEntry 9 }

eltdot1dStpMultiProcessRootCost OBJECT-TYPE
    SYNTAX  INTEGER
    MAX-ACCESS  read-only
    STATUS  current
    DESCRIPTION
            "The cost of the path to the root as seen from
            this bridge."
    REFERENCE
            "IEEE 802.1D-1990: Section 4.5.3.2"
    ::= { eltdot1dStpMultiProcessEntry 10 }

eltdot1dStpMultiProcessRootPort OBJECT-TYPE
    SYNTAX  INTEGER
    MAX-ACCESS  read-only
    STATUS  current
    DESCRIPTION
            "The port number of the port which offers the
            lowest cost path from this bridge to the root
            bridge."
    REFERENCE
            "IEEE 802.1D-1990: Section 4.5.3.3"
    ::= { eltdot1dStpMultiProcessEntry 11 }

eltdot1dStpMultiProcessMaxAge OBJECT-TYPE
    SYNTAX  Timeout
    MAX-ACCESS  read-only
    STATUS  current
    DESCRIPTION
            "The maximum age of Spanning Tree Protocol
            information learned from the network on any port
            before it is discarded, in units of hundredths of
            a second.  This is the actual value that this
            bridge is currently using."
    REFERENCE
            "IEEE 802.1D-1990: Section 4.5.3.4"
    ::= { eltdot1dStpMultiProcessEntry 12 }

eltdot1dStpMultiProcessHelloTime OBJECT-TYPE
    SYNTAX  Timeout
    MAX-ACCESS  read-only
    STATUS  current
    DESCRIPTION
            "The amount of time between the transmission of
            Configuration bridge PDUs by this node on any port
            when it is the root of the spanning tree or trying
            to become so, in units of hundredths of a second.
            This is the actual value that this bridge is
            currently using."
    REFERENCE
            "IEEE 802.1D-1990: Section 4.5.3.5"
    ::= { eltdot1dStpMultiProcessEntry 13 }

eltdot1dStpMultiProcessHoldTime OBJECT-TYPE
    SYNTAX  INTEGER
    MAX-ACCESS  read-only
    STATUS  current
    DESCRIPTION
            "This time value determines the interval length
            during which no more than two Configuration bridge
            PDUs shall be transmitted by this node, in units
            of hundredths of a second."
    REFERENCE
            "IEEE 802.1D-1990: Section 4.5.3.14"
    ::= { eltdot1dStpMultiProcessEntry 14 }

eltdot1dStpMultiProcessForwardDelay OBJECT-TYPE
    SYNTAX  Timeout
    MAX-ACCESS  read-only
    STATUS  current
    DESCRIPTION
            "This time value, measured in units of hundredths
            of a second, controls how fast a port changes its
            spanning state when moving towards the Forwarding
            state.  The value determines how long the port
            stays in each of the Listening and Learning
            states, which precede the Forwarding state.  This
            value is also used, when a topology change has
            been detected and is underway, to age all dynamic
            entries in the Forwarding Database.  [Note that
            this value is the one that this bridge is
            currently using, in contrast to
            eltdot1dStpMultiProcessBridgeForwardDelay which is the value that
            this bridge and all others would start using
            if/when this bridge were to become the root.]"
    REFERENCE
            "IEEE 802.1D-1990: Section 4.5.3.6"
    ::= { eltdot1dStpMultiProcessEntry 15 }

eltdot1dStpMultiProcessRowStatus OBJECT-TYPE
    SYNTAX      RowStatus
    MAX-ACCESS  read-only
    STATUS      current
    DESCRIPTION
        "Process entry row status."
    ::= { eltdot1dStpMultiProcessEntry 16 }

eltdot1dStpMultiProcessLastTopologyChangePort OBJECT-TYPE
	SYNTAX  INTEGER
    MAX-ACCESS  read-only
	STATUS  current
	DESCRIPTION
    		"This value contains port's ifIndex from
            which the request about the last change of topology came.
            If value is 0 - topology wasn't changed yet."
    ::= { eltdot1dStpMultiProcessEntry 17 }

eltdot1dStpMultiProcessPortTable OBJECT-TYPE
    SYNTAX  SEQUENCE OF Eltdot1dStpMultiProcessPortEntry
    MAX-ACCESS  not-accessible
    STATUS  current
    DESCRIPTION
        "A table that contains extended pair port specific information."
    ::= { eltMesDot1dStpMultiProcess 2 }

eltdot1dStpMultiProcessPortEntry OBJECT-TYPE
    SYNTAX  Eltdot1dStpMultiProcessPortEntry
    MAX-ACCESS  not-accessible
    STATUS  current
    DESCRIPTION
        "A list of information maintained by every port
         about the Spanning Tree Protocol state for that port."
    INDEX   { eltdot1dStpMultiProcessPortPort }
    ::= { eltdot1dStpMultiProcessPortTable 1 }

Eltdot1dStpMultiProcessPortEntry ::= SEQUENCE {
	eltdot1dStpMultiProcessPortPort               INTEGER,
    eltdot1dStpMultiProcessPortProcessId          INTEGER,
	eltdot1dStpMultiProcessPortSharedProcessId1   INTEGER,
    eltdot1dStpMultiProcessPortSharedProcessId2   INTEGER,
    eltdot1dStpMultiProcessPortSharedProcessId3   INTEGER,
    eltdot1dStpMultiProcessPortSharedProcessId4   INTEGER,
    eltdot1dStpMultiProcessPortSharedProcessId5   INTEGER,
    eltdot1dStpMultiProcessPortSharedProcessId6   INTEGER,
    eltdot1dStpMultiProcessPortSharedProcessId7   INTEGER,
    eltdot1dStpMultiProcessPortSharedProcessId8   INTEGER,
    eltdot1dStpMultiProcessPortSharedProcessId9   INTEGER,
    eltdot1dStpMultiProcessPortSharedProcessId10  INTEGER
}

eltdot1dStpMultiProcessPortPort OBJECT-TYPE
    SYNTAX  INTEGER (1..4096)
    MAX-ACCESS  read-only
    STATUS  current
    DESCRIPTION
        "The port number of the port for which this entry
         contains Spanning Tree Protocol management
         information."
    REFERENCE
         ""
    ::= { eltdot1dStpMultiProcessPortEntry 1 }

eltdot1dStpMultiProcessPortProcessId OBJECT-TYPE
    SYNTAX  INTEGER (0..31)
    MAX-ACCESS  read-write
    STATUS  current
    DESCRIPTION
        "Native process the port belongs to."
    REFERENCE
         ""
    ::= { eltdot1dStpMultiProcessPortEntry 2 }

eltdot1dStpMultiProcessPortSharedProcessId1 OBJECT-TYPE
    SYNTAX  INTEGER (0..31)
    MAX-ACCESS  read-write
    STATUS  current
    DESCRIPTION
        "Shared process the port belongs to."
    REFERENCE
         ""
    ::= { eltdot1dStpMultiProcessPortEntry 3 }

eltdot1dStpMultiProcessPortSharedProcessId2 OBJECT-TYPE
    SYNTAX  INTEGER (0..31)
    MAX-ACCESS  read-write
    STATUS  current
    DESCRIPTION
        "Shared process the port belongs to."
    REFERENCE
         ""
    ::= { eltdot1dStpMultiProcessPortEntry 4 }

eltdot1dStpMultiProcessPortSharedProcessId3 OBJECT-TYPE
    SYNTAX  INTEGER (0..31)
    MAX-ACCESS  read-write
    STATUS  current
    DESCRIPTION
        "Shared process the port belongs to."
    REFERENCE
         ""
    ::= { eltdot1dStpMultiProcessPortEntry 5 }

eltdot1dStpMultiProcessPortSharedProcessId4 OBJECT-TYPE
    SYNTAX  INTEGER (0..31)
    MAX-ACCESS  read-write
    STATUS  current
    DESCRIPTION
        "Shared process the port belongs to."
    REFERENCE
         ""
    ::= { eltdot1dStpMultiProcessPortEntry 6 }

eltdot1dStpMultiProcessPortSharedProcessId5 OBJECT-TYPE
    SYNTAX  INTEGER (0..31)
    MAX-ACCESS  read-write
    STATUS  current
    DESCRIPTION
        "Shared process the port belongs to."
    REFERENCE
         ""
    ::= { eltdot1dStpMultiProcessPortEntry 7 }

eltdot1dStpMultiProcessPortSharedProcessId6 OBJECT-TYPE
    SYNTAX  INTEGER (0..31)
    MAX-ACCESS  read-write
    STATUS  current
    DESCRIPTION
        "Shared process the port belongs to."
    REFERENCE
         ""
    ::= { eltdot1dStpMultiProcessPortEntry 8 }

eltdot1dStpMultiProcessPortSharedProcessId7 OBJECT-TYPE
    SYNTAX  INTEGER (0..31)
    MAX-ACCESS  read-write
    STATUS  current
    DESCRIPTION
        "Shared process the port belongs to."
    REFERENCE
         ""
    ::= { eltdot1dStpMultiProcessPortEntry 9 }

eltdot1dStpMultiProcessPortSharedProcessId8 OBJECT-TYPE
    SYNTAX  INTEGER (0..31)
    MAX-ACCESS  read-write
    STATUS  current
    DESCRIPTION
        "Shared process the port belongs to."
    REFERENCE
         ""
    ::= { eltdot1dStpMultiProcessPortEntry 10 }

eltdot1dStpMultiProcessPortSharedProcessId9 OBJECT-TYPE
    SYNTAX  INTEGER (0..31)
    MAX-ACCESS  read-write
    STATUS  current
    DESCRIPTION
        "Shared process the port belongs to."
    REFERENCE
         ""
    ::= { eltdot1dStpMultiProcessPortEntry 11 }

eltdot1dStpMultiProcessPortSharedProcessId10 OBJECT-TYPE
    SYNTAX  INTEGER (0..31)
    MAX-ACCESS  read-write
    STATUS  current
    DESCRIPTION
        "Shared process the port belongs to."
    REFERENCE
         ""
    ::= { eltdot1dStpMultiProcessPortEntry 12 }


eltdot1dStpMultiProcessPortListTable OBJECT-TYPE
    SYNTAX  SEQUENCE OF Eltdot1dStpMultiProcessPortListEntry
    MAX-ACCESS  not-accessible
    STATUS  current
    DESCRIPTION
            "A table that contains per-process port lists."
    ::= { eltMesDot1dStpMultiProcess 3 }

eltdot1dStpMultiProcessPortListEntry OBJECT-TYPE
    SYNTAX  Eltdot1dStpMultiProcessPortListEntry
    MAX-ACCESS  not-accessible
    STATUS  current
    DESCRIPTION
        "Entry."
    INDEX   { eltdot1dStpMultiProcessPortListProcessId }
    ::= { eltdot1dStpMultiProcessPortListTable 1 }

Eltdot1dStpMultiProcessPortListEntry ::= SEQUENCE {
	eltdot1dStpMultiProcessPortListProcessId  INTEGER,
	eltdot1dStpMultiProcessPortList           PortList
}

eltdot1dStpMultiProcessPortListProcessId OBJECT-TYPE
    SYNTAX  INTEGER (0..31)
    MAX-ACCESS  read-only
    STATUS  current
    DESCRIPTION
        "The Process index."
    ::= { eltdot1dStpMultiProcessPortListEntry 1 }

eltdot1dStpMultiProcessPortList OBJECT-TYPE
    SYNTAX  PortList
    MAX-ACCESS  read-only
    STATUS  current
    DESCRIPTION
        "The list of ports that belong to this process."
    ::= { eltdot1dStpMultiProcessPortListEntry 2 }



eltdot1sMstpMultiProcessInstanceTable OBJECT-TYPE
    SYNTAX  SEQUENCE OF Eltdot1sMstpMultiProcessInstanceEntry
    MAX-ACCESS  not-accessible
    STATUS  current
    DESCRIPTION
            "A table that contains per-process Mstp instance specific information
            for the Multiple Spanning Tree Protocol."
    ::= { eltMesDot1sMstpMultiProcess 1 }

eltdot1sMstpMultiProcessInstanceEntry OBJECT-TYPE
    SYNTAX  Eltdot1sMstpMultiProcessInstanceEntry
    MAX-ACCESS  not-accessible
    STATUS  current
    DESCRIPTION
        "A list of information maintained by every instance
         about the multiple Spanning Tree Protocol state for
         that instance."
    INDEX   { eltdot1sMstpMultiProcessInstanceProcessId, eltdot1sMstpMultiProcessInstanceId }
    ::= { eltdot1sMstpMultiProcessInstanceTable 1 }

Eltdot1sMstpMultiProcessInstanceEntry ::= SEQUENCE {
	eltdot1sMstpMultiProcessInstanceProcessId                 INTEGER,
    eltdot1sMstpMultiProcessInstanceId                        INTEGER,
    eltdot1sMstpMultiProcessInstanceEnable                    TruthValue,
    eltdot1sMstpMultiProcessInstanceTimeSinceTopologyChange   TimeTicks,
    eltdot1sMstpMultiProcessInstanceTopChanges                Counter,
    eltdot1sMstpMultiProcessInstanceDesignatedRoot            BridgeId,
    eltdot1sMstpMultiProcessInstanceRootCost                  INTEGER,
    eltdot1sMstpMultiProcessInstanceRootPort                  INTEGER,
    eltdot1sMstpMultiProcessInstanceMaxAge                    Timeout,
    eltdot1sMstpMultiProcessInstanceHelloTime                 Timeout,
    eltdot1sMstpMultiProcessInstanceHoldTime                  INTEGER,
    eltdot1sMstpMultiProcessInstanceForwardDelay              Timeout,
    eltdot1sMstpMultiProcessInstancePriority                  INTEGER,
    eltdot1sMstpMultiProcessInstanceRemainingHopes            INTEGER,
    eltdot1sMstpMultiProcessInstanceLastTopologyChangePort    INTEGER
}

eltdot1sMstpMultiProcessInstanceProcessId OBJECT-TYPE
    SYNTAX  INTEGER (1..31)
    MAX-ACCESS  read-only
    STATUS  current
    DESCRIPTION
        "The Process index."
    ::= { eltdot1sMstpMultiProcessInstanceEntry 1 }

eltdot1sMstpMultiProcessInstanceId OBJECT-TYPE
    SYNTAX  INTEGER
    MAX-ACCESS  read-only
    STATUS  current
    DESCRIPTION
        "The Instance index."
    ::= { eltdot1sMstpMultiProcessInstanceEntry 2 }

eltdot1sMstpMultiProcessInstanceEnable OBJECT-TYPE
    SYNTAX  TruthValue
    MAX-ACCESS  read-only
    STATUS  current
    DESCRIPTION
        "Specifies whether this Instance is STP enable or disable"
    REFERENCE
        " ??  "
    ::= { eltdot1sMstpMultiProcessInstanceEntry 3 }

eltdot1sMstpMultiProcessInstanceTimeSinceTopologyChange OBJECT-TYPE
    SYNTAX  TimeTicks
    MAX-ACCESS  read-only
    STATUS  current
    DESCRIPTION
        "The time (in hundredths of a second) since the
         last time a topology change was detected by the
         Mstp Instance ."
    REFERENCE
        "IEEE 802.1D-1990: Section 6.8.1.1.3"
    ::= { eltdot1sMstpMultiProcessInstanceEntry 4 }

eltdot1sMstpMultiProcessInstanceTopChanges OBJECT-TYPE
    SYNTAX  Counter
    MAX-ACCESS  read-only
    STATUS  current
    DESCRIPTION
        "The total number of topology changes detected by
         this Instance since the management entity was last
         reset or initialized."
    REFERENCE
        "IEEE 802.1D-1990: Section 6.8.1.1.3"
    ::= { eltdot1sMstpMultiProcessInstanceEntry 5 }

eltdot1sMstpMultiProcessInstanceDesignatedRoot OBJECT-TYPE
    SYNTAX  BridgeId
    MAX-ACCESS  read-only
    STATUS  current
    DESCRIPTION
        "The bridge identifier of the root of the spanning
         tree as determined by the Muliple Spanning Tree Protocol
         as executed by this node.  This value is used as
         the Root Identifier parameter in all Configuration
         Bridge PDUs originated by this node."
    REFERENCE
        "IEEE 802.1D-1990: Section 4.5.3.1"
    ::= { eltdot1sMstpMultiProcessInstanceEntry 6 }

eltdot1sMstpMultiProcessInstanceRootCost OBJECT-TYPE
    SYNTAX  INTEGER
    MAX-ACCESS  read-only
    STATUS  current
    DESCRIPTION
        "The cost of the path to the root as seen from
         this bridge."
    REFERENCE
        "IEEE 802.1D-1990: Section 4.5.3.2"
    ::= { eltdot1sMstpMultiProcessInstanceEntry 7 }

eltdot1sMstpMultiProcessInstanceRootPort OBJECT-TYPE
    SYNTAX  INTEGER
    MAX-ACCESS  read-only
    STATUS  current
    DESCRIPTION
        "The port number of the port which offers the
         lowest cost path from this bridge to the root
         bridge."
    REFERENCE
        "IEEE 802.1D-1990: Section 4.5.3.3"
    ::= { eltdot1sMstpMultiProcessInstanceEntry 8 }

eltdot1sMstpMultiProcessInstanceMaxAge OBJECT-TYPE
    SYNTAX  Timeout
    MAX-ACCESS  read-only
    STATUS  current
    DESCRIPTION
        "The maximum age of Spanning Tree Protocol
         information learned from the network on any port
         before it is discarded, in units of hundredths of
         a second.  This is the actual value that this
         bridge is currently using."
    REFERENCE
        "IEEE 802.1D-1990: Section 4.5.3.4"
    ::= { eltdot1sMstpMultiProcessInstanceEntry 9 }

eltdot1sMstpMultiProcessInstanceHelloTime OBJECT-TYPE
    SYNTAX  Timeout
    MAX-ACCESS  read-only
    STATUS  current
    DESCRIPTION
        "The amount of time between the transmission of
         Configuration bridge PDUs by this node on any port
         when it is the root of the spanning tree or trying
         to become so, in units of hundredths of a second.
         This is the actual value that this bridge is
         currently using."
    REFERENCE
        "IEEE 802.1D-1990: Section 4.5.3.5"
    ::= { eltdot1sMstpMultiProcessInstanceEntry 10 }

eltdot1sMstpMultiProcessInstanceHoldTime OBJECT-TYPE
    SYNTAX  INTEGER
    MAX-ACCESS  read-only
    STATUS  current
    DESCRIPTION
        "This time value determines the interval length
         during which no more than two Configuration bridge
         PDUs shall be transmitted by this node, in units
         of hundredths of a second."
    REFERENCE
        "IEEE 802.1D-1990: Section 4.5.3.14"
    ::= { eltdot1sMstpMultiProcessInstanceEntry 11 }

eltdot1sMstpMultiProcessInstanceForwardDelay OBJECT-TYPE
    SYNTAX  Timeout
    MAX-ACCESS  read-only
    STATUS  current
    DESCRIPTION
        "This time value, measured in units of hundredths
         of a second, controls how fast a port changes its
         spanning state when moving towards the Forwarding
         state.  The value determines how long the port
         stays in each of the Listening and Learning
         states, which precede the Forwarding state.  This
         value is also used, when a topology change has
         been detected and is underway, to age all dynamic
         entries in the Forwarding Database.  [Note that
         this value is the one that this bridge is
         currently using, in contrast to
         eltdot1dStpMultiProcessBridgeForwardDelay which is the value that
         this bridge and all others would start using
         if/when this bridge were to become the root.]"
    REFERENCE
        "IEEE 802.1D-1990: Section 4.5.3.6"
    ::= { eltdot1sMstpMultiProcessInstanceEntry 12 }

eltdot1sMstpMultiProcessInstancePriority OBJECT-TYPE
    SYNTAX  INTEGER (0..61440)
    MAX-ACCESS  read-write
    STATUS  current
    DESCRIPTION
            "The value of the write-able portion of the Bridge
            ID, i.e., the first four bits of the first octet
            of the (8 octet long) Bridge ID.The value is a product
            of 4096. The next 12 bit are the msti id .
            The other (last) 6 octets of the Bridge ID are given
            by the value of dot1dBaseBridgeAddress."
    REFERENCE
            "IEEE 802.1S-2001: Section 13.24.2"
    ::= {eltdot1sMstpMultiProcessInstanceEntry 13 }

eltdot1sMstpMultiProcessInstanceRemainingHopes OBJECT-TYPE
    SYNTAX  INTEGER
    MAX-ACCESS  read-only
    STATUS  current
    DESCRIPTION
        "This count value determines the amount of hopes
         the information transmited by this bridge on this
         instance can travel."
    REFERENCE
        "IEEE 802.1D-1990: Section 4.5.3.14"
    ::= { eltdot1sMstpMultiProcessInstanceEntry 14 }

eltdot1sMstpMultiProcessInstanceLastTopologyChangePort OBJECT-TYPE
	SYNTAX  INTEGER
    MAX-ACCESS  read-only
	STATUS  current
	DESCRIPTION
    		"This value contains port's ifIndex from
            which the request about the last change of topology came.
            If value is 0 - topology wasn't changed yet."
    ::= { eltdot1sMstpMultiProcessInstanceEntry 15}

eltdot1sMstpMultiProcessTable OBJECT-TYPE
    SYNTAX  SEQUENCE OF Eltdot1sMstpMultiProcessEntry
    MAX-ACCESS  not-accessible
    STATUS  current
    DESCRIPTION
            "A table that contains per-process information
            for the Multiple Spanning Tree Protocol."
    ::= { eltMesDot1sMstpMultiProcess 2 }

eltdot1sMstpMultiProcessEntry OBJECT-TYPE
    SYNTAX  Eltdot1sMstpMultiProcessEntry
    MAX-ACCESS  not-accessible
    STATUS  current
    DESCRIPTION
        "A list of information maintained by every process
         about the multiple Spanning Tree Protocol state for
         that process."
    INDEX   { eltdot1sMstpMultiProcessId }
    ::= { eltdot1sMstpMultiProcessTable 1 }

Eltdot1sMstpMultiProcessEntry ::= SEQUENCE {
	eltdot1sMstpMultiProcessId                         INTEGER,
	eltdot1sMstpMultiProcessMaxHopes                   INTEGER,
	eltdot1sMstpMultiProcessDesignatedMaxHopes         INTEGER,
	eltdot1sMstpMultiProcessRegionalRoot               BridgeId,
	eltdot1sMstpMultiProcessRegionalRootCost           INTEGER,
	eltdot1sMstpMultiProcessRemainingHops              INTEGER
}

eltdot1sMstpMultiProcessId OBJECT-TYPE
    SYNTAX  INTEGER (1..31)
    MAX-ACCESS  read-only
    STATUS  current
    DESCRIPTION
        "The Process index."
    ::= { eltdot1sMstpMultiProcessEntry 1 }

eltdot1sMstpMultiProcessMaxHopes OBJECT-TYPE
    SYNTAX  INTEGER (1..40)
    MAX-ACCESS  read-write
    STATUS  current
    DESCRIPTION
        "Max number of hopes that an MST BPDU will travel inside a region."
    DEFVAL { 20 }
    ::= { eltdot1sMstpMultiProcessEntry 2 }

eltdot1sMstpMultiProcessDesignatedMaxHopes OBJECT-TYPE
    SYNTAX  INTEGER (1..40)
    MAX-ACCESS  read-only
    STATUS  current
    DESCRIPTION
        "Max number of hopes that an MST BPDU will travel inside a region."
    ::= { eltdot1sMstpMultiProcessEntry 3 }

eltdot1sMstpMultiProcessRegionalRoot OBJECT-TYPE
    SYNTAX  BridgeId
    MAX-ACCESS  read-only
    STATUS  current
    DESCRIPTION
            "CIST Regional Root Identifier (13.16.4).
            The Bridge Identifier of the current CIST Regional Root."
    REFERENCE
            "IEEE 802.1S-2002: Section 13.16.4"
    ::= { eltdot1sMstpMultiProcessEntry 4 }

eltdot1sMstpMultiProcessRegionalRootCost OBJECT-TYPE
    SYNTAX  INTEGER
    MAX-ACCESS  read-only
    STATUS  current
    DESCRIPTION
            "The CIST path cost from the transmitting Bridge to the
            CIST Regional Root."
    REFERENCE
            "IEEE 802.1S-2002: Section 12.8.1.1.3"
    ::= { eltdot1sMstpMultiProcessEntry 5 }

eltdot1sMstpMultiProcessRemainingHops OBJECT-TYPE
    SYNTAX  INTEGER
    MAX-ACCESS  read-only
    STATUS  current
    DESCRIPTION
        "This count value determines the amount of hops
         the information transmitted by this bridge can travel."
    ::= { eltdot1sMstpMultiProcessEntry 6 }



END
