ELTEX-MES-SYSLOG-MIB DEFINITIONS ::= BEGIN

-- Title:      ELTEX MES SYSLOG Private MIB
-- Version:    2.0
-- Date:       11 May 2016
--
-- 03-Aug-2015 Added eltMesSyslogEvents
-- 11-May-2016 Added eltSyslogUserCmdEnable

IMPORTS
    eltMes                                  FROM ELTEX-MES
    EltCPURateLimiterTrafficType            FROM ELTEX-MES-SWITCH-RATE-LIMITER-MIB
    OBJECT-TYPE, IpAddress, Unsigned32,Counter32,
    MODULE-IDENTITY                         FROM SNMPv2-SMI
    DisplayString, TEXTUAL-CONVENTION,
    TruthValue, RowStatus                   FROM SNMPv2-TC;

eltMesSyslog MODULE-IDENTITY
          LAST-UPDATED "201605110000Z"
          ORGANIZATION "Eltex Ltd."
          CONTACT-INFO
                  "eltex.nsk.ru"
          DESCRIPTION
                  "The private MIB module definition for SYSLOG services in Eltex devices."
          ::= { eltMes 10 }

eltSyslogCPURateLimiterTable OBJECT-TYPE
    SYNTAX          SEQUENCE OF EltSyslogCPURateLimiterEntry
    MAX-ACCESS      not-accessible
    STATUS          current
    DESCRIPTION        "Enable/disable logging per CPU rate limitter."
    ::= { eltMesSyslog 1 }

eltSyslogCPURateLimiterEntry OBJECT-TYPE
    SYNTAX          EltSyslogCPURateLimiterEntry
    MAX-ACCESS      not-accessible
    STATUS          current
    DESCRIPTION        "An entry containing enable/disable logging settings per CPU rate limitter."
    INDEX           { eltSyslogCPURateLimiterIndex }
    ::= { eltSyslogCPURateLimiterTable 1 }

EltSyslogCPURateLimiterEntry ::= SEQUENCE {
        eltSyslogCPURateLimiterIndex       EltCPURateLimiterTrafficType,
        eltSyslogCPURateLimiterEnabled     TruthValue
}

eltSyslogCPURateLimiterIndex OBJECT-TYPE
    SYNTAX          EltCPURateLimiterTrafficType
    MAX-ACCESS      read-only
    STATUS          current
    DESCRIPTION        "Traffic type"
    ::= { eltSyslogCPURateLimiterEntry 1 }

eltSyslogCPURateLimiterEnabled OBJECT-TYPE
    SYNTAX          TruthValue
    MAX-ACCESS      read-write
    STATUS          current
    DESCRIPTION        "Enable logging of rate-limiter events"
    ::= { eltSyslogCPURateLimiterEntry 2 }

--
-- eltMesSyslogEvents
--

eltMesSyslogEvents  OBJECT IDENTIFIER
    ::= { eltMesSyslog 2 }

eltSyslogEventsVrrpTable OBJECT-TYPE
    SYNTAX          SEQUENCE OF EltSyslogEventsVrrpEntry
    MAX-ACCESS      read-write
    STATUS          current
    DESCRIPTION        "Enable/disable logging of VRRP events."
    ::= { eltMesSyslogEvents 1 }

EltSyslogEventsVRRPEventType ::= TEXTUAL-CONVENTION
    STATUS current
    DESCRIPTION    "Types of VRRP events."
    SYNTAX INTEGER {
        eltSyslogEventsVRRPEventProtocolError(1),
        eltSyslogEventsVRRPEventNewMaster(2)
}

EltSyslogEventsVrrpEntry ::= SEQUENCE {
	eltSyslogEventsVRRPEventIndex  		EltSyslogEventsVRRPEventType,
	eltSyslogEventsVRRPEventEnabled     TruthValue
}

eltSyslogEventsVrrpEntry OBJECT-TYPE
    SYNTAX          EltSyslogEventsVrrpEntry
    MAX-ACCESS      read-write
    STATUS          current
    DESCRIPTION        "An entry containing enable/disable logging of VRRP events."
    INDEX           { eltSyslogEventsVRRPEventIndex }
    ::= { eltSyslogEventsVrrpTable 1 }

eltSyslogEventsVRRPEventIndex OBJECT-TYPE
	SYNTAX			EltSyslogEventsVRRPEventType
    MAX-ACCESS		read-write
    STATUS			current
    DESCRIPTION			"Specify the index of VRRP event."
    ::= { eltSyslogEventsVrrpEntry 1 }

eltSyslogEventsVRRPEventEnabled OBJECT-TYPE
	SYNTAX			TruthValue
    MAX-ACCESS		read-write
    STATUS			current
    DESCRIPTION			"Enable logging of VRRP event."
    ::= { eltSyslogEventsVrrpEntry 2 }

eltSyslogUserCmdEnable OBJECT-TYPE
    SYNTAX  TruthValue
    MAX-ACCESS  read-write
    STATUS  current
    DESCRIPTION
        "User commands enter enable for syslog flash, syslog cache and syslog UDP.
         When set to true, generating syslog entry for user commands entered."
    DEFVAL  { false }
    ::= { eltMesSyslog 3 }
    
END
