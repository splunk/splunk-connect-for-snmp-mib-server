ChrComIfOpticsOMS-SRC-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfOptics				FROM  Chromatis-MIB
	chrComIfifIndex					FROM  ChrComIfifTable-MIB
	OMSControlType				FROM  OMSControlTypes-MIB
	Agcppc					FROM  OTSControlTypes-MIB
	APSDSTATE				FROM  OpaAPSDSTATE-MIB
	TruthValue				FROM  ChrTyp-MIB
	LaserActivation				FROM  LaserActivation-MIB;

-- chrComIfOpticsOMS-SRC Table

chrComIfOpticsOMS-SRCTable		OBJECT-TYPE
	SYNTAX		SEQUENCE OF ChrComIfOpticsOMS-SRCEntry
	MAX-ACCESS	not-accessible
	STATUS		current
	DESCRIPTION
	"The OMS is managed only for the Ring side of the Metropolis Network (not for the Trib side)."
	::= { chrComIfOptics 4}

chrComIfOpticsOMS-SRCEntry		OBJECT-TYPE
	SYNTAX		ChrComIfOpticsOMS-SRCEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "OMS-SRC"
	::= { chrComIfOpticsOMS-SRCTable  1 }

ChrComIfOpticsOMS-SRCEntry  ::=
	SEQUENCE  {
	chrComIfOpticsOmsSrcNumOfPrecedingOPAs Integer32	(-1..32),
	chrComIfOpticsOmsSrcDWDMOutputPower	Integer32	(-501..300),
	chrComIfOpticsOmsSrcDWDMLOOPThr	Integer32	(-501..300),
	chrComIfOpticsOmsSrcDWDMSafetyThr	Integer32	(-501..300),
	chrComIfOpticsOmsSrcTx1310Power	Integer32	(-501..300),
	chrComIfOpticsOmsSrcTxLambdaPower	Integer32	(-501..300),
	chrComIfOpticsOmsSrcADOMPwrControlMode OMSControlType,
	chrComIfOpticsOmsSrcExpectedAddedLambdaPower Integer32	(-501..300),
	chrComIfOpticsOmsSrcActualAddedPower	Integer32	(-501..300),
	chrComIfOpticsOmsSrcExpectedAddedLambdaPowerOffset Integer32	(-501..300),
	chrComIfOpticsOmsSrcActualAddedPowerOffset Integer32	(-501..300),
	chrComIfOpticsOmsSrcExpectedAddedChannelAttenuation Integer32	(-1..400),
	chrComIfOpticsOmsSrcActualAddedChannelAttenuation Integer32	(-1..400),
	chrComIfOpticsOmsSrcBackplaneAttenuatorLambda OCTET STRING	(SIZE (0..160)),
	chrComIfOpticsOmsSrcBackplaneAttenuator1310 Integer32	(-1..350),
	chrComIfOpticsOmsSrcTxLambdaLOOCThr	Integer32	(-501..300),
	chrComIfOpticsOmsSrcOCHSLOOCThrLambda	Integer32	(-501..300),
	chrComIfOpticsOmsSrcAddedLambdaLOOCThr Integer32	(-501..300),
	chrComIfOpticsOmsSrcTx1310LOOCThr	Integer32	(-501..300),
	chrComIfOpticsOmsSrcOCHSLOOCThr1310	Integer32	(-501..300),
	chrComIfOpticsOmsSrcPostOPADWDMInputPower Integer32	(-501..300),
	chrComIfOpticsOmsSrcPostOPAInputLOOCThr Integer32	(-501..300),
	chrComIfOpticsOmsSrcParamForPostOPAInputLOOCThr Integer32	(-501..300),
	chrComIfOpticsOmsSrcPostOPAInputLOOPThr Integer32	(-501..300),
	chrComIfOpticsOmsSrcPostOPAModeOfOperation Agcppc,
	chrComIfOpticsOmsSrcPostOPAExpectedGain Integer32	(-1..350),
	chrComIfOpticsOmsSrcPostOPAActualGain	Integer32	(-1..350),
	chrComIfOpticsOmsSrcPostOPAExpectedPumpPower Integer32	(-1..2000),
	chrComIfOpticsOmsSrcPostOPAActualPumpPower Integer32	(-1..2000),
	chrComIfOpticsOmsSrcPostOPAAPSDState	APSDSTATE,
	chrComIfOpticsOmsSrcPostOPAPumpRestartAction TruthValue,
	chrComIfOpticsOmsSrcPostOPAPumpLaserActivationStatus LaserActivation,
	chrComIfOpticsOmsSrcOPAExpectedAttenuatorAttenuation Integer32	(-1..400),
	chrComIfOpticsOmsSrcOPAActualAttenuatorAttenuation Integer32	(-1..400),
	chrComIfOpticsOmsSrcPostOPAPumpTemp	Unsigned32	(99..500),
	chrComIfOpticsOmsSrcPostOPAPumpBiasCurrent Integer32	(-1..4000),
	chrComIfOpticsAlarmVector		Integer32	(0..65535),
	chrComIfOpticsAlarmSeverityProfileIndex Unsigned32	(0..4294967295)
}

chrComIfOpticsOmsSrcNumOfPrecedingOPAs 	OBJECT-TYPE
	SYNTAX		Integer32	(-1..32)
	MAX-ACCESS 	read-write
	STATUS 		current
	DESCRIPTION
	"Number of OPAs prior to the respective ADOM/OMDM."
	::= { chrComIfOpticsOMS-SRCEntry  1 }

chrComIfOpticsOmsSrcDWDMOutputPower 	OBJECT-TYPE
	SYNTAX		Integer32	(-501..300)
	MAX-ACCESS 	read-only
	STATUS 		current
	DESCRIPTION
	"The optical power in the DWDM band (without the 1310nm channel) at the output of the module. "
	::= { chrComIfOpticsOMS-SRCEntry  2 }

chrComIfOpticsOmsSrcDWDMLOOPThr 	OBJECT-TYPE
	SYNTAX		Integer32	(-501..300)
	MAX-ACCESS 	read-write
	STATUS 		current
	DESCRIPTION
	"This is a threshold on OMS-SRC  DWDM output Power, indicating the existence of power in the DWDM band at the output of the module. "
	::= { chrComIfOpticsOMS-SRCEntry  3 }

chrComIfOpticsOmsSrcDWDMSafetyThr 	OBJECT-TYPE
	SYNTAX		Integer32	(-501..300)
	MAX-ACCESS 	read-write
	STATUS 		current
	DESCRIPTION
	"This is a threshold on OMS-SRC  DWDM output Power, indicating the safety power level in the DWDM band at the output of the ADOM/OMDM. "
	::= { chrComIfOpticsOMS-SRCEntry  4 }

chrComIfOpticsOmsSrcTx1310Power 	OBJECT-TYPE
	SYNTAX		Integer32	(-501..300)
	MAX-ACCESS 	read-only
	STATUS 		current
	DESCRIPTION
	"The optical power monitored on 1310 transmit point."
	::= { chrComIfOpticsOMS-SRCEntry  5 }

chrComIfOpticsOmsSrcTxLambdaPower 	OBJECT-TYPE
	SYNTAX		Integer32	(-501..300)
	MAX-ACCESS 	read-only
	STATUS 		current
	DESCRIPTION
	"The optical power monitored on Lambda transmit point."
	::= { chrComIfOpticsOMS-SRCEntry  6 }

chrComIfOpticsOmsSrcADOMPwrControlMode 	OBJECT-TYPE
	SYNTAX		OMSControlType
	MAX-ACCESS 	read-write
	STATUS 		current
	DESCRIPTION
	"Defines ADOM module operational mode. "
	::= { chrComIfOpticsOMS-SRCEntry  7 }

chrComIfOpticsOmsSrcExpectedAddedLambdaPower 	OBJECT-TYPE
	SYNTAX		Integer32	(-501..300)
	MAX-ACCESS 	read-write
	STATUS 		current
	DESCRIPTION
	"The expected added Lambda channel power after Attenuation (reflected to module out).  "
	::= { chrComIfOpticsOMS-SRCEntry  8 }

chrComIfOpticsOmsSrcActualAddedPower 	OBJECT-TYPE
	SYNTAX		Integer32	(-501..300)
	MAX-ACCESS 	read-only
	STATUS 		current
	DESCRIPTION
	"Monitored added lambda channel power after Attenuation (reflected to module out)."
	::= { chrComIfOpticsOMS-SRCEntry  9 }

chrComIfOpticsOmsSrcExpectedAddedLambdaPowerOffset 	OBJECT-TYPE
	SYNTAX		Integer32	(-501..300)
	MAX-ACCESS 	read-write
	STATUS 		current
	DESCRIPTION
	"The expected added to dropped lambda channel power offset. "
	::= { chrComIfOpticsOMS-SRCEntry  10 }

chrComIfOpticsOmsSrcActualAddedPowerOffset 	OBJECT-TYPE
	SYNTAX		Integer32	(-501..300)
	MAX-ACCESS 	read-only
	STATUS 		current
	DESCRIPTION
	"The Actual added to dropped lambda channel power offset."
	::= { chrComIfOpticsOMS-SRCEntry  11 }

chrComIfOpticsOmsSrcExpectedAddedChannelAttenuation 	OBJECT-TYPE
	SYNTAX		Integer32	(-1..400)
	MAX-ACCESS 	read-write
	STATUS 		current
	DESCRIPTION
	"The expected Attenuation of added  lambda channel  "
	::= { chrComIfOpticsOMS-SRCEntry  12 }

chrComIfOpticsOmsSrcActualAddedChannelAttenuation 	OBJECT-TYPE
	SYNTAX		Integer32	(-1..400)
	MAX-ACCESS 	read-only
	STATUS 		current
	DESCRIPTION
	""
	::= { chrComIfOpticsOMS-SRCEntry  13 }

chrComIfOpticsOmsSrcBackplaneAttenuatorLambda 	OBJECT-TYPE
	SYNTAX		OCTET STRING	(SIZE (0..160))
	MAX-ACCESS 	read-write
	STATUS 		current
	DESCRIPTION
	"Attenuation in dB. 
Zero when no backplane Attenuator exists.
"
	::= { chrComIfOpticsOMS-SRCEntry  14 }

chrComIfOpticsOmsSrcBackplaneAttenuator1310 	OBJECT-TYPE
	SYNTAX		Integer32	(-1..350)
	MAX-ACCESS 	read-write
	STATUS 		current
	DESCRIPTION
	"Attenuation in dB. 
Zero when no backplane Attenuator exists.
"
	::= { chrComIfOpticsOMS-SRCEntry  15 }

chrComIfOpticsOmsSrcTxLambdaLOOCThr 	OBJECT-TYPE
	SYNTAX		Integer32	(-501..300)
	MAX-ACCESS 	read-only
	STATUS 		current
	DESCRIPTION
	"Looc Threshold of transmitted lambda power."
	::= { chrComIfOpticsOMS-SRCEntry  16 }

chrComIfOpticsOmsSrcOCHSLOOCThrLambda 	OBJECT-TYPE
	SYNTAX		Integer32	(-501..300)
	MAX-ACCESS 	read-write
	STATUS 		current
	DESCRIPTION
	"A duplication of the OCH-S Looc Threshold."
	::= { chrComIfOpticsOMS-SRCEntry  17 }

chrComIfOpticsOmsSrcAddedLambdaLOOCThr 	OBJECT-TYPE
	SYNTAX		Integer32	(-501..300)
	MAX-ACCESS 	read-write
	STATUS 		current
	DESCRIPTION
	"Looc Threshold of added lambda."
	::= { chrComIfOpticsOMS-SRCEntry  18 }

chrComIfOpticsOmsSrcTx1310LOOCThr 	OBJECT-TYPE
	SYNTAX		Integer32	(-501..300)
	MAX-ACCESS 	read-only
	STATUS 		current
	DESCRIPTION
	"Looc Threshold of transmitted 1310."
	::= { chrComIfOpticsOMS-SRCEntry  19 }

chrComIfOpticsOmsSrcOCHSLOOCThr1310 	OBJECT-TYPE
	SYNTAX		Integer32	(-501..300)
	MAX-ACCESS 	read-write
	STATUS 		current
	DESCRIPTION
	"A duplication of the OCH-S Looc Threshold."
	::= { chrComIfOpticsOMS-SRCEntry  20 }

chrComIfOpticsOmsSrcPostOPADWDMInputPower 	OBJECT-TYPE
	SYNTAX		Integer32	(-501..300)
	MAX-ACCESS 	read-only
	STATUS 		current
	DESCRIPTION
	"The optical power in the DWDM band (without the 1310nm channel) at the input of the pre-OPA."
	::= { chrComIfOpticsOMS-SRCEntry  21 }

chrComIfOpticsOmsSrcPostOPAInputLOOCThr 	OBJECT-TYPE
	SYNTAX		Integer32	(-501..300)
	MAX-ACCESS 	read-only
	STATUS 		current
	DESCRIPTION
	"This is a threshold on OMS-SRC post-OPA DWDM input Power, indicating Loss Of Optical DWDM Channels at the input to the Post-OPA."
	::= { chrComIfOpticsOMS-SRCEntry  22 }

chrComIfOpticsOmsSrcParamForPostOPAInputLOOCThr 	OBJECT-TYPE
	SYNTAX		Integer32	(-501..300)
	MAX-ACCESS 	read-write
	STATUS 		current
	DESCRIPTION
	"Input parameter for calculating OMS-SRC post-OPA input LOOC threshold.

"
	::= { chrComIfOpticsOMS-SRCEntry  23 }

chrComIfOpticsOmsSrcPostOPAInputLOOPThr 	OBJECT-TYPE
	SYNTAX		Integer32	(-501..300)
	MAX-ACCESS 	read-write
	STATUS 		current
	DESCRIPTION
	"This is a threshold on OMS-SRC post-OPA DWDM input Power, indicating Loss Of Optical DWDM power at the input to the Post-OPA."
	::= { chrComIfOpticsOMS-SRCEntry  24 }

chrComIfOpticsOmsSrcPostOPAModeOfOperation 	OBJECT-TYPE
	SYNTAX		Agcppc
	MAX-ACCESS 	read-write
	STATUS 		current
	DESCRIPTION
	"§ (Automatic Gain Control  AGC  Default)
§ Automatic Pump Power Control  PPC
"
	::= { chrComIfOpticsOMS-SRCEntry  25 }

chrComIfOpticsOmsSrcPostOPAExpectedGain 	OBJECT-TYPE
	SYNTAX		Integer32	(-1..350)
	MAX-ACCESS 	read-write
	STATUS 		current
	DESCRIPTION
	"The Desired gain of the post OPA module (input to output optical DWDM power)."
	::= { chrComIfOpticsOMS-SRCEntry  26 }

chrComIfOpticsOmsSrcPostOPAActualGain 	OBJECT-TYPE
	SYNTAX		Integer32	(-1..350)
	MAX-ACCESS 	read-only
	STATUS 		current
	DESCRIPTION
	"The Actual gain of the post OPA (input to output optical DWDM power). "
	::= { chrComIfOpticsOMS-SRCEntry  27 }

chrComIfOpticsOmsSrcPostOPAExpectedPumpPower 	OBJECT-TYPE
	SYNTAX		Integer32	(-1..2000)
	MAX-ACCESS 	read-write
	STATUS 		current
	DESCRIPTION
	"The Desired EDFA pump power of post-OPA module. "
	::= { chrComIfOpticsOMS-SRCEntry  28 }

chrComIfOpticsOmsSrcPostOPAActualPumpPower 	OBJECT-TYPE
	SYNTAX		Integer32	(-1..2000)
	MAX-ACCESS 	read-only
	STATUS 		current
	DESCRIPTION
	"The Actual EDFA pump power of post-OPA module. "
	::= { chrComIfOpticsOMS-SRCEntry  29 }

chrComIfOpticsOmsSrcPostOPAAPSDState 	OBJECT-TYPE
	SYNTAX		APSDSTATE
	MAX-ACCESS 	read-write
	STATUS 		current
	DESCRIPTION
	"Controlling the Automatic Pump Shut Down (APSD) mode. "
	::= { chrComIfOpticsOMS-SRCEntry  30 }

chrComIfOpticsOmsSrcPostOPAPumpRestartAction 	OBJECT-TYPE
	SYNTAX		TruthValue
	MAX-ACCESS 	read-write
	STATUS 		current
	DESCRIPTION
	"Enables remote operation which is equivalent to the restart push button of the post-OPA."
	::= { chrComIfOpticsOMS-SRCEntry  31 }

chrComIfOpticsOmsSrcPostOPAPumpLaserActivationStatus 	OBJECT-TYPE
	SYNTAX		LaserActivation
	MAX-ACCESS 	read-only
	STATUS 		current
	DESCRIPTION
	"Post OPA Pump Laser ON/OFF Actual status. "
	::= { chrComIfOpticsOMS-SRCEntry  32 }

chrComIfOpticsOmsSrcOPAExpectedAttenuatorAttenuation 	OBJECT-TYPE
	SYNTAX		Integer32	(-1..400)
	MAX-ACCESS 	read-write
	STATUS 		current
	DESCRIPTION
	"The expected Attenuation of the attenuator at the output of the OPA  "
	::= { chrComIfOpticsOMS-SRCEntry  33 }

chrComIfOpticsOmsSrcOPAActualAttenuatorAttenuation 	OBJECT-TYPE
	SYNTAX		Integer32	(-1..400)
	MAX-ACCESS 	read-only
	STATUS 		current
	DESCRIPTION
	"The actual Attenuation of the attenuator at the output of the OPA"
	::= { chrComIfOpticsOMS-SRCEntry  34 }

chrComIfOpticsOmsSrcPostOPAPumpTemp 	OBJECT-TYPE
	SYNTAX		Unsigned32	(99..500)
	MAX-ACCESS 	read-only
	STATUS 		current
	DESCRIPTION
	"The temperature of the module."
	::= { chrComIfOpticsOMS-SRCEntry  35 }

chrComIfOpticsOmsSrcPostOPAPumpBiasCurrent 	OBJECT-TYPE
	SYNTAX		Integer32	(-1..4000)
	MAX-ACCESS 	read-only
	STATUS 		current
	DESCRIPTION
	""
	::= { chrComIfOpticsOMS-SRCEntry  36 }

chrComIfOpticsAlarmVector 	OBJECT-TYPE
	SYNTAX		Integer32	(0..65535)
	MAX-ACCESS 	read-only
	STATUS 		current
	DESCRIPTION
	""
	::= { chrComIfOpticsOMS-SRCEntry  37 }

chrComIfOpticsAlarmSeverityProfileIndex 	OBJECT-TYPE
	SYNTAX		Unsigned32	(0..4294967295)
	MAX-ACCESS 	read-write
	STATUS 		current
	DESCRIPTION
	""
	::= { chrComIfOpticsOMS-SRCEntry  38 }


END
