--
-- she-pm-cpuram-mib.mib
-- MIB generated by MG-SOFT Visual MIB Builder Version 6.0  Build 88
-- Thursday, September 18, 2008 at 08:40:36
--

-- Start of ClearCase branch-information of current release:
-- she-pm-cpuram-mib.mib   /main/she_r2.8_grf/1
-- End of ClearCase branch-information.

	SHE-PM-CPURAM-MIB DEFINITIONS ::= BEGIN
 
		IMPORTS
			she			
				FROM AN-MIB			
			PhysicalIndex			
				FROM ENTITY-MIB			
			OBJECT-GROUP, MODULE-COMPLIANCE			
				FROM SNMPv2-CONF			
			OBJECT-TYPE, MODULE-IDENTITY			
				FROM SNMPv2-SMI;
	
	
		shePmCpuRamMib MODULE-IDENTITY 
			LAST-UPDATED "200809180833Z"		-- September 18, 2008 at 08:33 GMT
			ORGANIZATION 
				"Nokia Siemens Networks"
			CONTACT-INFO 
				"COO BBA
				Siemens Building in Beijing
				
				jie.shen@nsn.com
				##########################
				gerd.barchmann@nsn.com"
			DESCRIPTION 
				"The MIB module to describe the CPU and RAM utilization
				PM counters."
			REVISION "200809180834Z"		-- September 18, 2008 at 08:34 GMT
			DESCRIPTION 
				"Merge to common SHE MIB package."
			::= { she 31 }

		
	
	
--
-- Node definitions
--
	
		shePmCpuRamObjects OBJECT IDENTIFIER ::= { shePmCpuRamMib 1 }

		
		shePmCpuRamTable OBJECT-TYPE
			SYNTAX SEQUENCE OF ShePmCpuRamEntry
			MAX-ACCESS not-accessible
			STATUS current
			DESCRIPTION
				"Each entry in this table contains the CPU and RAM usage
				for a CXU or IU board."
			::= { shePmCpuRamObjects 1 }

		
		shePmCpuRamEntry OBJECT-TYPE
			SYNTAX ShePmCpuRamEntry
			MAX-ACCESS not-accessible
			STATUS current
			DESCRIPTION
				"An entry in shePmCpuRamTable."
			INDEX { shePmCpuRamSlotPhysIndex }
			::= { shePmCpuRamTable 1 }

		
		ShePmCpuRamEntry ::=
			SEQUENCE { 
				shePmCpuRamSlotPhysIndex
					PhysicalIndex,
				shePmCpuRamCardPhysIndex
					PhysicalIndex,
				shePmCpuRamCpuUtilization
					INTEGER,
				shePmCpuRamRamUtilization
					INTEGER
			 }

		shePmCpuRamSlotPhysIndex OBJECT-TYPE
			SYNTAX PhysicalIndex
			MAX-ACCESS read-only
			STATUS current
			DESCRIPTION
				"The PhysicalIndex of the slot that contains the card whose CPU and
				RAM usage is given in this row."
			::= { shePmCpuRamEntry 1 }

		
		shePmCpuRamCardPhysIndex OBJECT-TYPE
			SYNTAX PhysicalIndex
			MAX-ACCESS read-only
			STATUS current
			DESCRIPTION
				"The PhysicalIndex of the card whose CPU and RAM usage is given in this row.
				The readable text of the card type could be obtained from entPhysicalName."
			::= { shePmCpuRamEntry 2 }

		
		shePmCpuRamCpuUtilization OBJECT-TYPE
			SYNTAX INTEGER (0..100)
			UNITS "%"
			MAX-ACCESS read-only
			STATUS current
			DESCRIPTION
				"The average, over the last minute, of the percentage of time that the CPU was not idle."
			::= { shePmCpuRamEntry 3 }

		
		shePmCpuRamRamUtilization OBJECT-TYPE
			SYNTAX INTEGER (0..100)
			UNITS "%"
			MAX-ACCESS read-only
			STATUS current
			DESCRIPTION
				"The percentage of used RAM compared to the total RAM size."
			::= { shePmCpuRamEntry 4 }

		
		shePmCpuRamMibConformance OBJECT IDENTIFIER ::= { shePmCpuRamMib 100 }

		
		shePmCpuRamMibCompliances OBJECT IDENTIFIER ::= { shePmCpuRamMibConformance 1 }

		
		shePmCpuRamMibCompliance MODULE-COMPLIANCE
			STATUS current
			DESCRIPTION 
				"Description."
			MODULE -- this module
				MANDATORY-GROUPS { shePmCpuRamMibGroup }
			::= { shePmCpuRamMibCompliances 1 }

		
		shePmCpuRamMibGroups OBJECT IDENTIFIER ::= { shePmCpuRamMibConformance 2 }

		
		shePmCpuRamMibGroup OBJECT-GROUP
			OBJECTS { shePmCpuRamSlotPhysIndex, shePmCpuRamCardPhysIndex, shePmCpuRamCpuUtilization, shePmCpuRamRamUtilization }
			STATUS current
			DESCRIPTION 
				"Description."
			::= { shePmCpuRamMibGroups 1 }

		
	
	END

--
-- she-pm-cpuram-mib.mib
--
