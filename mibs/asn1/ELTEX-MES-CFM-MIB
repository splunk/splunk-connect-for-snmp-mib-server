-- Descriptions of managed objects for ELTEX IEEE 802.ag CFM MIB.
--
-- March 2013, Babintsev
--
-- Copyright (c) 2012-2013 by Eltex Ent.
-- All rights reserved.
-- *****************************************************************
-- --------------------------------------------------------------
-- Eltex MES CFM MIB
-- --------------------------------------------------------------
--
-- This MIB is an addendum to the standard IEEE8021-CFM-MIB.


ELTEX-MES-CFM-MIB DEFINITIONS ::= BEGIN

IMPORTS
	MODULE-IDENTITY,
	OBJECT-TYPE,
	NOTIFICATION-TYPE,
	Integer32, Counter32,
	Unsigned32               FROM SNMPv2-SMI    -- [RFC2578]
	TEXTUAL-CONVENTION,
	TimeInterval,
	TimeStamp, RowStatus,
	TruthValue, MacAddress,
	TDomain, TAddress        FROM SNMPv2-TC     -- [RFC2579]
	eltMesMng                FROM ELTEX-MES
	MODULE-COMPLIANCE,
	OBJECT-GROUP,
	NOTIFICATION-GROUP       FROM SNMPv2-CONF   -- [RFC2580]
	InterfaceIndex,
	InterfaceIndexOrZero     FROM IF-MIB        -- [RFC2863]
	VlanIdOrNone, VlanId     FROM Q-BRIDGE-MIB  -- [RFC4363]
	Dot1agCfmMpDirection     FROM IEEE8021-CFM-MIB
	;

eltMesCfmMIB   MODULE-IDENTITY
	LAST-UPDATED "201511190000Z"    -- 19/11/2015 00:00GMT
	ORGANIZATION "Eltex, Ent."
	CONTACT-INFO
					"www.eltex.nsk.ru"
	DESCRIPTION
		"Connectivity Fault Management module for managing Eltex devices"

	REVISION	 "201303190000Z"	-- 19/03/2013 00:00GMT
	DESCRIPTION
	"Initial version."
  
	REVISION	 "201511190000Z"	-- 19/11/2015 00:00GMT
	DESCRIPTION
  		"Deprecate all objects in this module."
		::= { eltMesMng 774 }


eltMesCfmNotifications      OBJECT IDENTIFIER ::= { eltMesCfmMIB 0 }
eltMesCfmMIBObjects         OBJECT IDENTIFIER ::= { eltMesCfmMIB 1 }
eltMesCfmConformance        OBJECT IDENTIFIER ::= { eltMesCfmMIB 2 }

-- ******************************************************************
-- Groups in the CFM MIB Module
-- ******************************************************************
eltMesCfmMd                 OBJECT IDENTIFIER ::= { eltMesCfmMIBObjects 1 }
eltMesCfmMa                 OBJECT IDENTIFIER ::= { eltMesCfmMIBObjects 2 }


-- ******************************************************************
-- The Maintenance Domain Table
-- ******************************************************************

eltCfmMdTable OBJECT-TYPE
    SYNTAX      SEQUENCE OF EltCfmMdEntry
    MAX-ACCESS  not-accessible
    STATUS      deprecated
    DESCRIPTION
       "The Maintenance Domain table. Each row in the table
        represents a physical maintanance domain that corresponds
        user-like domain name.
        "
    ::= { eltMesCfmMd 1 }

eltCfmMdEntry OBJECT-TYPE
    SYNTAX      EltCfmMdEntry
    MAX-ACCESS  not-accessible
    STATUS      deprecated
    DESCRIPTION
       "The Maintenance Domain table entry. This entry is not lost
        upon reboot. It is backed up by stable storage.
       "
    INDEX {eltCfmMdName }
    ::= { eltCfmMdTable 1 }

EltCfmMdEntry ::= SEQUENCE {
      eltCfmMdName                 OCTET STRING,
      eltCfmMdIndex                Unsigned32,
      eltCfmMdRowStatus            RowStatus
    }

eltCfmMdName OBJECT-TYPE
    SYNTAX      OCTET STRING (SIZE(1..32))
    MAX-ACCESS  not-accessible
    STATUS      deprecated
    DESCRIPTION
       "The user-like name of Maintenance Domain.
       "
    ::= { eltCfmMdEntry 1 }

eltCfmMdIndex OBJECT-TYPE
    SYNTAX      Unsigned32(1..4294967295)
    MAX-ACCESS  read-create
    STATUS      deprecated
    DESCRIPTION
       "The index to the Maintenance Domain table dot1agCfmMdTable
       (IEEE8021-CFM-MIB).
       "
    ::= { eltCfmMdEntry 2 }

eltCfmMdRowStatus OBJECT-TYPE
    SYNTAX      RowStatus
    MAX-ACCESS  read-create
    STATUS      deprecated
    DESCRIPTION
       "The status of the row.

        The writable columns in a row can not be changed if the row
        is active. All columns MUST have a valid value before a row
        can be activated.
       "
    ::= { eltCfmMdEntry 3 }

-- ******************************************************************
-- The Maintenance Association (MA) Table
-- ******************************************************************

eltCfmMaTable OBJECT-TYPE
    SYNTAX      SEQUENCE OF EltCfmMaEntry
    MAX-ACCESS  not-accessible
    STATUS      deprecated
    DESCRIPTION
       "The Maintenance Association table. This is the part of the complete
        MA table from IEEE8021-CFM-MIB. It implements
        restrictions in IEEE 802.1ag-2007 22.2.2 upon creating MEPS.
        Each row in the table represents an MA.  An MA is a set of MEPs,
        each configured with a single service instance.

        This table uses two indices, first index is the index of the
        Maintenance Domain table.  The second index is the same as the
        index of the dot1agCfmMaCompEntry for the same MA.

        The writable objects in this table need to be persistent
        upon reboot or restart of a device.

       "
    REFERENCE
       "22.2.2"
    ::= { eltMesCfmMa 1 }

eltCfmMaEntry OBJECT-TYPE
    SYNTAX      EltCfmMaEntry
    MAX-ACCESS  not-accessible
    STATUS      deprecated
    DESCRIPTION
       "The MA table entry."
    INDEX {eltCfmMdIndex, eltCfmMaIndex }
    ::= { eltCfmMaTable 1 }

EltCfmMaEntry ::= SEQUENCE {
      eltCfmMaIndex                Unsigned32,
      eltCfmMaDirection            Dot1agCfmMpDirection,
      eltCfmMaRowStatus            RowStatus
    }

eltCfmMaIndex OBJECT-TYPE
    SYNTAX      Unsigned32(1..4294967295)
    MAX-ACCESS  not-accessible
    STATUS      deprecated
    DESCRIPTION
       "Index of the MA table.
       "
    ::= { eltCfmMaEntry 1 }

eltCfmMaDirection OBJECT-TYPE
    SYNTAX      Dot1agCfmMpDirection
    MAX-ACCESS  read-create
    STATUS      deprecated
    DESCRIPTION
       "Direction in which the all the MPs in current MA face on the Bridge Port.
       "
    ::= { eltCfmMaEntry 2 }

eltCfmMaRowStatus OBJECT-TYPE
    SYNTAX      RowStatus
    MAX-ACCESS  read-create
    STATUS      deprecated
    DESCRIPTION
       "The status of the row.

        The writable columns in a row can not be changed if the row
        is active. All columns MUST have a valid value before a row
        can be activated.
       "
    ::= { eltCfmMaEntry 3 }


END
