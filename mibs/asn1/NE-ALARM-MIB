--======================================================================
-- ALARM MIB 
--======================================================================

-- File Name   : ALARM-MIB.mib
-- Date        : Tue May 16 00:00:00 CEST 2006
-- Author      : Franck Paris

NE-ALARM-MIB DEFINITIONS ::= BEGIN

  IMPORTS
	spidcom       FROM SPIDCOM-MIB;
		

--  1.3.6.1.4.1.22764.2    
  neMibAlarm OBJECT IDENTIFIER ::= { spidcom 2 }



--=========================   END OF DOCUMENT   ========================

END
