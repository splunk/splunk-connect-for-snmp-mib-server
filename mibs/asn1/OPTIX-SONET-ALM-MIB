--
-- OPTIX-SONET-ALM-MIB.mib
-- MIB generated by MG-SOFT Visual MIB Builder Version 3.0 Build 253
-- Wednesday, February 22, 2006 at 18:32:03
--

-- =================================================================
-- Copyright (C) 2006 by HUAWEI TECHNOLOGIES. All rights reserved
-- 
-- Description:This MIB describes the Alarm interface of Huawei SONET transmit
-- Reference:
-- Version: V1.00
-- History:
-- <author>,<date>,<contents>
-- =================================================================
-- 

    OPTIX-SONET-ALM-MIB DEFINITIONS ::= BEGIN
 
        IMPORTS
            optixCommonSonet            
                FROM OPTIX-OID-MIB            
            MOD2Type, AlmDataNtfcnCdeType, AlarmEventType, AlmDataSrvEffType, LocationType, 
            DirectionType            
                FROM OPTIX-SONET-TC-MIB            
            OBJECT-GROUP, MODULE-COMPLIANCE            
                FROM SNMPv2-CONF            
            Unsigned32, OBJECT-TYPE, MODULE-IDENTITY            
                FROM SNMPv2-SMI            
            DateAndTime            
                FROM SNMPv2-TC;
    
    
        optixSonetAlarm MODULE-IDENTITY 
            LAST-UPDATED "200602250000Z"
            ORGANIZATION 
                "Huawei Technologies co.,Ltd."
            CONTACT-INFO 
                "R&D Building
                Huawei Technologies Co., Ltd.
                Bantian, Longgang District 
                Shenzhen, P. R. China
                http://www.huawei.com
                Zip:518129
                E-mail:support@huawei.com
                "
            DESCRIPTION 
                "Description."
            REVISION "200602250000Z"
            DESCRIPTION
                "The initial revision of this MIB module."
            ::= { optixCommonSonet 10 }
        
    
    
--
-- Node definitions
--
    
        -- 1.3.6.1.4.1.2011.2.25.3.20.10.10
        almData OBJECT IDENTIFIER ::= { optixSonetAlarm 10 }  
               
-- *************************************************************************
--  Fault Management
-- -------------------------------------------------------------------------
--  Alarm Data Table (RTRV-ALM-<MOD2>)
-- -------------------------------------------------------------------------
        -- 1.3.6.1.4.1.2011.2.25.3.20.10.10.10
        almDataTable OBJECT-TYPE
            SYNTAX SEQUENCE OF AlmDataEntry
            MAX-ACCESS not-accessible
            STATUS current
            DESCRIPTION
                "Alarm data table"
            ::= { almData 10 }
        
        -- 1.3.6.1.4.1.2011.2.25.3.20.10.10.10.1
        almDataEntry OBJECT-TYPE
            SYNTAX AlmDataEntry
            MAX-ACCESS not-accessible
            STATUS current
            DESCRIPTION
                "Alarm data table"
            INDEX { almDataMOD2, almDataSlot, almDataPort, almDataPath, almDataVT, 
                almDataNtfcnCde, almDataName, almDataSrvEff, almDataLocation, almDataDirection
                 }
            ::= { almDataTable 1 }
        
        AlmDataEntry ::=
            SEQUENCE { 
                almDataMOD2
                    MOD2Type,
                almDataSlot
                    Unsigned32,
                almDataPort
                    Unsigned32,
                almDataPath
                    Unsigned32,
                almDataVT
                    Unsigned32,
                almDataNtfcnCde
                    AlmDataNtfcnCdeType,
                almDataName
                    AlarmEventType,
                almDataSrvEff
                    AlmDataSrvEffType,
                almDataLocation
                    LocationType,
                almDataDirection
                    DirectionType,
                almDataDateTime
                    DateAndTime,
                almDataDesc
                    OCTET STRING,
                almDataAiddet
                    Unsigned32
             }

--  <MOD2>
-- <aid> 
-- <aid>  
-- <aid>  
-- <aid>  
-- <ntfcncde>                     
-- <condtype>            
-- <srveff>          
-- <locn>          
-- <dirn>  
-- <ocrdat> + <ocrtm> 
-- <conddesc>  
-- <aiddet>  
        -- 1.3.6.1.4.1.2011.2.25.3.20.10.10.10.1.1
        almDataMOD2 OBJECT-TYPE
            SYNTAX MOD2Type
            MAX-ACCESS read-only
            STATUS current
            DESCRIPTION
                "Signal mode."
            ::= { almDataEntry 1 }
        
        -- 1.3.6.1.4.1.2011.2.25.3.20.10.10.10.1.2
        almDataSlot OBJECT-TYPE
            SYNTAX Unsigned32
            MAX-ACCESS read-only
            STATUS current
            DESCRIPTION
                "Slot number.
                
                This will indicate what is the slot 
                of the object which raised this alarm.
                If not relevant to the alarm, will be
                zero."
            ::= { almDataEntry 2 }
        
        -- 1.3.6.1.4.1.2011.2.25.3.20.10.10.10.1.3
        almDataPort OBJECT-TYPE
            SYNTAX Unsigned32
            MAX-ACCESS read-only
            STATUS current
            DESCRIPTION
                "Port Number.
                
                This will indicate what is the Port 
                of the object which raised this alarm.
                If not relevant to the alarm, will be
                zero."
            ::= { almDataEntry 3 }
        
        -- 1.3.6.1.4.1.2011.2.25.3.20.10.10.10.1.4
        almDataPath OBJECT-TYPE
            SYNTAX Unsigned32
            MAX-ACCESS read-only
            STATUS current
            DESCRIPTION
                "Path number.
                
                This will indicate what is the Path 
                of the object which raised this alarm.
                If not relevant to the alarm, will be
                zero."
            ::= { almDataEntry 4 }
        
        -- 1.3.6.1.4.1.2011.2.25.3.20.10.10.10.1.5
        almDataVT OBJECT-TYPE
            SYNTAX Unsigned32
            MAX-ACCESS read-only
            STATUS current
            DESCRIPTION
                "VT path number.
                
                This will indicate what is the VT path 
                of the object which raised this alarm.
                If not relevant to the alarm, will be
                zero."
            ::= { almDataEntry 5 }
        
        -- 1.3.6.1.4.1.2011.2.25.3.20.10.10.10.1.6
        almDataNtfcnCde OBJECT-TYPE
            SYNTAX AlmDataNtfcnCdeType
            MAX-ACCESS read-only
            STATUS current
            DESCRIPTION
                "The notification code of the retrieved alarm. 
                Only CR|MJ|MN will be represented here."
            ::= { almDataEntry 6 }
        
        -- 1.3.6.1.4.1.2011.2.25.3.20.10.10.10.1.7
        almDataName OBJECT-TYPE
            SYNTAX AlarmEventType
            MAX-ACCESS read-only
            STATUS current
            DESCRIPTION
                "Alarm name."
            ::= { almDataEntry 7 }
        
        -- 1.3.6.1.4.1.2011.2.25.3.20.10.10.10.1.8
        almDataSrvEff OBJECT-TYPE
            SYNTAX AlmDataSrvEffType
            MAX-ACCESS read-only
            STATUS current
            DESCRIPTION
                "The effect on service caused by the alarm condition.
                Only NSA(Nonservice-effecting)|SA(Service-effecting) will be represented here."
            ::= { almDataEntry 8 }
        
        -- 1.3.6.1.4.1.2011.2.25.3.20.10.10.10.1.9
        almDataLocation OBJECT-TYPE
            SYNTAX LocationType
            MAX-ACCESS read-only
            STATUS current
            DESCRIPTION
                "Alarm location. 
                Only NEND(Near end)|FEND(Far end)|ALL will be represented here."
            ::= { almDataEntry 9 }
        
        -- 1.3.6.1.4.1.2011.2.25.3.20.10.10.10.1.10
        almDataDirection OBJECT-TYPE
            SYNTAX DirectionType
            MAX-ACCESS read-only
            STATUS current
            DESCRIPTION
                "Alarm direction.
                Only RCV(Receive direction)|TRMT(Transmit direction)|ALL will be represented here."
            ::= { almDataEntry 10 }
        
        -- 1.3.6.1.4.1.2011.2.25.3.20.10.10.10.1.11
        almDataDateTime OBJECT-TYPE
            SYNTAX DateAndTime
            MAX-ACCESS read-only
            STATUS current
            DESCRIPTION
                "Alarm date and time."
            ::= { almDataEntry 11 }
        
        -- 1.3.6.1.4.1.2011.2.25.3.20.10.10.10.1.12
        almDataDesc OBJECT-TYPE
            SYNTAX OCTET STRING (SIZE (0..64))
            MAX-ACCESS read-only
            STATUS current
            DESCRIPTION
                "Text message."
            ::= { almDataEntry 12 }
        
        -- 1.3.6.1.4.1.2011.2.25.3.20.10.10.10.1.13
        almDataAiddet OBJECT-TYPE
            SYNTAX Unsigned32
            MAX-ACCESS read-only
            STATUS current
            DESCRIPTION
                "Supplementary equipment identification."
            ::= { almDataEntry 13 }
        
--  -------------------------------------------------------------------------
-- Alarm Condition Table (RTRV-COND-<MOD2>)
-- -------------------------------------------------------------------------
        -- 1.3.6.1.4.1.2011.2.25.3.20.10.10.20
        condDataTable OBJECT-TYPE
            SYNTAX SEQUENCE OF CondDataEntry
            MAX-ACCESS not-accessible
            STATUS current
            DESCRIPTION
                "MOD2 condition table."
            ::= { almData 20 }
        
        -- 1.3.6.1.4.1.2011.2.25.3.20.10.10.20.1
        condDataEntry OBJECT-TYPE
            SYNTAX CondDataEntry
            MAX-ACCESS not-accessible
            STATUS current
            DESCRIPTION
                "MOD2 condition table."
            INDEX { condDataMOD2, condDataSlot, condDataPort, condDataPath, condDataVT, 
                condDataName, condDataLocation, condDataDirection }
            ::= { condDataTable 1 }
        
        CondDataEntry ::=
            SEQUENCE { 
                condDataMOD2
                    MOD2Type,
                condDataSlot
                    Unsigned32,
                condDataPort
                    Unsigned32,
                condDataPath
                    Unsigned32,
                condDataVT
                    Unsigned32,
                condDataName
                    AlarmEventType,
                condDataLocation
                    LocationType,
                condDataDirection
                    DirectionType,
                condDataNtfcnCde
                    AlmDataNtfcnCdeType,
                condDataSrvEff
                    AlmDataSrvEffType,
                condDataDateTime
                    DateAndTime,
                condDataDesc
                    OCTET STRING
             }

--  <MOD2>
-- <aid> 
-- <aid> 
-- <aid> 
-- <aid> 
-- <typerep> 
-- <locn>         
-- <dirn>   
-- <ntfcncde>  
-- <srveff> 
-- <ocrdat> + <ocrtm>
-- <conddesc>      
        -- 1.3.6.1.4.1.2011.2.25.3.20.10.10.20.1.1
        condDataMOD2 OBJECT-TYPE
            SYNTAX MOD2Type
            MAX-ACCESS read-only
            STATUS current
            DESCRIPTION
                "Signal mode."
            ::= { condDataEntry 1 }
        
        -- 1.3.6.1.4.1.2011.2.25.3.20.10.10.20.1.2
        condDataSlot OBJECT-TYPE
            SYNTAX Unsigned32
            MAX-ACCESS read-only
            STATUS current
            DESCRIPTION
                "Slot number.
                
                This will indicate what is the slot 
                of the object which raised this alarm.
                If not relevant to the alarm, will be
                zero."
            ::= { condDataEntry 2 }
        
        -- 1.3.6.1.4.1.2011.2.25.3.20.10.10.20.1.3
        condDataPort OBJECT-TYPE
            SYNTAX Unsigned32
            MAX-ACCESS read-only
            STATUS current
            DESCRIPTION
                "Port number.
                
                This will indicate what is the Port 
                of the object which raised this alarm.
                If not relevant to the alarm, will be
                zero."
            ::= { condDataEntry 3 }
        
        -- 1.3.6.1.4.1.2011.2.25.3.20.10.10.20.1.4
        condDataPath OBJECT-TYPE
            SYNTAX Unsigned32
            MAX-ACCESS read-only
            STATUS current
            DESCRIPTION
                "Path number."
            ::= { condDataEntry 4 }
        
        -- 1.3.6.1.4.1.2011.2.25.3.20.10.10.20.1.5
        condDataVT OBJECT-TYPE
            SYNTAX Unsigned32
            MAX-ACCESS read-only
            STATUS current
            DESCRIPTION
                "VT path number.
                
                This will indicate what is the VT path 
                of the object which raised this alarm.
                If not relevant to the alarm, will be
                zero."
            ::= { condDataEntry 5 }
        
        -- 1.3.6.1.4.1.2011.2.25.3.20.10.10.20.1.6
        condDataName OBJECT-TYPE
            SYNTAX AlarmEventType
            MAX-ACCESS read-only
            STATUS current
            DESCRIPTION
                "Condition name."
            ::= { condDataEntry 6 }
        
        -- 1.3.6.1.4.1.2011.2.25.3.20.10.10.20.1.7
        condDataLocation OBJECT-TYPE
            SYNTAX LocationType
            MAX-ACCESS read-only
            STATUS current
            DESCRIPTION
                "Alarm location.
                Only NEND(Near end)|FEND(Far end)|ALL will be represented here."
            ::= { condDataEntry 7 }
        
        -- 1.3.6.1.4.1.2011.2.25.3.20.10.10.20.1.8
        condDataDirection OBJECT-TYPE
            SYNTAX DirectionType
            MAX-ACCESS read-only
            STATUS current
            DESCRIPTION
                "Alarm direction.
                Only RCV(Receive direction)|TRMT(Transmit direction)|ALL will be represented here."
            ::= { condDataEntry 8 }
        
        -- 1.3.6.1.4.1.2011.2.25.3.20.10.10.20.1.9
        condDataNtfcnCde OBJECT-TYPE
            SYNTAX AlmDataNtfcnCdeType
            MAX-ACCESS read-only
            STATUS current
            DESCRIPTION
                "The notification code of the retrieved alarm. 
                Only NA|NR will be represented here."
            ::= { condDataEntry 9 }
        
        -- 1.3.6.1.4.1.2011.2.25.3.20.10.10.20.1.10
        condDataSrvEff OBJECT-TYPE
            SYNTAX AlmDataSrvEffType
            MAX-ACCESS read-only
            STATUS current
            DESCRIPTION
                "The effect on service caused by the alarm condition.
                Only NSA(Nonservice-effecting)|SA(Service-effecting) will be represented here."
            ::= { condDataEntry 10 }
        
        -- 1.3.6.1.4.1.2011.2.25.3.20.10.10.20.1.11
        condDataDateTime OBJECT-TYPE
            SYNTAX DateAndTime
            MAX-ACCESS read-only
            STATUS current
            DESCRIPTION
                "Date and time when the triggering event occurred."
            ::= { condDataEntry 11 }
        
        -- 1.3.6.1.4.1.2011.2.25.3.20.10.10.20.1.12
        condDataDesc OBJECT-TYPE
            SYNTAX OCTET STRING (SIZE (0..64))
            MAX-ACCESS read-only
            STATUS current
            DESCRIPTION
                "Text message."
            ::= { condDataEntry 12 }
        
--  -------------------------------------------------------------------------
-- Alarm Environment Table (RTRV-ALM-ENV)
-- -------------------------------------------------------------------------
        -- 1.3.6.1.4.1.2011.2.25.3.20.10.10.30
        almEnvDataTable OBJECT-TYPE
            SYNTAX SEQUENCE OF AlmEnvDataEntry
            MAX-ACCESS not-accessible
            STATUS current
            DESCRIPTION
                "environment alarm table"
            ::= { almData 30 }
        
        -- 1.3.6.1.4.1.2011.2.25.3.20.10.10.30.1
        almEnvDataEntry OBJECT-TYPE
            SYNTAX AlmEnvDataEntry
            MAX-ACCESS not-accessible
            STATUS current
            DESCRIPTION
                "environment alarm table"
            INDEX { almEnvDataAid, almEnvDataNtfcnCde, almEnvDataName }
            ::= { almEnvDataTable 1 }
        
        AlmEnvDataEntry ::=
            SEQUENCE { 
                almEnvDataAid
                    Unsigned32,
                almEnvDataNtfcnCde
                    AlmDataNtfcnCdeType,
                almEnvDataName
                    AlarmEventType,
                almEnvDataDateTime
                    DateAndTime,
                almEnvDataCondDesc
                    OCTET STRING
             }

--  <envaid>
-- <ntfcncde>
-- <almtype>
-- <ocrdat> + <ocrtm>
-- <almmsg>   
        -- 1.3.6.1.4.1.2011.2.25.3.20.10.10.30.1.1
        almEnvDataAid OBJECT-TYPE
            SYNTAX Unsigned32
            MAX-ACCESS read-only
            STATUS current
            DESCRIPTION
                "AID of the input switch for environment monitoring."
            ::= { almEnvDataEntry 1 }
        
        -- 1.3.6.1.4.1.2011.2.25.3.20.10.10.30.1.2
        almEnvDataNtfcnCde OBJECT-TYPE
            SYNTAX AlmDataNtfcnCdeType
            MAX-ACCESS read-only
            STATUS current
            DESCRIPTION
                "The notification code of the retrieved alarm. 
                Only CR|MJ|MN|NA will be represented here."
            ::= { almEnvDataEntry 2 }
        
        -- 1.3.6.1.4.1.2011.2.25.3.20.10.10.30.1.3
        almEnvDataName OBJECT-TYPE
            SYNTAX AlarmEventType
            MAX-ACCESS read-only
            STATUS current
            DESCRIPTION
                "Condition type."
            ::= { almEnvDataEntry 3 }
        
        -- 1.3.6.1.4.1.2011.2.25.3.20.10.10.30.1.4
        almEnvDataDateTime OBJECT-TYPE
            SYNTAX DateAndTime
            MAX-ACCESS read-only
            STATUS current
            DESCRIPTION
                "Date and time when the triggering event occurred."
            ::= { almEnvDataEntry 4 }
        
        -- 1.3.6.1.4.1.2011.2.25.3.20.10.10.30.1.5
        almEnvDataCondDesc OBJECT-TYPE
            SYNTAX OCTET STRING (SIZE (0..64))
            MAX-ACCESS read-only
            STATUS current
            DESCRIPTION
                "Text message."
            ::= { almEnvDataEntry 5 }

--  -------------------------------------------------------------------------
-- Alarm Summary Table
-- --------------------------------------------------------------------------

        -- 1.3.6.1.4.1.2011.2.25.3.20.10.11
        almSummary OBJECT IDENTIFIER ::= { optixSonetAlarm 11 } 

        -- 1.3.6.1.4.1.2011.2.25.3.20.10.11.10
        almSummaryCritical OBJECT-TYPE
            SYNTAX INTEGER
            MAX-ACCESS read-only
            STATUS current
            DESCRIPTION
                "Critical alarm count."
            ::= { almSummary 10 }

        -- 1.3.6.1.4.1.2011.2.25.3.20.10.11.20
        almSummaryMajor OBJECT-TYPE
            SYNTAX INTEGER
            MAX-ACCESS read-only
            STATUS current
            DESCRIPTION
                "Major alarm count."
            ::= { almSummary 20 }
            
        -- 1.3.6.1.4.1.2011.2.25.3.20.10.11.30
        almSummaryMinor OBJECT-TYPE
            SYNTAX INTEGER
            MAX-ACCESS read-only
            STATUS current
            DESCRIPTION
                "Minor alarm count."
            ::= { almSummary 30 }                

        
        -- 1.3.6.1.4.1.2011.2.25.3.20.10.20
        optixSonetAlarmConformance OBJECT IDENTIFIER ::= { optixSonetAlarm 20 }
        
        -- 1.3.6.1.4.1.2011.2.25.3.20.10.20.1
        optixSonetAlarmGroups OBJECT IDENTIFIER ::= { optixSonetAlarmConformance 1 }
        
        -- 1.3.6.1.4.1.2011.2.25.3.20.10.20.1.1
        optixSonetAlarmObjectGroup OBJECT-GROUP
            OBJECTS { almDataMOD2, almDataSlot, almDataPort, almDataPath, almDataVT, 
                almDataNtfcnCde, almDataName, almDataSrvEff, almDataLocation, almDataDirection, 
                almDataDateTime, almDataDesc, almDataAiddet, condDataMOD2, condDataSlot, 
                condDataPort, condDataPath, condDataVT, condDataName, condDataLocation, 
                condDataDirection, condDataNtfcnCde, condDataSrvEff, condDataDateTime, condDataDesc, 
                almEnvDataAid, almEnvDataNtfcnCde, almEnvDataName, almEnvDataDateTime, almEnvDataCondDesc
                 }
            STATUS current
            DESCRIPTION 
                "Enter the description of the created OBJECT-GROUP."
            ::= { optixSonetAlarmGroups 1 }
        
        -- 1.3.6.1.4.1.2011.2.25.3.20.10.20.2
        optixSonetAlarmCompliances OBJECT IDENTIFIER ::= { optixSonetAlarmConformance 2 }
        
        -- 1.3.6.1.4.1.2011.2.25.3.20.10.20.2.1
        optixSonetAlarmBasicCompliance MODULE-COMPLIANCE
            STATUS current
            DESCRIPTION 
                "Enter the description of the created MODULE-COMPLIANCE."
            MODULE -- this module
                MANDATORY-GROUPS { optixSonetAlarmObjectGroup }
            ::= { optixSonetAlarmCompliances 1 }
        
    
    END

--
-- OPTIX-SONET-ALM-MIB.mib
--
