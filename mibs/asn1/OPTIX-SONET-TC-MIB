--
-- OPTIX-SONET-TC-MIB.mib
-- MIB generated by MG-SOFT Visual MIB Builder Version 3.0 Build 253
-- Monday, March 06, 2006 at 10:11:59
--

-- =================================================================
-- Copyright (C) 2006 by HUAWEI TECHNOLOGIES. All rights reserved
-- 
-- Description:This MIB describes the TC interface of Huawei SONET transmit
-- Reference:
-- Version: V1.10
-- History:
-- <yuanxiaoshu>,<2006-05-10>,<change event name from evtXXX to almXXX, because alarm attribute can be changed>
-- =================================================================

    OPTIX-SONET-TC-MIB DEFINITIONS ::= BEGIN
 
        IMPORTS
            optixCommon            
                FROM OPTIX-OID-MIB            
            MODULE-IDENTITY            
                FROM SNMPv2-SMI            
            TEXTUAL-CONVENTION            
                FROM SNMPv2-TC;
    
    
        optixsonetTCMIB MODULE-IDENTITY 
            LAST-UPDATED "200602250000Z"
            ORGANIZATION 
                "Huawei Technologies Co.,Ltd."
            CONTACT-INFO 
                "R&D Building
                Huawei Technologies Co., Ltd.
                Bantian, Longgang District 
                Shenzhen, P. R. China
                http://www.huawei.com
                Zip:518129
                E-mail:support@huawei.com
                "
            DESCRIPTION 
                "This module describes rules of Huawei transmit 
                platform self-defined types."
            REVISION "200602250000Z"
            DESCRIPTION
                "The initial revision of this MIB module."
            ::= { optixCommon 99 }
        
    
--
-- Textual conventions
--
    
        AlarmEventType ::= TEXTUAL-CONVENTION
            STATUS current
            DESCRIPTION 
                "Alarm ID."
            SYNTAX INTEGER
                {
                almLoc(3),
                almFileLost(6),
                almReiL(37),
                almBcmPumHigh(69),
                almTimS(87),
                almSyncAllLos(100),
                almSyncBad(101),
                almSyncLos(111),
                almPs(120),
                almDbmsError(185),
                almLosMut(186),
                almLosChan(187),
                almChanAdd(188),
                almTd(189),
                almClcPumHigh(192),
                almS1SynChange(193),
                almProtectMode(198),
                almSecuAlm(200),
                almFecLof(212),
                almFecOof(213),
                almRateOver(223),
                almCfgbdFail(232),
                almLoopback(240),
                almClcModHigh(270),
                almOtuLof(272),
                almOtuOom(273),
                almSmTim(274),
                almPmTim(275),
                almSmBdi(276),
                almPmBdi(277),
                almSmBei(278),
                almPmBei(279),
                almSmIae(280),
                almSmBipExc(282),
                almPmBipExc(283),
                almSmBipSd(284),
                almPmBipSd(285),
                almOtuAis(286),
                almOduAis(287),
                almOduOci(288),
                almOduLck(289),
                almSumInpwrHigh(323),
                almSumInpwrLow(324),
                almSumOutpwrHigh(325),
                almSumOutpwrLow(326),
                almGainLow(327),
                almBeffecExc(335),
                almDgeAdjFail(433),
                almWavelenLockFail(439),
                almHscUnavail(440),
                envEnvAircompr(502),
                envEnvAircond(503),
                envEnvAirdryr(504),
                envEnvBatdschrg(505),
                envEnvBattery(506),
                envEnvClfan(507),
                envEnvCpmajor(508),
                envEnvCpminor(509),
                envEnvEngine(510),
                envEnvEngoprg(511),
                envEnvExplgs(512),
                envEnvFirdetr(513),
                envEnvFire(514),
                envEnvFlood(515),
                envEnvFuse(516),
                envEnvGen(517),
                envEnvHiair(518),
                envEnvHihum(519),
                envEnvHitemp(520),
                envEnvHiwtr(521),
                envEnvIntruder(522),
                envEnvLwbatvg(523),
                envEnvLwfuel(524),
                envEnvLwhum(525),
                envEnvLwpres(526),
                envEnvLwtemp(527),
                envEnvLwwtr(528),
                envEnvMisc(529),
                envEnvOpendr(530),
                envEnvPower(531),
                envEnvPump(532),
                envEnvPwr48(536),
                envEnvRect(537),
                envEnvRecthi(538),
                envEnvRectlo(539),
                envEnvSmoke(540),
                envEnvToxicgas(541),
                envEnvVentn(542),
                envContAircond(543),
                envContEngine(544),
                envContFan(545),
                envContGen(546),
                envContHeat(547),
                envContLight(548),
                envContMisc(549),
                envContSpklr(550),
                almEsconCderr(570),
                almCommitTimeout(573),
                almSwdlNepkgcheck(574),
                almSwdlChgmngMismatch(575),
                almDbsyncFail(591),
                almClientMm(604),
                almLaserModuleMismatch(606),
                almEqptNsa(32768),
                almEqptSa(32769),
                almApsb(32774),
                almFeprlf(32776),
                almApscm(32777),
                almApsmm(32778),
                almApstm(32779),
                almHldoverSync(32791),
                almFreerunSync(32792),
                almFstsync(32794),
                almManualSsmSet(32798),
                almFanRmv(32802),
                almSingleFanFail(32803),
                almMultiFanFail(32804),
                almMea(32807),
                almRmv(32808),
                almTf(32814),
                almSfS(32815),
                almInPwrHigh(32816),
                almInPwrLow(32817),
                almSfL(32818),
                almSdL(32819),
                almLsrEol(32820),
                almOutPwrHigh(32821),
                almOutPwrLow(32822),
                almSdS(32823),
                almAisL(32824),
                almRfiL(32825),
                almAisP(32826),
                almLopP(32827),
                almTimP(32828),
                almUneqP(32829),
                almSfP(32830),
                almSdP(32831),
                almRfiP(32832),
                almAls(32833),
                almLpbkfacility(32834),
                almLpbkterm(32835),
                almPlmP(32836),
                almErfiPPld(32837),
                almErfiPSer(32838),
                almErfiPConn(32839),
                almPdiP(32840),
                almPwrFail(32841),
                almLopV(32842),
                almAisV(32843),
                almPlmV(32844),
                almUneqV(32845),
                almRfiV(32846),
                almErfiVSer(32847),
                almErfiVConn(32848),
                almErfiVPld(32849),
                almIntfRmv(32876),
                almSyncSsmChange(32877),
                almTimingModeChange(32878),
                almLow(32879),
                almLp(32880),
                almFrcd(32881),
                almMan(32882),
                almExer(32883),
                almWtr(32884),
                almSwtoidle(32886),
                almSwFail(32887),
                almSyncSw(32889),
                almChanFail(32890),
                almPwraFail(32891),
                almPwrbFail(32892),
                almIntfMea(32899),
                almIntfFail(32900),
                almAic(32901),
                almDbmsCfgDamage(32903),
                almDefkbyte(32904),
                almIncnaps(32905),
                almImaps(32906),
                almEtsql(32907),
                almTplalm(32908),
                almSqlalm(32909),
                almNodeidMm(32910),
                almXconMm(32911),
                almRingmMm(32912),
                almSqlmMm(32913),
                almLpS(32915),
                almLowR(32916),
                almLowS(32917),
                almFrcdR(32918),
                almFrcdS(32919),
                almManR(32920),
                almManS(32921),
                almExerR(32922),
                almExerS(32923),
                almLpAllS(32924),
                almRingswitch(32925),
                almSpanswtich(32926),
                almSwtopassthru(32927),
                almLsql(32928),
                almDbmsCfgBackupFailed(33156),
                almFanFail(33161),
                almInvalidEqpt(33170),
                almLapdbvHigh(33171),
                almLapdbvLow(33172),
                almLbcHigh(33174),
                almLbcLow(33175),
                almLccHigh(33176),
                almLccLow(33177),
                almLinkErr(33280),
                almLoa(33281),
                almLof(33282),
                almLomP(33283),
                almLos(33284),
                almLtempHigh(33286),
                almLtempLow(33287),
                almNebdDataMea(33289),
                almNoLsrPara(33298),
                almReffail(33301),
                almSdV(33304),
                almSfV(33305),
                almSqmP(33312),
                almSvMea(33314),
                almTempHi(33315),
                almAis(33316),
                almInhlpbk(33330),
                almLockout(33331),
                almLaserShut(33332),
                almLpbkallds1feac(33333),
                almLpbkcrs(33335),
                almLpbkds1feac(33336),
                almLpbkds3feac(33337),
                almLpbkfacilityP(33345),
                almLpbktermP(33347),
                almPrimarychnChange(33348),
                almRai(33349),
                almSsmDql(33350),
                almSsmLos(33351),
                almTsa(33361),
                almNormal(33363),
                almWkswbk(33364),
                almWkswpr(33365),
                almAteRmv(33368),
                almPowerRmv(33370),
                almOof(33372),
                almExerSuccess(33373),
                almExerFail(33374),
                almUpgradeIp(33375),
                almChassisMea(33377),
                almLaserNotExist(36923),
                almLcasBwReduced(36924),
                almGfpLof(36925),
                almFanOpen(36926),
                almFanClose(36927),
                almLevelMea(36928),
                almTCvL(36930),
                almDccFail(36936),
                almLanLoc(36937),
                almTCvcpP(36938),
                almTCvP(36939),
                almTCvpP(36940),
                almTCvS(36941),
                almTCvV(36942),
                almTEscpP(36943),
                almTEsL(36944),
                almTEsP(36945),
                almTEspP(36946),
                almTEsS(36947),
                almTEsV(36948),
                almTPjcsPdet(36949),
                almTPjcsVdet(36950),
                almTSescpP(36951),
                almTSesL(36952),
                almTSesP(36953),
                almTSespP(36954),
                almTSesS(36955),
                almTSesV(36956),
                almTUascpP(36957),
                almTUasL(36958),
                almTUasP(36959),
                almTUaspP(36960),
                almTUasV(36961),
                almBitsAis(36966),
                almBitsLof(36967),
                almBitsLos(36968),
                almBitsCvover(36969),
                almBlsrSfR(36970),
                almBlsrSfS(36971),
                almBlsrSdR(36972),
                almBlsrSdS(36973),
                almIsolateNode(36974),
                almSf(36975),
                almSd(36976),
                almAutosw(36977),
                almLpbkfac2ni(40960),
                almStateChange(40973),
                almMtMode(40974),
                almRmvToMt(40979),
                almRstFromMt(40980),
                almLpbk(40981),
                almRlsLpbk(40982),
                almRemcSf(63604),
                almRemcSD(63605),
                almPowerSwitch(63607),
                almPortOffline(63629),
                almDataLost(63630),
                almSqmV(65409),
                almLomV(65410),
                almFcsErr(65411),
                almRevertiveModeMismatch(40970),
                almRingIDMismatch(40971),
                almIncorrectFiberConnection(40972),
                almSyncNotSyncnronized(40983),
                almPowerExceed(40984),
                almLcasPlct(36978),
                almLcasPlcr(36979),
                almLcasTlct(36980),
                almLcasTlcr(36981),
                almLcasFopt(36985),
                almLcasFopr(36986),
                almGfpCsf(40961),
                almLptRfi(12300),
                almPartialUnprotected(40985),
                almFanMea(40986),
                almLagPortFail(12769),
                almDlagProtFail(12288),
                almCcLoss(12298),
                almMpConflict(12299),
                almOamRemoteLoop(12291),
                almOamRemoteSD(12292),
                almOamRemoteSF(12293),
                almOamFail(12294),
                almOamSelfLoop(12767),
                almEthCfmMismerge(12823),
                almEthCfmUnexperi(12824),
                almEthCfmLoc(12825),
                almEthCfmRdi(12826)
                }
            
        AlmDataNtfcnCdeType ::= TEXTUAL-CONVENTION
            STATUS current
            DESCRIPTION 
                "The notification code of alarm."
            SYNTAX INTEGER
                {
                cr(1),
                mj(2),
                mn(3),
                na(4),
                nr(5)
                }
            
        AlmDataSrvEffType ::= TEXTUAL-CONVENTION
            STATUS current
            DESCRIPTION 
                "The effect on service caused by alarm."
            SYNTAX INTEGER
                {
                nsa(1),
                sa(2)
                }
            
        DirectionType ::= TEXTUAL-CONVENTION
            STATUS current
            DESCRIPTION 
                "Direction parameters,sorted by ID."
            SYNTAX INTEGER
                {
                all(0),
                rcv(1),
                trmt(2)
                }
            
        LocationType ::= TEXTUAL-CONVENTION
            STATUS current
            DESCRIPTION 
                "Location parameters,sorted by ID."
            SYNTAX INTEGER
                {
                all(0),
                nend(1),
                fend(2)
                }
            
        MOD2Type ::= TEXTUAL-CONVENTION
            STATUS current
            DESCRIPTION 
                "MOD2 parameters,sorted by ID."
            SYNTAX INTEGER
                {
                mod2All(0),
                mod2Ds1(1),
                mod2E100(2),
                mod2E1000(3),
                mod2Ec1(4),
                mod2Oc3(5),
                mod2Oc12(6),
                mod2Oc48(7),
                mod2Oc192(8),
                mod2Sts1(9),
                mod2Sts3c(10),
                mod2Sts6c(11),
                mod2Sts9c(12),
                mod2Sts12c(13),
                mod2Sts15c(14),
                mod2Sts24c(15),
                mod2Sts48c(16),
                mod2Sts192c(17),
                mod2T1(18),
                mod2T3(19),
                mod2M13(20),
                mod2Vt1(21),
                mod2Vt2(22),
                mod2Env(23),
                mod2Sync(24),
                mod2Bits(25),
                mod2Eqpt(26),
                mod2Ds3(27),
                mod2Stm1(28),
                mod2Stm4(29),
                mod2Stm16(30),
                mod2Stm64(31),
                mod2Vc3(32),
                mod2Vc4(33),
                mod2Vc12(34),
                mod2Vc16c(35),
                mod2Vc4c(36),
                mod2E1(37),
                mod2E3(38),
                mod2E1t1(39),
                mod2E3t3(40),
                mod2Hardware(41),
                mod2Syncall(42),
                mod2Syncne(43),
                mod2Syncfac(44),
                mod2Cont(45),
                mod2Ochl(46),
                mod2Pg(47),
                mod2Feth(48),
                mod2Geth(49),
                mod2Fe(50),
                mod2Ge(51),
                mod2Vctrunk(52),
                mod2Och(53),
                mod2Wdm(54),
                mod2Client(55),
                mod2Eth(56),
                mod2Osc(57),
                mod2Mca(58),
                mod2Variable(59),
                mod2Xgeth(60),
                mod2Fc(61),
                mod2Dcc(62),
                mod2Lan(63),
                mod2EQPT(64),
                mod2Butt(65)
                }
            
        PerformanceEventType ::= TEXTUAL-CONVENTION
            STATUS current
            DESCRIPTION 
                "Performance ID."
            SYNTAX INTEGER
                {
                pmSesS(32770),
                pmCvL(32784),
                pmEsL(32785),
                pmSesL(32786),
                pmUasL(32789),
                pmPsd(32799),
                pmCvP(32800),
                pmEsP(32801),
                pmPjcsVDet(32852),
                pmBdtempcur(32992),
                pmBdtempmax(32993),
                pmBdtempmin(32994),
                pmPmutempcur(33000),
                pmPmutempmax(33001),
                pmPmutempmin(33002),
                pmLbccur(33008),
                pmLbcmax(33009),
                pmLbcmin(33010),
                pmOptcur(33011),
                pmOptmax(33012),
                pmOptmin(33013),
                pmOprcur(33014),
                pmOprmax(33015),
                pmOprmin(33016),
                pmCvpP(33056),
                pmCvcpP(33057),
                pmEspP(33058),
                pmEscpP(33059),
                pmSespP(33060),
                pmSescpP(33061),
                pmUaspP(33064),
                pmUascpP(33065),
                pmPscProtect(33088),
                pmPsdProtect(33089),
                pmPscSpan(33090),
                pmPsdSpan(33091),
                pmPscRing(33092),
                pmPsdRing(33093),
                pmPscWork(33094),
                pmPsdWork(33095),
                pmLcccur(36864),
                pmLccmax(36865),
                pmLccmin(36866),
                pmLtempcur(36867),
                pmLtempmax(36868),
                pmLtempmin(36869),
                pmLapdbvcur(36870),
                pmLapdbvmax(36871),
                pmLapdbvmin(36872),
                pmPlbccur(36873),
                pmPlbcmax(36874),
                pmPlbcmin(36875),
                pmPlwccur(36876),
                pmPlwcmax(36877),
                pmPlwcmin(36878),
                pmCvS(36879),
                pmEsS(36880),
                pmSesP(36881),
                pmUasP(36882),
                pmCvV(36883),
                pmEsV(36884),
                pmSesV(36885),
                pmUasV(36886),
                pmPsc(36887),
                pmPjcsPDet(45065)
                }
            
        ValidflagType ::= TEXTUAL-CONVENTION
            STATUS current
            DESCRIPTION 
                "Valid flag,sorted by ID."
            SYNTAX INTEGER
                {
                invalid(0),
                valid(1)
                }
            
    
--
-- Node definitions
--
    
    
    END

--
-- OPTIX-SONET-TC-MIB.mib
--
