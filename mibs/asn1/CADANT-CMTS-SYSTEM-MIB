CADANT-CMTS-SYSTEM-MIB DEFINITIONS ::= BEGIN

IMPORTS
    OBJECT-TYPE, MODULE-IDENTITY, Counter32, Integer32, IpAddress, Unsigned32
        FROM SNMPv2-SMI
    MODULE-COMPLIANCE, OBJECT-GROUP
        FROM SNMPv2-CONF
    TruthValue, DisplayString, MacAddress, DateAndTime, RowStatus
        FROM SNMPv2-TC
    InetAddressType, InetAddress, InetAddressIPv4, InetAddressIPv6
        FROM INET-ADDRESS-MIB
    InterfaceIndexOrZero 
        FROM IF-MIB
    cadSystem
        FROM CADANT-PRODUCTS-MIB
    CardId, AdminState, ServerType, OverloadThreshold, AdminSrcAddrType
        FROM CADANT-TC
    BitRate
        FROM DOCS-QOS3-MIB
    TenthdB
        FROM DOCS-IF-MIB
    SnmpAdminString, SnmpEngineID
        FROM SNMP-FRAMEWORK-MIB;

cadSystemMib MODULE-IDENTITY
    LAST-UPDATED "201511110000Z" -- November 11, 2015
    ORGANIZATION 
        "ARRIS Group, Inc."
    CONTACT-INFO 
        "Arris Technical Support
         Phone:  +1 630 281 3000
         E-Mail: support@arris.com"
    DESCRIPTION 
        "Arris E6000 system parameters and constants"
        
--  REVISION "201512150000Z"
--  DESCRIPTION  
--     "Add operation mode to prevent modems from using an upstream frequency beyond 42 MHz."
    REVISION "201511110000Z" -- November 11, 2015
    DESCRIPTION  
        "Add ofdmSparingCleanupOff(8) to cadSysSpOperMode" 
    REVISION "201511060000Z" -- November 6, 2015
    DESCRIPTION  
        "Adjust default network packet/event rates."
    REVISION "201509100000Z" -- Sept 10, 2015
    DESCRIPTION  
        "Add upDownTrapIfDescrOff(7) to cadSysSpOperMode" 
    REVISION "201507210000Z" -- July 21, 2015
    DESCRIPTION  
        "Change upper limit of cadSysLicensePorts from 1000 to 5000."
    REVISION "201506030000Z" -- June 3, 2015
    DESCRIPTION  
        "Change upper limit of cadSysLicensePorts from 256 to 1000."
    REVISION "201503300000Z" -- March 30, 2015
    DESCRIPTION  
        "Change default value of cadSysContact from support@arrisi.com to support@arris.com."
    REVISION "201503050000Z" -- March 5, 2015
    DESCRIPTION  
        "Increase the allowed IGMP throttle rate."
    REVISION "201410070000Z" -- Oct 7, 2014
    DESCRIPTION  
        "Add cadSysProcErmRpcPacketRate, cadSysProcErmRpcPacketsReceivedPassed and
         cadSysProcErmRpcPacketsReceivedDropped."
    REVISION "201408050000Z" -- Aug 5, 2014
    DESCRIPTION  
        "Add cadSysAES128Enable."
    REVISION "201406100000Z" -- June 10, 2014
    DESCRIPTION  
        "Add configuration for flap list insertion."
    REVISION "201405290000Z" -- May 29, 2014
    DESCRIPTION  
        "Remove support for reduced TCS generation (i.e. remove tcsReducedOff(8) from cadSysSpOperMode)."
    REVISION "201405210000Z" -- May 21, 2014
    DESCRIPTION  
        "Changed cadSysMtceDULPacketInterval default from 30000 to 10000"
    REVISION "201405140000Z" -- May 14, 2014
    DESCRIPTION  
        "Remove cadSysModPriUsInTcsEnabled and cadSysModPriUsDbcEnabled"
    REVISION "201404250000Z" -- April 25, 2014
    DESCRIPTION  
        "Change default value of cadSysProcVrepPacketRate and cadSysProcVpmePacketRate"
    REVISION "201404100000Z" -- April 10, 2014
    DESCRIPTION  
        "Add cadSysProcVrepPacketRate, cadSysProcVpmePacketRate,
         cadSysProcVrepPacketsReceivedPassed, cadSysProcVrepPacketsReceivedDropped,
         cadSysProcVpmePacketsReceivedPassed and cadSysProcVpmePacketsReceivedDropped."
    REVISION "201403130000Z" -- March 13, 2014
    DESCRIPTION  
        "Add cadSysProcLacpPacketRate, cadSysProcLacpPacketsReceivedPassed and 
             cadSysProcLacpPacketsReceivedDropped."
    REVISION "201403060000Z" -- March 6, 2014
    DESCRIPTION  
        "Add cadSysPatchParams."
    REVISION "201402210000Z" -- Feburary 21, 2014
    DESCRIPTION  
        "Add cadSysModPriUsInTcsEnabled and cadSysModPriUsDbcEnabled"
    REVISION "201401160000Z" -- January 16, 2014
    DESCRIPTION  
        "remove rcsLoadBalOn(20) from cadSysSpOperMode."
    REVISION "201311190000Z" -- November 19, 2013
    DESCRIPTION  
        "Add operation mode for RCS load balancing control."
    REVISION "201309060000Z" -- Sep 6, 2013
    DESCRIPTION  
        "Add cadSysProcClearPolicingCounts."
    REVISION "201308130000Z" -- August 13, 2013
    DESCRIPTION  
        "Add support for LDP protocol throttling."
    REVISION "201307220000Z" -- July 22, 2013
    DESCRIPTION  
        "Add an additional reload status value for patch apply" 
    REVISION "201307100000Z" -- July 10, 2013
    DESCRIPTION  
        "Removed factoryDCAMTestOff(7) from cadSysSpOperMode" 
    REVISION "201307010000Z" -- July 1, 2013
    DESCRIPTION  
        "Add patch apply support." 
    REVISION "201306210000Z" -- June 21, 2013
    DESCRIPTION  
        "Add support for reduced TCS generation."
    REVISION "201306200000Z" -- June 20, 2013
    DESCRIPTION  
        "Add cadSys1x1onCmAcPwrLossEnabled." 
    REVISION "201306190000Z" -- Jun 19, 2013
    DESCRIPTION  
        "Add NPU Host Event throttling rate into CadSysProcPolicingConfig and related counts into CadSysProcPolicingCounts." 
    REVISION "201305150000Z" -- May 5, 2013
    DESCRIPTION  
        "Add cadSysMICSecondarySecretTable." 
    REVISION "201301080000Z" -- January 8, 2013
    DESCRIPTION  
        "Add patching operation support."
    REVISION "201212030000Z" -- Dec 3, 2012
    DESCRIPTION  
        "Remove fiveTapPtsOff(20) from cadSysSpOperMode." 
    REVISION "201211300000Z" -- Nov 30, 2012
    DESCRIPTION  
        "Rename object names in cadLaesMdTimestampModeTable" 
    REVISION "201211150000Z" -- Oct 15, 2012
    DESCRIPTION  
        "Add loadBalUnbondedVoipOn(6) and factoryDCAMTestOff(7) to cadSysSpOperMode" 
    REVISION "201210040000Z" -- Oct 4, 2012
    DESCRIPTION  
        "Remove cadSysDownChannelAnnex" 
    REVISION "201210010000Z" -- Oct 1, 2012
    DESCRIPTION  
        "Add cadLaesMdTimestampModeTable" 
    REVISION "201206150000Z" -- June 15, 2012
    DESCRIPTION  
        "remove CadSysSourceInterface table and
         remove cadSnmpSourceIpAddrType and
         cadSnmpSourceIpAddr" 
    REVISION "201203220000Z" -- Mar 22, 2012
    DESCRIPTION  
        "Add port licensing control."
    REVISION "201203040000Z" -- Mar 4, 2012
    DESCRIPTION  
        "Add new reload status values for standby firmware upgrade and standby write mem."
    REVISION "201202230000Z" -- Feb 23, 2012
    DESCRIPTION  
        "Add cadSysSourceAddressTable"
    REVISION "201202080000Z" -- February 9, 2012
    DESCRIPTION  
        "Add support for enhanced SNR with new TAPs."
    REVISION "201201180000Z" -- Jan 18, 2012
    DESCRIPTION  
        "Add new reload status value for image copy."
    REVISION "201112130000Z" -- Dec 13, 2011
    DESCRIPTION  
        "Add new reload status value."
    REVISION "201111170000Z" -- Nov 17, 2011
    DESCRIPTION  
        "Add new reload status values."
    REVISION "201111080000Z" -- Nov 8, 2011
    DESCRIPTION  
        "Removed upstreamLockupIgnore and upstreamLockupDetectLong. 
         Add support for maintenance lockup detection configuration."
    REVISION "201111040000Z" -- Nov 4, 2011
    DESCRIPTION  
        "Remove the following MIB objects:
         cadSysProcScmGlobalPacketRate ,cadSysProcScmGlobalPacketsReceivedPassed, 
         cadSysProcScmGlobalPacketsReceivedDropped,cadSysProcOspfv3PacketsSent,
         cadSysProcTftpIpv6PacketsSent,cadSysProcRouterControlGlobalPacketsSent,
         cadSysProcArpPacketsSent, cadSysProcDhcpPacketsSent,
         cadSysProcIcmpPacketsSent, cadSysProcOspfPacketsSent,
         cadSysProcRipPacketsSent, cadSysProcIgmpPacketsSent,
         cadSysProcRouterControlOtherPacketsSent, cadSysProcSnmpPacketsSent,
         cadSysProcTftpPacketsSent, cadSysProcIsisPacketsSent,
         cadSysProcScmGlobalPacketsSent, cadSysProcNdPacketsSent,
         cadSysProcDhcpIpv6PacketsSent, cadSysProcIcmpIpv6PacketsSent,
         cadSysProcMldPacketsSent, cadSysProcBgpPacketsSent,
         cadSysProcPimPacketsSent, cadSysProcSnmpCmPacketsSent,
         cadSysProcCopsPacketsSent, and cadSysProcTelnetPacketsSent."
    REVISION "201107080000Z" -- July 8, 2011
    DESCRIPTION  
        "Add support for maintenance control of fan speed."
    REVISION "201105220000Z" -- May 22, 2011
    DESCRIPTION  
        "Add support for maintenance overload configuration."
    REVISION "201104050000Z" -- Apr 5, 2011 
    DESCRIPTION 
        "Modified allowed values of cadSysReloadStatus."
    REVISION "201103030000Z" -- March 3, 2011
    DESCRIPTION 
        "Add cadSysTftpProxy 
             cadSysProcTftpIpv6PacketRate 
             cadSysProcTftpIpv6PacketsReceivedPassed 
             cadSysProcTftpIpv6PacketsReceivedDropped 
             cadSysProcTftpIpv6PacketsSent"
    REVISION "201102230000Z" -- Feb 23, 2011 
    DESCRIPTION 
        "Add cpeNacksForceCmReset bit back to cadSysSpOperMode"
    REVISION "201012220000Z" -- Dec 22, 2010
    DESCRIPTION  
        "Change cadSysDataServerSnmpRefreshTime to be in seconds"
    REVISION "201012100000Z" -- Dec 10, 2010
    DESCRIPTION  
        "Deprecated upstreamLockupIgnore and upstreamLockupDetectLong
         and cadSysModemLossThreshold"
    REVISION "201012010000Z" -- Dec 1, 2010
    DESCRIPTION  
        "Add cadSysSnmpReadAheadMax and cadSysSnmpRefreshTime"
    REVISION "201011180000Z" -- Nov 18, 2010
    DESCRIPTION  
        "Add cadSysMacMoveBlockedOnRcptDhcpPkt"
    REVISION "201009220000Z" -- Sep 22, 2010
    DESCRIPTION  
        "Add support for DataServer variables."
    REVISION "201009150000Z" -- Sep 15, 2010
    DESCRIPTION  
        "Add pending(3), and none(4) to cadSysXDLicKeyStatus"
    REVISION "201009020000Z" -- Sep 2, 2010
    DESCRIPTION  
        "Add cadSysUnicastNpUsAcquisition"
    REVISION "201007310000Z" -- July 31, 2010
    DESCRIPTION  
        "Add support for OSPFv3 counts."
    REVISION "201007210000Z" -- July 21, 2010 
    DESCRIPTION 
        "Remove cadSysAttrFlowAssignStrictEnforcement"   
    REVISION "201007120000Z" -- July 12, 2010 
    DESCRIPTION 
         "Add cadSysAttrFlowAssignStrictEnforcement"
    REVISION "201003150000Z" -- Mar 15, 2010 
    DESCRIPTION 
         "Add cadSysAllowAmbiguityOverride"
    REVISION "201002230000Z" -- Feb 23, 2010 
    DESCRIPTION 
         "Deprecate cadSysControlGroup"
    REVISION "201002110000Z" -- Feb 11, 2010 
    DESCRIPTION 
         "Add reloadWritemem and reloadEraseMem to cadSysReloadOperation
          and eraseMem and remoteEraseMem to cadSysReloadStatus"
    REVISION "201001080000Z" -- Jan 8, 2010 
    DESCRIPTION 
        "Add cadSysPeakTrRateUpstream and cadCosUpPeakTrafficRate for Upstream 
         Power Boot feature. Make cadSysPeakTrafRateFor11CMs obsolete"   
    REVISION "200910080000Z" -- Oct 8, 2009 
    DESCRIPTION 
        "change default value of cadSysDelayedCpeLearning from false(2) to true(1)"   
    REVISION "200909220000Z" -- Sep 22, 2009
    DESCRIPTION  
        "chagne default value of cadSysProcNdPacketRate from 1000 to 700"
    REVISION "200909140000Z" -- Sep 14, 2009
    DESCRIPTION  
        "Add cadSysSendTccRefIdPerFragment"
    REVISION "200908170000Z" -- Aug 17, 2009
    DESCRIPTION  
        "Add cadSysModPriDsInRccEnabled"
    REVISION "200905040000Z" -- May 4, 2009
    DESCRIPTION  
        "Add new cadSysSpOperMode use16ForDSPeakTrafficRate"
    REVISION "200904220000Z" -- Apr 22, 2009
    DESCRIPTION 
        "Added cadSysSourceIpAddrCableIntercept, cadSysSourceInterfaceCableIntercept
         and cadSnmpSourceIpAddrTypeCableIntercept."
    REVISION "200901230000Z" -- Jan 23, 2009
    DESCRIPTION 
        "Added cadSysDelayedCpeLearning."
    REVISION "200812180000Z" -- December 18, 2008
    DESCRIPTION 
       "cadSysProcArpPacketRate default value changed from 2500 to 700"    
    REVISION "200812080000Z" -- December 8, 2008
    DESCRIPTION 
        "Add cadMtcmConditionalOverride."
    REVISION "200810220000Z" -- October 22, 2008
    DESCRIPTION 
        "Add cadSysLO1LeakDetect control for DMM LO1 spurs."
    REVISION "200809240000Z" -- Sep 24, 2008
    DESCRIPTION 
        "Add cadSysProcCopsPacketRate and cadSysProcTelnetPacketRate."
    REVISION "200809150000Z" -- Sep 15, 2008
    DESCRIPTION 
        "Change default value of cadSysProcSnmpPacketRate from 100 to 650."
    REVISION "200808280000Z" -- Aug 28, 2008
    DESCRIPTION 
        "Add cadSysMaxUcdBurstLength."
    REVISION "200803170000Z" -- March 17, 2008
    DESCRIPTION 
        "Add oper mode bit for policy TLV and protocol throttling for IPV6."
    REVISION "200802190000Z" -- Feb 19, 2008
    DESCRIPTION 
        "Modified allowed values of cadSysReloadStatus."
    REVISION "200802040000Z" -- Feb 4, 2008
    DESCRIPTION 
        "Added cadSysDownChannelAnnex. Annex is configured per CMTS bassis."
    REVISION "200712020000Z" -- December 2, 2007
    DESCRIPTION 
        "Added additional reload support"
    REVISION "200611090000Z" -- November 9, 2006
    DESCRIPTION  
        "Add oneDCmDSMaxTrafBurstOn to operation mode."
    REVISION "200608290000Z" -- August 29, 2006
    DESCRIPTION
        "Add cadSysSourceInterfaceRemoteQuery to cadSysSourceInterface Object."
    REVISION "200608100000Z" -- August 10, 2006
    DESCRIPTION
        "Add bpiHybridOff to cadSysSpOperMode object."
    REVISION "200607120000Z"
    DESCRIPTION 
        "Added SNMP remote engine support."
    REVISION "200602220000Z"
    DESCRIPTION 
        "Removed cpeNacksForceCmReset bit from cadSysSpOperMode"
    REVISION "200601250000Z"
    DESCRIPTION 
        "Added upstreamLockupDetectLong BIT to cadSysSpOperMode for longer upstream lockup detect sampling period." 
    REVISION "200601120000Z"
    DESCRIPTION 
        "Added cadSysMtceParams for maintenance intervals and scheduling."
    REVISION "200601030000Z"
    DESCRIPTION 
        "Added cadSysCpeHostAuthorization for CPE Host Authorization (Motorola Style Anti-Spoofing) feature."
    REVISION "200509230000Z"
    DESCRIPTION 
        "Added cadSnmpSourceIp for Legal Intercept feature."
    REVISION "200509210000Z"
    DESCRIPTION 
        "Add support for suppressing downstream priority channel mapping
         add support for virtual modems."
    REVISION "200508300000Z"
    DESCRIPTION 
        "Add support for disabling downstream override and supressing DCDs."
    REVISION "200508240000Z"
    DESCRIPTION 
        "Added cadSysPeakTrafRateFor11CMs."
    REVISION "200508080000Z"
    DESCRIPTION 
        "Add support for DOCSIS 1.0+"
    REVISION "200507110000Z"
    DESCRIPTION 
        "Added cadCosDnPeakTrafficRate for Traffic Shaping for 2D12U feature."
    REVISION "200506200000Z"
    DESCRIPTION  
        "Renamed showCmFormatCV bit to showCmFormatCVOff and flipped the semantics"
    REVISION "200506080000Z"
    DESCRIPTION  
        "Added SCM Global counts"
    REVISION "200505180000Z"
    DESCRIPTION  
        "Added bpiDynamicMulticastOff bit to cadSysSpOperMode"
    REVISION "200504210000Z"
    DESCRIPTION  
        "Added showCmFormatCV bit to cadSysSpOperMode"
    REVISION "200504140000Z"
    DESCRIPTION 
        "Merge with 4.6"
    REVISION "200503010000Z"
    DESCRIPTION 
        "Remove obsolete error recovery bits"
    REVISION "200501060000Z"
    DESCRIPTION 
        "Included support for Source Interface for SNMP Traps."
    REVISION "200412030000Z"
    DESCRIPTION 
        "Included support for TFTP Enforce feature."
    REVISION "200410120000Z"
    DESCRIPTION 
        "Included support for SNMP policing on the FCM."
    REVISION "200409220000Z"
    DESCRIPTION 
        "Included cadSysTcpSmoothingValue1D8U and cadSysTcpSmoothingValue2D12U in the cadSysParamsGroup."
    REVISION "200404300000Z"
    DESCRIPTION 
        "Added IS-IS counts."
    REVISION "200404130000Z"
    DESCRIPTION 
        "Included cadSysRemoteFSEnable and cadSysRemotePortEnable in the cadSysParamsGroup."
    REVISION "200403230000Z"
    DESCRIPTION 
        "Added cadSysRemoteFSEnable and cadSysRemotePortEnable for allowing
         the active SCM to access filesystems and ports of the standby SCM."
    REVISION "200402230000Z"
    DESCRIPTION 
        "Added cadSysFlaplistPowerAdjustThreshold for FlapManager enhancement."
    REVISION "200402200000Z"
    DESCRIPTION 
        "Add automatic fan control switch to sysparams."
    REVISION "200312050000Z"
    DESCRIPTION 
        "Change default FCM other protocol policing rate for BGP."
    REVISION "200310280000Z"
    DESCRIPTION 
        "Removed mapgbdiff, mapgbsm1, mapgbsm2, ptcspec, and preeq10 from cadSysSpOperMode object."
    REVISION "200310210000Z"
    DESCRIPTION 
        "Changed cadCosToQosMapping scalar object to a table."
    REVISION "200310200000Z"
    DESCRIPTION 
        "Changed bootparams to rw."
    REVISION "200308260000Z"
    DESCRIPTION 
        "Added default maximum traffic burst for 1.1 CMs."
    REVISION "200308250000Z"
    DESCRIPTION 
        "Added percent additional downstream bandwidth allocated for dynamic service flows."
    REVISION "200308180000Z"
    DESCRIPTION 
        "Change default FCM policing default rates"
    REVISION "200308060000Z"
    DESCRIPTION  
        "Added upce bit to cadSysSpOperMode"
    REVISION "200306160000Z"
    DESCRIPTION  
        "Added cpeNacksForceCmReset bit to cadSysSpOperMode"
    REVISION "200305230000Z"
    DESCRIPTION 
        "Changed default of cadSysMaxQoSActiveTimeout from 0 to 30"
    REVISION "200305080000Z"
    DESCRIPTION 
        "Add server enable/disable support."
    REVISION "200304300000Z"
    DESCRIPTION 
        "Add both front panel addresses to bootparams."
    REVISION "200304200000Z"
    DESCRIPTION 
        "Changed maximum size of MIC authstring to 64 bytes."
    REVISION "200304140000Z"
    DESCRIPTION 
        "Added cmstatusoperational bit to cadSysSpOperMode object."
    REVISION "200303200000Z"
    DESCRIPTION 
        "Added ability to provision whether a CM in 1.0 can use concat and/or frag"
    REVISION "200303140000Z"
    DESCRIPTION 
        "Added maximum allowed QoS Active and Admitted Timeout values"
    REVISION "200303070000Z"
    DESCRIPTION  
        "Change length of MIC auth string"
    REVISION "200302140000Z"
    DESCRIPTION  
        "Added tables to support banner related objects.
         Change encoding of MIC auth string"
    REVISION "200212120000Z"
    DESCRIPTION  
        "Removed special operating mode for preeq."
    REVISION "200211220000Z"
    DESCRIPTION  
        "Added control object for erasing NVRAM."
    REVISION "200211200000Z"
    DESCRIPTION  
        "Add processor protocol policing objects."
    REVISION "200210040000Z"
    DESCRIPTION  
        "Added special operating mode for preeq."
    REVISION "200210030000Z"
    DESCRIPTION  
        "Changed cadCosUpMaxTrafficBurst from 1522 to 3044, per RFI-N-02091."
    REVISION "200207020000Z"
    DESCRIPTION  
        "Changed cadSysCMConfiguration to read-write."
    REVISION "200204250000Z"
    DESCRIPTION  
        "Add key chain objects."
    REVISION "200204230000Z"
    DESCRIPTION  
        "Add enbudptcpfltr bit to cadSysSpOperMode object."
    REVISION "200204220000Z"
    DESCRIPTION  
        "Add global counts collection rate object."
    REVISION "200204020001Z"
    DESCRIPTION  
        "Add cadSysSpOperMode object."
    REVISION "200204020000Z"
    DESCRIPTION  
        "Add cosToQosMapping group."
    REVISION "200201150000Z"
    DESCRIPTION  
        "Add configuration save time."
    REVISION "200111070000Z"
    DESCRIPTION  
        "Add floating IP address and remove NAM support."
    REVISION "200108180000Z"
    DESCRIPTION  
        "Add system table dictionary."
    REVISION "200107180000Z"
    DESCRIPTION  
        "Add enable/disable for Mcard ports."

    ::= { cadSystem 1 }

--=========== System Objects ==============================
cadSysParams  OBJECT IDENTIFIER ::= { cadSystemMib 1 }
cadSysSystem  OBJECT IDENTIFIER ::= { cadSystemMib 2 }
cadSysControl OBJECT IDENTIFIER ::= { cadSystemMib 3 }
cadSysSnmp    OBJECT IDENTIFIER ::= { cadSystemMib 4 }
cadSysBootParams    OBJECT IDENTIFIER ::= { cadSystemMib 5 }
cadSysReload  OBJECT IDENTIFIER ::= { cadSystemMib 6 }
cadSysImage   OBJECT IDENTIFIER ::= { cadSystemMib 7 }
cadSysDictionary   OBJECT IDENTIFIER ::= { cadSystemMib 8 }
cadSysConfiguration   OBJECT IDENTIFIER ::= { cadSystemMib 9 }
cadCosToQosMapping  OBJECT IDENTIFIER ::= { cadSystemMib 10 }
cadSysKeyChain   OBJECT IDENTIFIER ::= { cadSystemMib 11 }
cadSysProcPolicingConfig   OBJECT IDENTIFIER ::= { cadSystemMib 13 }
cadSysProcPolicingCounts   OBJECT IDENTIFIER ::= { cadSystemMib 14 }
cadSysBanner   OBJECT IDENTIFIER ::= { cadSystemMib 15 }
cadSysServer   OBJECT IDENTIFIER ::= { cadSystemMib 16 }
cadSysPatchParams  OBJECT IDENTIFIER ::= { cadSystemMib 17 }
cadSysMtceParams OBJECT IDENTIFIER ::= { cadSystemMib 19 }
cadSysDataServer OBJECT IDENTIFIER ::= { cadSystemMib 21 }
cadSysSourceAddress OBJECT IDENTIFIER ::= { cadSystemMib 22 }
cadSysLicenseControl OBJECT IDENTIFIER ::= { cadSystemMib 23 }
cadLaesMdTimestampMode OBJECT IDENTIFIER ::= { cadSystemMib 24 }
cadSysSharedSecret OBJECT IDENTIFIER ::= { cadSystemMib 25 }

--=========== Params Objects ==============================

cadSysSyncInterval OBJECT-TYPE
    SYNTAX  Integer32 (0..200)
    UNITS "Milliseconds"
    MAX-ACCESS  read-only
    STATUS  current
    DESCRIPTION
        "Nominal time between transmission of SYNC messages.  (ref 6.3.2)"
    ::= { cadSysParams 1 }

cadSysUCDInterval OBJECT-TYPE
    SYNTAX  Integer32 (0..2000)
    UNITS "Milliseconds"
    MAX-ACCESS  read-only
    STATUS  current
    DESCRIPTION
        "Time between transmission of UCD messages.  (ref 6.3.3)"
    ::= { cadSysParams 2 }

cadSysMaxMAPPending OBJECT-TYPE
    SYNTAX  Integer32 (0..4096)
    MAX-ACCESS  read-only
    STATUS  current
    DESCRIPTION
        "The number of mini-slots that a CMTS is allowed to map
         into the future.  (ref 6.3.4)"
    ::= { cadSysParams 3 }

cadSysRangingInterval OBJECT-TYPE
    SYNTAX  Integer32 (0..2000)
    UNITS "Milliseconds"
    MAX-ACCESS  read-only
    STATUS  current
    DESCRIPTION
        "Time between transmission of broadcast Ranging requests.  (ref 7.3.3)"
    ::= { cadSysParams 4 }

cadSysInvitedRangingRetries OBJECT-TYPE
    SYNTAX  Integer32 (16)
    MAX-ACCESS  read-only
    STATUS  current
    DESCRIPTION
        "Number of retries on inviting ranging requests.  (ref 9.2.4)"
    ::= { cadSysParams 5 }

cadSysRegistrationRequestRetries OBJECT-TYPE
    SYNTAX  Integer32 (3)
    MAX-ACCESS  read-only
    STATUS  current
    DESCRIPTION
        "Number of retries on registration requests/responses."
    ::= { cadSysParams 6 }

cadSysCMMAPProcessingTime OBJECT-TYPE
    SYNTAX  Integer32 (200..2000)
    UNITS "Microseconds"
    MAX-ACCESS  read-only
    STATUS  current
    DESCRIPTION
        "Time provided between arrival of the last bit of a MAP 
         at a CM and effectiveness of that MAP.  (ref 7.1.1)"
    ::= { cadSysParams 7 }

cadSysCMRangingResponseProcessingTime OBJECT-TYPE
    SYNTAX  Integer32 (1..200)
    UNITS "Milliseconds"
    MAX-ACCESS  read-only
    STATUS  current
    DESCRIPTION
        "Minimum tile allowed fro a CM following receipt of a rangin
         response before it is expected to reply to an invited ranging
         request."
    ::= { cadSysParams 8 }

cadSysCMConfiguration OBJECT-TYPE
    SYNTAX  Integer32 (30..2000)
    UNITS "Seconds"
    MAX-ACCESS  read-write
    STATUS  current
    DESCRIPTION
        "Maximum time allowed for a CM, following receipt of a 
         configuration file, to send a Registration Request to a CMTS."
    DEFVAL { 30 }
    ::= { cadSysParams 9 }

cadSysT5Timeout OBJECT-TYPE
    SYNTAX  Integer32 (0..2000)
    UNITS "Milliseconds"
    MAX-ACCESS  read-only
    STATUS  current
    DESCRIPTION
        "Wait for Upstream CHannel Change response."
    ::= { cadSysParams 10 }

cadSysT6Timeout OBJECT-TYPE
    SYNTAX  Integer32 (0..3000)
    UNITS "Milliseconds"
    MAX-ACCESS  read-only
    STATUS  current
    DESCRIPTION
      "Wait for REG-RSP and REG-ACK"
    ::= { cadSysParams 11 }

cadSysMiniSlotSize OBJECT-TYPE
    SYNTAX  Integer32 (32..300)
    MAX-ACCESS  read-only
    STATUS  current
    DESCRIPTION
        "Size of mini-slotfor upstream transmission.  Must be a 
         power of 2 (in units of the Timebase Tick)."
    ::= { cadSysParams 12 }

cadSysDSxRequestRetries OBJECT-TYPE
    SYNTAX  Integer32 (3)
    MAX-ACCESS  read-only
    STATUS  current
    DESCRIPTION
        "Number of Timeout Retries on DSA/DSC/DSD Requests."
    ::= { cadSysParams 13 }

cadSysDSxResponseRetries OBJECT-TYPE
    SYNTAX  Integer32 (3)
    MAX-ACCESS  read-only
    STATUS  current
    DESCRIPTION
        "Number of Timeout Retries on DSA/DSC/DSD Responses."
    ::= { cadSysParams 14 }

cadSysT7Timeout OBJECT-TYPE
    SYNTAX  Integer32 (0..1000)
    UNITS "Milliseconds"
    MAX-ACCESS  read-only
    STATUS  current
    DESCRIPTION
        "Wait for DSA/DSC/DSD Response timeout."
    ::= { cadSysParams 15 }

cadSysT8Timeout OBJECT-TYPE
    SYNTAX  Integer32 (0..300)
    UNITS "Milliseconds"
    MAX-ACCESS  read-only
    STATUS  current
    DESCRIPTION
        "Wait for DSA/DSC/DSD Acknowledge timeout."
    ::= { cadSysParams 16 }

cadSysT9Timeout OBJECT-TYPE
    SYNTAX  Integer32 (15..1500)
    UNITS "Minutes"
    MAX-ACCESS  read-only
    STATUS  current
    DESCRIPTION
        "Registration timeout, the time allowed between the CMTS
         sending a RNG-RSP(success) to a CM, and receiving a 
         REG-REQ from that same CM."
    ::= { cadSysParams 17 }

cadSysT10Timeout OBJECT-TYPE
    SYNTAX  Integer32 (0..3000)
    UNITS "Milliseconds"
    MAX-ACCESS  read-only
    STATUS  current
    DESCRIPTION
        "Wait for Transaction End timeout."
    ::= { cadSysParams 18 }

cadSysT11Timeout OBJECT-TYPE
    SYNTAX  Integer32 (0..300)
    UNITS "Milliseconds"
    MAX-ACCESS  read-only
    STATUS  current
    DESCRIPTION
        "Wait for a DCC Response on the old channel."
    ::= { cadSysParams 19 }

cadSysT13Timeout OBJECT-TYPE
    SYNTAX  Integer32 (0..1000)
    UNITS "Milliseconds"
    MAX-ACCESS  read-only
    STATUS  current
    DESCRIPTION
        "Maximum holding time for QOS resources for DCC."
    ::= { cadSysParams 20 }

cadSysDCCREQRetries OBJECT-TYPE
    SYNTAX  Integer32 (3)
    MAX-ACCESS  read-only
    STATUS  current
    DESCRIPTION
        "Number of retries on Dynamic Channel Change Request."
    ::= { cadSysParams 21 }

cadSysMICEnable OBJECT-TYPE
    SYNTAX  TruthValue
    MAX-ACCESS  read-write
    STATUS  current
    DESCRIPTION
        "Enable MIC checking on the CMTS."
    ::= { cadSysParams 22 }

cadSysMICAuthString OBJECT-TYPE
    SYNTAX  OCTET STRING (SIZE (0..64))
    MAX-ACCESS  read-write
    STATUS  current
    DESCRIPTION
        "Encrypted MIC Authentication"
    ::= { cadSysParams 23 }

cadSysAutoRecoveryEnable OBJECT-TYPE
    SYNTAX  TruthValue
    MAX-ACCESS  read-write
    STATUS  current
    DESCRIPTION
        "Enable automatic recovery of card/port/software in case
         of component failure."
    DEFVAL { true }
    ::= { cadSysParams 24 }

cadSysActiveIpAddress OBJECT-TYPE
    SYNTAX  IpAddress
    MAX-ACCESS  read-write
    STATUS  current
    DESCRIPTION
        "Ip Address of the active control complex."
    DEFVAL { '00000000'h }
    ::= { cadSysParams 25 }

cadSysSpOperMode OBJECT-TYPE
    SYNTAX BITS {
        dqossf10cms(0),
        adjrxpwrctl(1),
        enbudptcpfltr(2),
        upce(3),
        use16ForDSPeakTrafficRate(4),
        cpeNacksForceCmReset(5),
        loadBalUnbondedVoipOn(6),
        upDownTrapIfDescrOff(7),
        ofdmSparingCleanupOff(8),
        limitUsRngRspFreqOff(9),
        reserved10(10),
        cmstatusoperational(11),
        reserved12(12),
        docsis20test(13),
        reserved14(14),
        reserved15(15),
        reserved16(16),
        reserved17(17),
        reserved18(18),
        reserved19(19), 
        reserved20(20),
        showCmFormatCVOff(21),
        bpiDynamicMulticastOff(22),
        docsis10plusOff(23),
        downstreamOverrideOn(24),
        supressDCDOff(25),
        virtualCmOff(26),
        bpiHybridOff(27),
        oneDCmDSMaxTrafBurstOn(28),
        docsis30ReqTxPolicyChkOff(29),
        reserved30(30),
        reserved31(31)
    }
    MAX-ACCESS  read-write
    STATUS  current
    DESCRIPTION
        "Special operational mode.  Value of 1 indicates the mode is enabled.
         dqossf10cms - Allow 1.0 CMs to be stored in DocsQosServiceFlowEntry
         adjrxpwrctl - Allow rx power control to be adjusted by mod type usage
         enbudptcpfltr - Allow combining of Udp and Tcp messages in a single filter
         upce - Allow Upstream Packet Classifier Enforcement
         use16ForDSPeakTrafficRate - use the defunct TLV type 16 for DS peak traffic rate
         cpeNacksForceCmReset - - Force CM reset upon receiving 3 consecutive CPE NACKs
         loadBalUnbondedVoipOn - Allow load balancing for non-bonded voice calls
         limitUsRngRspFreqOff - Prevent CM from using an upstream frequency beyond 42 MHz
         upDownTrapIfDescrOff  - Allow linkup or linkdown trap to include ifDescr
         ofdmSparingCleanupOff - Allow automatically reset any D3.1 CMs in a cable-mac that
                                 has an OFDM channel on that DCAM in the CM's RCS after a 
                                 failover or fallback
         cmstatusoperational - Support DOCS-IF-MIB draft-05 (cw26)'s change to
         docsIfCmtsCmStatusValue, such that online modems take on a value of
         operational(8) at the CMTS. If disabled, operational(8) is not used and
         online modems take on a value of registrationComplete(6) at the CMTS.
         docsis20test - Allow running of DOCSIS 2.0 Tests.
         showCmFormatCVOff - show cable modem is formatted per CableVision's requirements if set to 0.
         docsis10plusOff - DOCSIS 1.0+ support is enabled if set to 0.
         downstreamOverrideOn - downstream overrides are disabled if this is set to 0.
         supressDCDOff - DCDs are suppressed if set to 0.
         virtualCmOff - support for virtual modems is enabled if set to 0.
         bpiHybridOff - Allow DOCSIS 1.1 modems to operate in BPI instead of BPI+ if this is set to 0.
         oneDCmDSMaxTrafBurstOn - Override Max Traffic Burst for DOCSIS 1.1 modems on a 1D CAM with E6000 setting if this is set to 0.
         docsis30ReqTxPolicyChkOff - Override DOCSIS 3.0 checking for Request/Transmission Policy TLV on upstream flows.
	 " 
    DEFVAL { { dqossf10cms, adjrxpwrctl, enbudptcpfltr, use16ForDSPeakTrafficRate, cpeNacksForceCmReset,
               loadBalUnbondedVoipOn, upDownTrapIfDescrOff, ofdmSparingCleanupOff, limitUsRngRspFreqOff, reserved10,
               cmstatusoperational, reserved12, reserved14,
               reserved15, reserved16, reserved17,
               reserved18, reserved19, reserved20, showCmFormatCVOff, bpiDynamicMulticastOff,
               docsis10plusOff, downstreamOverrideOn, supressDCDOff, virtualCmOff, bpiHybridOff,
               oneDCmDSMaxTrafBurstOn, docsis30ReqTxPolicyChkOff, reserved30, reserved31
           } } -- upce and docsis20test disabled and use16ForDSPeakTrafficRate by default
    ::= { cadSysParams 26 }
    
cadSysCountsCollectionRate OBJECT-TYPE
    SYNTAX  Unsigned32 (0|15..1440) -- disabled or from 15 minutes to 24 hours
    MAX-ACCESS read-write
    STATUS  current
    DESCRIPTION
        "The period, in minutes, in which every count in the CMTS
        is to be collected. If this object is set to 0, counts
        collection will be disabled."
    DEFVAL { 120 } -- 2 hours
    ::= { cadSysParams 27 }

cadSysMaxQoSActiveTimeout OBJECT-TYPE
    SYNTAX  Integer32 (0..65535)
    UNITS "seconds"
    MAX-ACCESS  read-write
    STATUS  current
    DESCRIPTION
        "Defines the maximum QoS Active Timeout the E6000 is willing to allow.  If
        a larger value is received in a CM request the E6000 will return this value
        instead in the response (Reference DOCSIS RFI Section c.2.2.5.6). Note a
        value of 0 is infinite and is therefore treated as the largest value in the
        range."
    DEFVAL { 30 }
    ::= { cadSysParams 28 }

cadSysMaxQoSAdmittedTimeout OBJECT-TYPE
    SYNTAX  Integer32 (0..65535)
    UNITS "seconds"
    MAX-ACCESS  read-write
    STATUS  current
    DESCRIPTION
        "Defines the maximum QoS Admitted Timeout the E6000 is willing to allow.  If
         a larger value is received in a CM request the E6000 will return this value
         instead in the response (Reference DOCSIS RFI Section c.2.2.5.7). Note a
         value of 0 is infinite and is therefore treated as the largest value in the
         range."
    DEFVAL { 200 }
    ::= { cadSysParams 29 }

cadSysAllow10CmConcatenation OBJECT-TYPE
    SYNTAX  TruthValue
    MAX-ACCESS  read-write
    STATUS  current
    DESCRIPTION
        "Defines whether or not the E6000 will allow a modem operating in DOCSIS 1.0
         mode to utilize concatenation.  If this value is false and a modem operating 
         in 1.0 mode sends up a modem capability indicating concatenation the E6000 will
         respond by turning that capability off.  If this value is true the modem will
         be returned whatever it requests (on or off)."
    DEFVAL { false }
    ::= { cadSysParams 30 }

cadSysAllow10CmFragmentation OBJECT-TYPE
    SYNTAX  TruthValue
    MAX-ACCESS  read-write
    STATUS  current
    DESCRIPTION
        "Defines whether or not the E6000 will allow a modem operating in DOCSIS 1.0
         mode to utilize fragmentation.  If this value is false and a modem operating 
         in 1.0 mode sends up a modem capability indicating fragmentation the E6000 will
         respond by turning that capability off.  If this value is true the modem will
         be returned whatever it requests (on or off)."
    DEFVAL { true }
    ::= { cadSysParams 31 }

cadSysPercentAddtlDsBwAllocated OBJECT-TYPE
    SYNTAX  Integer32 (0..5)
    MAX-ACCESS  read-write
    STATUS  current
    DESCRIPTION
        "This value of this setting is used to make a percentage increase to a dynamic
         downstream service flows maximum traffic rate.  This is flexiblity actually 
         causes the E6000 to operate outside the DOCSIS 1.1 specification by allocating and
         allowing more traffic than was actually requested.  The initial reason for 
         providing this capability is to mask problems produced in the Voice environment
         where devices have been seen to violate the traffic rates.  Examples of this are
         MTAs that overuse the QI bit for long durations thus overdriving the downstream
         burst interval and the Neura IPDT gateway introducing an additional 0.5% inband
         signaling to the DS voice flow"
    DEFVAL { 1 }
    ::= { cadSysParams 32 }

cadSysMaxTrafBurstFor11CMs OBJECT-TYPE
    SYNTAX  Integer32 (0..2147483647)
    MAX-ACCESS  read-write
    STATUS  current
    DESCRIPTION
        "This is the default value that will be used to populate the Maximum Traffic Burst
         for a 1.1 modem unless the maximum traffic burst TLV is explicitly provided in either
         the modems Request or in a Service Class Name definition.  This value is being made
         programmable for 2 reasons: 1) So that it can be set to the DOCSIS default of 3044 for
         CableLabs testing and 2) it can be tuned for real world applications."
    DEFVAL { 128000 }
    ::= { cadSysParams 33 }

cadSysFanSpeedControlEnable OBJECT-TYPE
    SYNTAX  TruthValue
    MAX-ACCESS  read-write
    STATUS  obsolete
    DESCRIPTION
    "Enable automatic fan speed control. "
    DEFVAL { false }
    ::= { cadSysParams 34 }

cadSysFlaplistPowerAdjustThreshold OBJECT-TYPE
    SYNTAX      TenthdB (0|10..100)
    UNITS       "dB"
    MAX-ACCESS  read-write
    STATUS      current
    DESCRIPTION
        "The threshold is used to monitor the power adjust in the flap 
         list. For a range request received that results in a power adjust
         exceeding the threshold value will cause the counter 
         cadIfCmtsCmCountsPowerAdjExceedsThreshold to be incremented.
         If the threshold is set to 0, the monitoring of power adjustment
         in the flap list is disabled."     
    DEFVAL { 30 }
    ::= { cadSysParams 35 }

cadSysRemoteFSEnable OBJECT-TYPE
    SYNTAX      TruthValue
    MAX-ACCESS  read-write
    STATUS      current
    DESCRIPTION
        "Indicates whether the active SCM should allow mounting the
         the filesystems of the standby SCM."
    DEFVAL { true }
    ::= { cadSysParams 36 }

cadSysRemotePortEnable OBJECT-TYPE
    SYNTAX      TruthValue
    MAX-ACCESS  read-write
    STATUS      current
    DESCRIPTION
        "Indicates whether the active SCM should allow redirection of
         the serial console of the standby SCM."
    DEFVAL { true }
    ::= { cadSysParams 37 }

cadSysTcpSmoothingValue1D8U OBJECT-TYPE
    SYNTAX      Unsigned32
    MAX-ACCESS  read-write
    STATUS      current
    DESCRIPTION
        "TCP smoothing value to be programmed into hardware on 1D8U CAMs."
    DEFVAL { 0 }
    ::= { cadSysParams 38 }

cadSysTcpSmoothingValue2D12U OBJECT-TYPE
    SYNTAX      Unsigned32
    MAX-ACCESS  read-write
    STATUS      current
    DESCRIPTION
        "TCP smoothing value to be programmed into hardware on 2D12U CAMs."
    DEFVAL { 0 }
    ::= { cadSysParams 39 }

cadSysModemLossThreshold OBJECT-TYPE
    SYNTAX      Unsigned32 (10..2000)
    MAX-ACCESS  read-write
    STATUS      deprecated
    DESCRIPTION
        "Minimum modem threshold triggering detection of an 
         upstream channel lockup."
    DEFVAL { 10 }
    ::= { cadSysParams 40 }

cadSysPeakTrafRateFor11CMs OBJECT-TYPE
    SYNTAX      BitRate
    MAX-ACCESS  read-write
    STATUS      obsolete 
    DESCRIPTION
        "This is the default value that will be used to populate the Peak Traffic Rate
         for a 1.1 modem configuration file unless the peak traffic rate is explicitly
         provided by a Service Class Name definition."
    DEFVAL { 0 }
    ::= { cadSysParams 41 }


cadSysCpeHostAuthorization OBJECT-TYPE
    SYNTAX      TruthValue
    MAX-ACCESS  read-write
    STATUS      current
    DESCRIPTION
        "This variable enables the CPE Host Authorization feature."
    DEFVAL { false }
    ::= { cadSysParams 44 }

cadSysMaxUcdBurstLength OBJECT-TYPE
    SYNTAX      Integer32(2048..16128)
    UNITS       "bytes"
    MAX-ACCESS  read-write
    STATUS      current
    DESCRIPTION
        "This variable limits the maximum UCD burst length."
    DEFVAL { 16128 }
    ::= { cadSysParams 46 }

cadSysLO1LeakDetect OBJECT-TYPE
    SYNTAX      TruthValue
    MAX-ACCESS  read-write
    STATUS      current
    DESCRIPTION
        "This variable controls LO1 leak detection on the DMM."
    DEFVAL { false }
    ::= { cadSysParams 47 }

cadMtcmConditionalOverride OBJECT-TYPE
    SYNTAX      TruthValue
    MAX-ACCESS  read-write
    STATUS      current
    DESCRIPTION
        "If set to 'true', for a MAC Domain configured for MTCM enabled operation, 
        the E6000 will set a registering MTCM-capable CM to be MTCM disabled (via REG-RSP message) 
        unless at least one of the config file's service flows was specifically configured 
        to have the Bonded bit set in the Required attribute mask 
        (in which case the CM will be set to MTCM enabled).
        If set to false, standard DOCSIS 3.0 operation will result."
    DEFVAL { false }
    ::= { cadSysParams 48 }

cadSysDelayedCpeLearning OBJECT-TYPE
    SYNTAX      TruthValue
    MAX-ACCESS  read-write
    STATUS      current
    DESCRIPTION
        "This setting only applies to modems that have BPI enabled.  
        When set to false(2), CPE learning is enabled during registration 
        when BPI initialization is initiated for those modems using BPI.  
        When set to true(1), CPE learning is delayed during registration 
        until BPI initialization is complete for those modems using BPI.  
        For modems not using BPI, CPE learning is enabled when registration is complete." 
    DEFVAL { true }
    ::= { cadSysParams 49 }

cadSysModPriDsInRccEnabled OBJECT-TYPE
    SYNTAX     TruthValue
    MAX-ACCESS read-write
    STATUS     current 
    DESCRIPTION 
        "Enable modifying primary Downstream channel in RCC of Reg-Rsp-MP.
         Refer ECN 690."
    DEFVAL { false }
    ::= { cadSysParams 52 }

cadSysSendTccRefIdPerFragment OBJECT-TYPE
    SYNTAX     TruthValue
    MAX-ACCESS read-write
    STATUS     current 
    DESCRIPTION 
        "Settings for sending the Transmit Channel Configuration (TCC) Reference sub-type 46.1 for type 46 TCC fragmentation.
         If 'true', sends 46.1 Ref ID in every type 46 TCC fragment;
         If 'false', only sends 46.1 Ref ID in the first TCC fragment (DOCSIS Compliant)."
    DEFVAL { true }
    ::= { cadSysParams 53 }

cadSysPeakTrRateUpstream OBJECT-TYPE
    SYNTAX     TruthValue
    MAX-ACCESS read-write
    STATUS     current 
    DESCRIPTION 
        "This object enables support for Peak Traffic Rate in the upstream direction."
    DEFVAL { false }
    ::= { cadSysParams 54 }

cadSysAllowAmbiguityOverride OBJECT-TYPE
    SYNTAX     TruthValue
    MAX-ACCESS read-write
    STATUS     current 
    DESCRIPTION 
        "This object enables ambiguity resolution channel-override actions."
    DEFVAL { false }
    ::= { cadSysParams 55 }

cadSysUnicastNpUsAcquisition OBJECT-TYPE
    SYNTAX     TruthValue
    MAX-ACCESS read-write
    STATUS     current 
    DESCRIPTION 
        "This object enables unicast non-primary upstream channel acquisition."
    DEFVAL { false }  
    ::= { cadSysParams 56}

cadSysMacMoveBlockedOnRcptDhcpPkt OBJECT-TYPE
    SYNTAX TruthValue
    MAX-ACCESS read-write
    STATUS     current
    DESCRIPTION 
        "MAC movement is blocked on receipt of DHCP packets"
    DEFVAL { true }    
    ::= { cadSysParams 57 }

cadSysTftpProxy           OBJECT-TYPE
    SYNTAX      INTEGER {
         disable(0),
         enable(1),
         ipv4only(2),
         ipv6only(3)
        }
    MAX-ACCESS  read-write
    STATUS      current
    DESCRIPTION
        "This parameter provides a global enable for the TFTP
         Enforce and Dynamic Shared Secret features. In order for
         the cadIfMacDomainTftpEnforce and cadIfMacDomainDynamicSecret
         parameters to take effect, this parameter must also be enabled.
         This parameter can also limit those features to only IPv4
         transfers or IPv6 transfers."
    DEFVAL { enable }
    ::= { cadSysParams 58 }

cadSysFanSpeedLevel OBJECT-TYPE
    SYNTAX  Integer32(0..255)
    MAX-ACCESS  read-write
    STATUS  current
    DESCRIPTION
        "Set the fan speed for the chassis."
    DEFVAL { 0 }
    ::= { cadSysParams 59 }

cadSys1x1onCmAcPwrLossEnabled OBJECT-TYPE
    SYNTAX     TruthValue
    MAX-ACCESS read-write
    STATUS     current 
    DESCRIPTION 
        "This object enables/disables the CMTS reaction to a AC Power Loss CM-STATUS.
         If true, the CMTS will wait until cadSys1x1onCmAcPwrLossHoldoff expires, and then 
         the CMTS will place the CM into a 1x1 (US/DS) channel mode to conserve CM battery power.
         If false, the CMTS will not place a CM that reports an AC Power Loss into 1x1 mode."
    DEFVAL { false }  
    ::= { cadSysParams 60 }

cadSysFlapListInsertionThreshold OBJECT-TYPE
    SYNTAX     Integer32 (60..86400)
    UNITS      "seconds"
    MAX-ACCESS read-write
    STATUS     current 
    DESCRIPTION 
        "This object shows the number of seconds between successive ranging 
         attempts that must pass before the modem is counted as flapped.
         The modem must have also been in a provisioning or registered state
         before the ranging request."
    DEFVAL { 180 }  
    ::= { cadSysParams 61 }

cadSysAES128Enable OBJECT-TYPE
    SYNTAX  TruthValue
    MAX-ACCESS  read-write
    STATUS  current
    DESCRIPTION
        "Enables AES-128 Cryptography Suite for BPI+ when true."
    DEFVAL { false }
    ::= { cadSysParams 62 }

--=========== System Objects ==============================
cadSysContact OBJECT-TYPE
    SYNTAX      DisplayString (SIZE (0..255))
    MAX-ACCESS  read-only
    STATUS      current
    DESCRIPTION
        "The textual identification of the contact person for this
         managed node, together with information on how to contact
         this person.  If no contact information is known, the value
         is the zero-length string."
    DEFVAL { "support@arris.com" }
    ::= { cadSysSystem 1 }

cadSysName OBJECT-TYPE
    SYNTAX      DisplayString (SIZE (0..255))
    MAX-ACCESS  read-only
    STATUS      current
    DESCRIPTION
        "An administratively-assigned name for this managed node.
         By convention, this is the node's fully-qualified domain
         name.  If the name is unknown, the value is the zero-length
         string."
    ::= { cadSysSystem 2 }

cadSysLocation OBJECT-TYPE
    SYNTAX      DisplayString (SIZE (0..255))
    MAX-ACCESS  read-only
    STATUS      current
    DESCRIPTION
        "The physical location of this node (e.g., `telephone
         closet, 3rd floor').  If the location is unknown, the value
         is the zero-length string."
    DEFVAL { "" }
    ::= { cadSysSystem 3 }

--=========== Control Objects =============================

cadSysWriteMem OBJECT-TYPE
    SYNTAX  TruthValue
    MAX-ACCESS  read-write
    STATUS  current
    DESCRIPTION
        "This variable always returns FALSE upon reading. When
         set to TRUE, the configuration data currently resident
         in volatile memory (RAM) is written to persistent memory (NVRAM)."
    DEFVAL { false }
    ::= { cadSysControl 1 }

cadSysEraseMem OBJECT-TYPE
    SYNTAX  TruthValue
    MAX-ACCESS  read-write
    STATUS  current
    DESCRIPTION
        "This variable always returns FALSE upon reading. When
         set to TRUE, the configuration data currently resident
         in persistent memory (NVRAM) is erased."
    DEFVAL { false }
    ::= { cadSysControl 2 }

--=========== SNMP Objects =============================

cadSysEnableAuthenTraps OBJECT-TYPE
    SYNTAX      INTEGER  { enable(1), disabled(2) }
    MAX-ACCESS  read-write
    STATUS      current
    DESCRIPTION
        "Indicates whether the SNMP entity is permitted to generate 
         authentication traps."
    ::= { cadSysSnmp 1 }

cadSysSnmpReadAheadMax OBJECT-TYPE
    SYNTAX     Unsigned32 (0..20)
    MAX-ACCESS read-write
    STATUS     current
    DESCRIPTION
        "This value is the maximum number of records to read ahead"
    DEFVAL { 0 }
    ::= { cadSysSnmp 2 }

cadSysSnmpRefreshTime OBJECT-TYPE
    SYNTAX     Unsigned32 (0..1200)
    UNITS      "seconds"
    MAX-ACCESS read-write
    STATUS     current
    DESCRIPTION
        "This value represents how old a database record can be to be used."
    DEFVAL { 0 }
    ::= { cadSysSnmp 3 }

cadSnmpRemoteEngineTable OBJECT-TYPE
    SYNTAX  SEQUENCE OF CadSnmpRemoteEngineEntry
    MAX-ACCESS not-accessible
    STATUS deprecated
    DESCRIPTION
        "Table containing information of remote SNMP engines."
    ::= { cadSysSnmp 4 }

cadSnmpRemoteEngineEntry OBJECT-TYPE
    SYNTAX CadSnmpRemoteEngineEntry
    MAX-ACCESS not-accessible
    STATUS current
    DESCRIPTION
        "Entry containing information of remote SNMP engines."
    INDEX { cadSnmpRemoteEngineIpAddress, cadSnmpRemoteEnginePortNumber }
    ::= { cadSnmpRemoteEngineTable 1 }

CadSnmpRemoteEngineEntry ::= SEQUENCE {
    cadSnmpRemoteEngineIpAddress  IpAddress,
    cadSnmpRemoteEnginePortNumber Integer32,
    cadSnmpRemoteEngineID         SnmpEngineID,
    cadSnmpRemoteUserName         SnmpAdminString,
    cadSnmpRemoteEngineType       INTEGER,
    cadSnmpRemoteEngineStatus     RowStatus
}

cadSnmpRemoteEngineIpAddress OBJECT-TYPE
    SYNTAX IpAddress
    MAX-ACCESS not-accessible
    STATUS current
    DESCRIPTION 
        "The IP address of a remote SNMP engine with which this user can communicate."
    ::= { cadSnmpRemoteEngineEntry 1 }

cadSnmpRemoteEnginePortNumber OBJECT-TYPE
    SYNTAX Integer32 (0..65535)
    MAX-ACCESS not-accessible
    STATUS current
    DESCRIPTION 
        "The UDP port of a remote SNMP engine with which this user can communicate."
    ::= { cadSnmpRemoteEngineEntry 2 }

cadSnmpRemoteEngineID OBJECT-TYPE
    SYNTAX SnmpEngineID
    MAX-ACCESS read-create
    STATUS deprecated
    DESCRIPTION 
        "An SNMP engine's administratively-unique identifier of a remote 
         SNMP engine with which this user can communicate."
    ::= { cadSnmpRemoteEngineEntry 3 }

cadSnmpRemoteUserName OBJECT-TYPE
    SYNTAX SnmpAdminString (SIZE(1..32))
    MAX-ACCESS read-create
    STATUS current
    DESCRIPTION 
        "A human readable string representing the name of the user of a remote 
         SNMP engine."
    ::= { cadSnmpRemoteEngineEntry 4 }

cadSnmpRemoteEngineType OBJECT-TYPE
    SYNTAX INTEGER {
        manual (1),
        auto (2)
    }
    MAX-ACCESS  read-only
    STATUS current
    DESCRIPTION 
        "The type to indicate the remote engineID is manually configured or 
         internally detected via SNMP V3 Informs probe response."
    DEFVAL { manual }
    ::= { cadSnmpRemoteEngineEntry 5 }

cadSnmpRemoteEngineStatus OBJECT-TYPE
    SYNTAX RowStatus
    MAX-ACCESS read-create
    STATUS current
    DESCRIPTION 
        "The status of this conceptual row." 
    ::= { cadSnmpRemoteEngineEntry 6 }

--=========== Boot Param Objects =============================

cadSysBootMacAddress OBJECT-TYPE
    SYNTAX      MacAddress
    MAX-ACCESS  read-only
    STATUS      current
    DESCRIPTION 
        " Mac address of system controller "
    ::= { cadSysBootParams 1 }

cadSysBootFpIpAddress OBJECT-TYPE
    SYNTAX      IpAddress
    MAX-ACCESS  read-write
    STATUS      current
    DESCRIPTION 
        " Ip address of E6000 front panel ethernet port "
    ::= { cadSysBootParams 2 }

cadSysBootFpSubnetMask OBJECT-TYPE
    SYNTAX      IpAddress
    MAX-ACCESS  read-write
    STATUS      current
    DESCRIPTION 
        " E6000 front port interface subnet mask "
    ::= { cadSysBootParams 3 }

cadSysBootDefaultGateway OBJECT-TYPE
    SYNTAX      IpAddress
    MAX-ACCESS  read-write
    STATUS      current
    DESCRIPTION 
        " Default gateway "
    ::= { cadSysBootParams 6 }

cadSysBootTimeOffset OBJECT-TYPE
    SYNTAX      Integer32
    MAX-ACCESS  read-only
    STATUS      current
    DESCRIPTION 
        " Time offset (seconds) from UTC "
    ::= { cadSysBootParams 7 }

cadSysBootTimeServer OBJECT-TYPE
    SYNTAX      IpAddress
    MAX-ACCESS  read-only
    STATUS      current
    DESCRIPTION 
        " Ip address of TOD server "
    ::= { cadSysBootParams 8 }

cadSysBootTimeServerConnType OBJECT-TYPE
    SYNTAX INTEGER {
        tcp(1),
        udp(2),
        none(3)
    }
    MAX-ACCESS  read-only
    STATUS      current
    DESCRIPTION 
        " Protocol (tcp/udp) used to connect to TOD server "
    DEFVAL { udp }
    ::= { cadSysBootParams 9 }

cadSysBootStartupApplication OBJECT-TYPE
    SYNTAX INTEGER {
        bootprobe(1),
        bootapplication(4)
    }
    MAX-ACCESS  read-only
    STATUS      current
    DESCRIPTION 
        " Startup mode of the E6000 "
    DEFVAL { bootapplication }
    ::= { cadSysBootParams 10 }

cadSysBootStartupDelay OBJECT-TYPE
    SYNTAX      Integer32 (1..60)
    MAX-ACCESS  read-only
    STATUS      current
    DESCRIPTION 
        " Delay (in seconds) allowing changes before booting application "
    DEFVAL { 1 }
    ::= { cadSysBootParams 11 }

cadSysBootSelection OBJECT-TYPE
    SYNTAX      Integer32 (1..2)
    MAX-ACCESS  read-only
    STATUS      current
    DESCRIPTION 
        " Bootloader to use (1 or 2) "
    DEFVAL { 1 }
    ::= { cadSysBootParams 12 }

cadSysBootBaud OBJECT-TYPE
    SYNTAX      Integer32
    MAX-ACCESS  read-only
    STATUS      deprecated
    DESCRIPTION 
        " Baud rate of front panel serial port "
    DEFVAL { 9600 }
    ::= { cadSysBootParams 13 }

cadSysBootFpBIpAddress OBJECT-TYPE
    SYNTAX      IpAddress
    MAX-ACCESS  read-write
    STATUS      current
    DESCRIPTION 
        " Ip address of E6000 side B front panel ethernet port "
    ::= { cadSysBootParams 15 }

cadSysBootParity OBJECT-TYPE
    SYNTAX      OCTET STRING (SIZE(1))
    MAX-ACCESS  read-only
    STATUS      current
    DESCRIPTION 
        "Serial parity of console port.  Valid values are N (no parity),
         E (even parity), and O (odd parity)."
    DEFVAL { "N" }
    ::= { cadSysBootParams 16 }

--=========== Reload Control Objects =============================

cadSysReloadOperation OBJECT-TYPE
    SYNTAX      INTEGER {
        reloadImage(1),
        reloadCommit(2),
        reloadActive(3),
        reloadHitless(4),
        reloadWritemem(5),
        reloadErasemem(6),
        reloadPatchInstall(7),
        reloadPatchRemove(8),
        reloadPatchApply(9),
        none(99)
    }
    MAX-ACCESS  read-write
    STATUS      current
    DESCRIPTION 
        " Control object for E6000 reload, reading this object always returns none(99) "
    DEFVAL { none }
    ::= { cadSysReload 1 }

cadSysReloadImageName OBJECT-TYPE
    SYNTAX      DisplayString
    MAX-ACCESS  read-write
    STATUS      current
    DESCRIPTION 
        " Image name to use in reloadImage operation "
    DEFVAL { "" }
    ::= { cadSysReload 2 }

cadSysReloadStatus OBJECT-TYPE
    SYNTAX  BITS {
        idle(0),
        inProgress(1),
        localCheckImage(2),
        localCommit(3),
        remoteCommit(4),
        remoteCopyImage(5),
        remoteCheckImage(6),
        patchInstall(7),
        localReboot(8),
        patchRemove(9),
        remoteFirmwareUpdate(10),
        firmwareUpdate(11),
        waitStandby(12),
        remotePatchInstall(13),
        writeMem(14),
        bundling(15),
        unbundling(16),
        complete(17),
        abort(18),
        remotePatchRemove(19),
        remoteWriteMem(20),
        eraseMem(21),
        remoteEraseMem(22),
        preloadCams(23),
        localInstallImage(24),
        remoteInstallImage(25),
        localPreloadRsm(26),
        remotePreloadRsm(27),
        remoteCommitRsm(28),
        copyImage(29),
        remoteFirmwareUpdateRsm(30),
        patchApplyCheck(31),
        waitSoftswitch(32),
        waitSpareCamsReset(33),
        waitCamsReset(34)
    }
    MAX-ACCESS  read-only
    STATUS      current
    DESCRIPTION 
        " Status object for E6000 reload "
    DEFVAL { { idle } }
    ::= { cadSysReload 3 }

cadSysReloadStatusDescription OBJECT-TYPE
    SYNTAX      DisplayString
    MAX-ACCESS  read-write
    STATUS      current
    DESCRIPTION 
        " Textual description of reload status "
    DEFVAL { "" }
    ::= { cadSysReload 4 }

cadSysReloadPatchName OBJECT-TYPE
    SYNTAX      DisplayString
    MAX-ACCESS  read-write
    STATUS      current
    DESCRIPTION 
        " Patch image name to use in patch operations "
    DEFVAL { "" }
    ::= { cadSysReload 5 }

--=========== Image Status Objects =============================

cadSysImageFile OBJECT-TYPE
    SYNTAX      DisplayString
    MAX-ACCESS  read-only
    STATUS      current
    DESCRIPTION 
        " Image filename for current E6000 image "
    ::= { cadSysImage 1 }

cadSysImageId OBJECT-TYPE
    SYNTAX      Integer32
    MAX-ACCESS  read-only
    STATUS      current
    DESCRIPTION 
        " Image identifier for current E6000 image "
    ::= { cadSysImage 2 }

cadSysImageName OBJECT-TYPE
    SYNTAX      DisplayString
    MAX-ACCESS  read-only
    STATUS      current
    DESCRIPTION 
        " Image name for current E6000 image "
    ::= { cadSysImage 3 }

cadSysImageComponentCount OBJECT-TYPE
    SYNTAX      Integer32
    MAX-ACCESS  read-only
    STATUS      current
    DESCRIPTION 
        " Image component count for current E6000 image "
    ::= { cadSysImage 4 }

--=========== Dictionary Objects =============================

cadSysDictionaryTable OBJECT-TYPE
    SYNTAX  SEQUENCE OF CadSysDictionaryEntry
    MAX-ACCESS not-accessible
    STATUS current
    DESCRIPTION
        " Table describing internal state of database. "
    ::= { cadSysDictionary 1 }

cadSysDictionaryEntry OBJECT-TYPE
    SYNTAX CadSysDictionaryEntry
    MAX-ACCESS not-accessible
    STATUS current
    DESCRIPTION
        " Describes the internal state of an individual table. "
    INDEX { cadSysDictionaryTableId }
    ::= { cadSysDictionaryTable 1 }

CadSysDictionaryEntry ::= SEQUENCE {
    cadSysDictionaryTableId         Unsigned32,
    cadSysDictionaryName            DisplayString,
    cadSysDictionaryDynamic         TruthValue,
    cadSysDictionaryNumberEntries   Integer32,
    cadSysDictionaryCurrentVer      Unsigned32,
    cadSysDictionaryPersistentVer   Unsigned32,
    cadSysDictionaryModuleVer       Unsigned32
}

cadSysDictionaryTableId OBJECT-TYPE
    SYNTAX Unsigned32
    MAX-ACCESS not-accessible
    STATUS current
    DESCRIPTION 
        "Internal identifier for this MIB data."
    ::= { cadSysDictionaryEntry 1 }

cadSysDictionaryName OBJECT-TYPE
    SYNTAX DisplayString
    MAX-ACCESS read-only
    STATUS current
    DESCRIPTION 
        "Internal name for this MIB data."
    ::= { cadSysDictionaryEntry 2 }

cadSysDictionaryDynamic OBJECT-TYPE
    SYNTAX TruthValue
    MAX-ACCESS read-only
    STATUS current
    DESCRIPTION 
        "Indicates whether table is persistent or volatile only."
    ::= { cadSysDictionaryEntry 3 }

cadSysDictionaryNumberEntries OBJECT-TYPE
    SYNTAX Integer32
    MAX-ACCESS read-only
    STATUS current
    DESCRIPTION 
        "Current number of rows contained in the MIB table."
    ::= { cadSysDictionaryEntry 4 }

cadSysDictionaryCurrentVer OBJECT-TYPE
    SYNTAX Unsigned32
    MAX-ACCESS read-only
    STATUS current
    DESCRIPTION 
        "Current internal dynamic version number of the MIB table."
    ::= { cadSysDictionaryEntry 5 }

cadSysDictionaryPersistentVer OBJECT-TYPE
    SYNTAX Unsigned32
    MAX-ACCESS read-only
    STATUS current
    DESCRIPTION 
        "Current internal version number of the MIB table on flash."
    ::= { cadSysDictionaryEntry 6 }

cadSysDictionaryModuleVer OBJECT-TYPE
    SYNTAX Unsigned32
    MAX-ACCESS read-only
    STATUS current
    DESCRIPTION 
        "Current internal version number of the schema of the MIB table."
    ::= { cadSysDictionaryEntry 7 }

--=========== Configuration Objects =============================

cadSysConfigSaveTime OBJECT-TYPE
    SYNTAX      DateAndTime
    MAX-ACCESS  read-only
    STATUS      current
    DESCRIPTION 
        " The date and time of the last write of the configuration to nvram. "
    ::= { cadSysConfiguration 1 }

--== Class of Service to Quality of Service Mapping Objects ====
--
-- These cadCostoQosMapping objects only apply to 1.0 flows.
-- To configure 1.1 flows, the objects in the docsQosParamSetTable
-- should be used.
--

cadCosToQosMappingTable OBJECT-TYPE
    SYNTAX      SEQUENCE OF CadCosToQosMappingEntry
    MAX-ACCESS  not-accessible
    STATUS      current
    DESCRIPTION 
        "Table of COS to QOS Mapping data"
    ::= { cadCosToQosMapping 9 }

cadCosToQosMappingEntry OBJECT-TYPE
    SYNTAX          CadCosToQosMappingEntry
    MAX-ACCESS      not-accessible
    STATUS          current
    DESCRIPTION     "This entry contains all of the data to map
                     1.0 COS to 1.1 QOS parameters."
    INDEX { cadCosToQosMappingIndex }
    ::= { cadCosToQosMappingTable 1 }

CadCosToQosMappingEntry ::= SEQUENCE {
    cadCosToQosMappingIndex     Integer32,
    cadCosUpMaxTrafficBurst     Unsigned32,
    cadCosDnMaxTrafficBurst     Unsigned32,
    cadCosDnMinReservedRate     BitRate,
    cadCosUpMinReservedPkt      Integer32,
    cadCosDnMinReservedPkt      Integer32,
    cadCosUpTosAndMask          OCTET STRING,
    cadCosUpTosOrMask           OCTET STRING,
    cadCosDnMaxLatency          Unsigned32,
    cadCosDnPriority            Integer32,
    cadCosDnPeakTrafficRate     BitRate,
    cadCosUpPeakTrafficRate     BitRate
}

cadCosToQosMappingIndex OBJECT-TYPE
    SYNTAX      Integer32 (1..16)
    MAX-ACCESS  not-accessible
    STATUS      current
    DESCRIPTION 
        "The upstream 1.0 equivalent of the (1.1) DOCS-QOS3-MIB
         object docsQosParamSetMaxTrafficBurst"
    ::= { cadCosToQosMappingEntry 1 }

cadCosUpMaxTrafficBurst OBJECT-TYPE
    SYNTAX      Unsigned32
    MAX-ACCESS  read-write
    STATUS      current
    DESCRIPTION 
        "The upstream 1.0 equivalent of the (1.1) DOCS-QOS3-MIB
         object docsQosParamSetMaxTrafficBurst"
    DEFVAL { 3044 }
    ::= { cadCosToQosMappingEntry 2 }

cadCosDnMaxTrafficBurst OBJECT-TYPE
    SYNTAX      Unsigned32
    MAX-ACCESS  read-write
    STATUS      current
    DESCRIPTION 
        "The downstream 1.0 equivalent of the (1.1) DOCS-QOS3-MIB
         object docsQosParamSetMaxTrafficBurst"
    DEFVAL { 96000 }
    ::= { cadCosToQosMappingEntry 3 }

cadCosDnMinReservedRate OBJECT-TYPE
    SYNTAX      BitRate
    MAX-ACCESS  read-write
    STATUS      current
    DESCRIPTION 
        "The downstream 1.0 equivalent of the (1.1) DOCS-QOS3-MIB
         object docsQosParamSetMinReservedRate"
    DEFVAL { 0 }
    ::= { cadCosToQosMappingEntry 4 }

cadCosUpMinReservedPkt OBJECT-TYPE
    SYNTAX      Integer32 (0..65535)
    MAX-ACCESS  read-write
    STATUS      current
    DESCRIPTION 
        "The upstream 1.0 equivalent of the (1.1) DOCS-QOS3-MIB
         object docsQosParamSetMinReservedPkt"
    DEFVAL { 0 }
    ::= { cadCosToQosMappingEntry 5 }

cadCosDnMinReservedPkt OBJECT-TYPE
    SYNTAX      Integer32 (0..65535)
    MAX-ACCESS  read-write
    STATUS      current
    DESCRIPTION 
        "The downstream 1.0 equivalent of the (1.1) DOCS-QOS3-MIB
         object docsQosParamSetMinReservedPkt"
    DEFVAL { 0 }
    ::= { cadCosToQosMappingEntry 6 }

cadCosUpTosAndMask OBJECT-TYPE
    SYNTAX      OCTET STRING (SIZE(1))
    MAX-ACCESS  read-write
    STATUS      current
    DESCRIPTION 
        "The upstream 1.0 equivalent of the (1.1) DOCS-QOS3-MIB
         object docsQosParamSetTosAndMask"
    DEFVAL { 'ff'h }
    ::= { cadCosToQosMappingEntry 7 }

cadCosUpTosOrMask OBJECT-TYPE
    SYNTAX      OCTET STRING (SIZE(1))
    MAX-ACCESS  read-write
    STATUS      current
    DESCRIPTION 
        "The upstream 1.0 equivalent of the (1.1) DOCS-QOS3-MIB
         object docsQosParamSetTosOrMask"
    DEFVAL { '00'h }
    ::= { cadCosToQosMappingEntry 8 }

cadCosDnMaxLatency OBJECT-TYPE
    SYNTAX      Unsigned32
    MAX-ACCESS  read-write
    STATUS      current
    DESCRIPTION 
        "The upstream 1.0 equivalent of the (1.1) DOCS-QOS3-MIB
         object docsQosParamSetMaxLatency"
    DEFVAL { 0 }
    ::= { cadCosToQosMappingEntry 9 }

cadCosDnPriority OBJECT-TYPE
    SYNTAX      Integer32 (-1|0..7)
    MAX-ACCESS  read-write
    STATUS      current
    DESCRIPTION "The downstream channel priority to use. A -1 indicates
                 that the current method of using the upstream channel
         priority should be used."
    DEFVAL { -1 }
    ::= { cadCosToQosMappingEntry 10 }

cadCosDnPeakTrafficRate OBJECT-TYPE
    SYNTAX          BitRate
    MAX-ACCESS      read-write
    STATUS          current
    DESCRIPTION    
        "Peak traffic rate shaped to while traffic still conforms to
         the policing parameters (Tmax and Burst).  If the peak rate is set to a
         value greater than Tmax, then the traffic will  be shaped to the peak
         rate until the traffic is non-conforming to the policing parameters,
         and then the traffic will be shaped to the Tmax rate. If the peak rate
         is less than the Tmax for a flow, then all traffic for that flow will shaped
         to the Tmax rate.  Setting the peak rate to a value of 0 will result in all
         flows being limited to Tmax at all times. Setting the peak rate to a
         value of 0xffffffff will result in flows having virtually unlimited
         bandwidth until their burst size is used up. This parameter only has
         meaning for flows on downstreams that are shaped."
    DEFVAL { 0 }
    ::= { cadCosToQosMappingEntry 11 }

cadCosUpPeakTrafficRate OBJECT-TYPE
    SYNTAX          BitRate
    MAX-ACCESS      read-write
    STATUS          current
    DESCRIPTION    
        "Peak traffic rate shaped to while traffic still conforms to
         the policing parameters (Tmax and Burst).  If the peak rate is set to a
         value greater than Tmax, then the traffic will be shaped to the peak
         rate until the traffic is non-conforming to the policing parameters,
         and then the traffic will be shaped to the Tmax rate. If the peak rate
         is less than the Tmax for a flow, then all traffic for that flow will shaped
         to the Tmax rate.  Setting the peak rate to a value of 0 will result in all
         flows being limited to Tmax at all times. Setting the peak rate to a
         value of 0xffffffff will result in flows having virtually unlimited
         bandwidth until their burst size is used up. This parameter only has
         meaning for upstream flows."
    DEFVAL { 0 }
    ::= { cadCosToQosMappingEntry 12 }



--=========== Key Chain Objects =============================

cadSysKeyChainKeyTable OBJECT-TYPE
    SYNTAX  SEQUENCE OF CadSysKeyChainKeyEntry
    MAX-ACCESS not-accessible
    STATUS current
    DESCRIPTION
        " Table describing key-chain key provisioned data. "
    ::= { cadSysKeyChain 1 }

cadSysKeyChainKeyEntry OBJECT-TYPE
    SYNTAX CadSysKeyChainKeyEntry
    MAX-ACCESS not-accessible
    STATUS current
    DESCRIPTION
        " Describes the provisioned data for a key in a key-chain. "
    INDEX { cadSysKeyChainName, cadSysKeyChainKeySequenceId }
    ::= { cadSysKeyChainKeyTable 1 }

CadSysKeyChainKeyEntry ::= SEQUENCE {
    cadSysKeyChainName                              OCTET STRING,
    cadSysKeyChainKeySequenceId                     Unsigned32,
    cadSysKeyChainKey                               OCTET STRING,
    cadSysKeyChainKeyAcceptStartTime                DateAndTime,
    cadSysKeyChainKeyAcceptStopTime                 DateAndTime,
    cadSysKeyChainKeyAcceptInfiniteLifetime         TruthValue,
    cadSysKeyChainKeySendStartTime                  DateAndTime,
    cadSysKeyChainKeySendStopTime                   DateAndTime,
    cadSysKeyChainKeySendInfiniteLifetime           TruthValue,
    cadSysKeyChainKeyRowStatus                      RowStatus
}

cadSysKeyChainName OBJECT-TYPE
    SYNTAX OCTET STRING (SIZE(1..16))
    MAX-ACCESS not-accessible
    STATUS current
    DESCRIPTION
        "The key-chain name."
    ::= { cadSysKeyChainKeyEntry 1 }

cadSysKeyChainKeySequenceId OBJECT-TYPE
    SYNTAX Unsigned32 (0..255)
    MAX-ACCESS not-accessible
    STATUS current
    DESCRIPTION
        "The sequence id of the key."
    ::= { cadSysKeyChainKeyEntry 2 }

cadSysKeyChainKey OBJECT-TYPE
    SYNTAX OCTET STRING (SIZE(0..16))
    MAX-ACCESS read-create
    STATUS current
    DESCRIPTION
        "The key string."
    ::= { cadSysKeyChainKeyEntry 3 }

cadSysKeyChainKeyAcceptStartTime OBJECT-TYPE
    SYNTAX DateAndTime
    MAX-ACCESS read-create
    STATUS current
    DESCRIPTION
        "The start time when this key is valid for received packets."
    ::= { cadSysKeyChainKeyEntry 4 }

cadSysKeyChainKeyAcceptStopTime OBJECT-TYPE
    SYNTAX DateAndTime
    MAX-ACCESS read-create
    STATUS current
    DESCRIPTION
        "The stop time when this key is no longer valid for received packets."
    ::= { cadSysKeyChainKeyEntry 5 }

cadSysKeyChainKeyAcceptInfiniteLifetime OBJECT-TYPE
    SYNTAX TruthValue
    MAX-ACCESS read-create
    STATUS current
    DESCRIPTION
        "If this value is set to true, the key has an infinite lifetime for
         received packets. Otherwise use the accept start and stop time to
         determine the lifetime."
    DEFVAL { true }
    ::= { cadSysKeyChainKeyEntry 6 }

cadSysKeyChainKeySendStartTime OBJECT-TYPE
    SYNTAX DateAndTime
    MAX-ACCESS read-create
    STATUS current
    DESCRIPTION
        "The start time when this key is valid for sending packets."
    ::= { cadSysKeyChainKeyEntry 7 }

cadSysKeyChainKeySendStopTime OBJECT-TYPE
    SYNTAX DateAndTime
    MAX-ACCESS read-create
    STATUS current
    DESCRIPTION
        "The stop time when this key is no longer valid for sending packets."
    ::= { cadSysKeyChainKeyEntry 8 }

cadSysKeyChainKeySendInfiniteLifetime OBJECT-TYPE
    SYNTAX TruthValue
    MAX-ACCESS read-create
    STATUS current
    DESCRIPTION
        "If this value is set to true, the key has an infinite lifetime for
         sending packets. Otherwise use the send start and stop time to
         determine the lifetime."
    DEFVAL { true }
    ::= { cadSysKeyChainKeyEntry 9 }

cadSysKeyChainKeyRowStatus OBJECT-TYPE
    SYNTAX RowStatus
    MAX-ACCESS read-create
    STATUS current
    DESCRIPTION
        "The row status variable used according to row installation
         and removal convention. In our case, we have simplified this
         to the usage of only the following states - active, createAndGo,
         and destroy. Other three states notInService, notReady and
         createAndWait are not permitted."
    ::= { cadSysKeyChainKeyEntry 10 }

--=========== Processor Protocol Policing Objects =============================

-- configuration objects

cadSysProcRouterControlGlobalPacketRate OBJECT-TYPE
    SYNTAX      Unsigned32 (0..65535)
    UNITS       "packets/second"
    MAX-ACCESS  read-write
    STATUS      current
    DESCRIPTION 
        "The maximum permitted global protocol packet throttle rate to 
         the Router Control processor."
    DEFVAL { 2500 }
    ::= { cadSysProcPolicingConfig 1 }

cadSysProcArpPacketRate OBJECT-TYPE
    SYNTAX      Unsigned32 (0..65535)
    UNITS       "packets/second"
    MAX-ACCESS  read-write
    STATUS      current
    DESCRIPTION 
        "The maximum permitted ARP packet rate to the Router Control processor."
    DEFVAL { 700 }
    ::= { cadSysProcPolicingConfig 2 }

cadSysProcDhcpPacketRate OBJECT-TYPE
    SYNTAX      Unsigned32 (0..65535)
    UNITS       "packets/second"
    MAX-ACCESS  read-write
    STATUS      current
    DESCRIPTION 
        "The maxmimu permitted DHCP packet rate to the Router Control processor."
    DEFVAL { 750 }
    ::= { cadSysProcPolicingConfig 3 }

cadSysProcIcmpPacketRate OBJECT-TYPE
    SYNTAX      Unsigned32 (0..65535)
    UNITS       "packets/second"
    MAX-ACCESS  read-write
    STATUS      current
    DESCRIPTION 
        "The maximum permitted ICMP(IPv4) packet rate to the Router Control processor."
    DEFVAL { 500 }
    ::= { cadSysProcPolicingConfig 4 }

cadSysProcOspfPacketRate OBJECT-TYPE
    SYNTAX      Unsigned32 (0..65535)
    UNITS       "packets/second"
    MAX-ACCESS  read-write
    STATUS      current
    DESCRIPTION 
        "The maximum permitted OSPFv2 packet rate to the Router Control processor."
    DEFVAL { 750 }
    ::= { cadSysProcPolicingConfig 5 }

cadSysProcRipPacketRate OBJECT-TYPE
    SYNTAX      Unsigned32 (0..65535)
    UNITS       "packets/second"
    MAX-ACCESS  read-write
    STATUS      current
    DESCRIPTION 
        "The maximum permitted RIP packet rate to the Router Control processor."
    DEFVAL { 500 }
    ::= { cadSysProcPolicingConfig 6 }

cadSysProcIgmpPacketRate OBJECT-TYPE
    SYNTAX      Unsigned32 (0..65535)
    UNITS       "packets/second"
    MAX-ACCESS  read-write
    STATUS      current
    DESCRIPTION 
        "The maximum permitted IGMP packet rate to the Router Control processor."
    DEFVAL { 500 }
    ::= { cadSysProcPolicingConfig 7 }

cadSysProcRouterControlOtherPacketRate OBJECT-TYPE
    SYNTAX      Unsigned32 (0..65535)
    UNITS       "packets/second"
    MAX-ACCESS  read-write
    STATUS      current
    DESCRIPTION 
        "The other protocol packet rate to the Router Control processor."
    DEFVAL { 500 }
    ::= { cadSysProcPolicingConfig 8 }

cadSysProcSnmpPacketRate OBJECT-TYPE
    SYNTAX      Unsigned32 (0..65535)
    UNITS       "packets/second"
    MAX-ACCESS  read-write
    STATUS      current
    DESCRIPTION 
        "The SNMP packet rate to the System Control processor."
    DEFVAL { 650 }
    ::= { cadSysProcPolicingConfig 10 }

cadSysProcTftpPacketRate OBJECT-TYPE
    SYNTAX      Unsigned32 (0..65535)
    UNITS       "packets/second"
    MAX-ACCESS  read-write
    STATUS      current
    DESCRIPTION 
        "The TFTP packet rate to the processor."
    DEFVAL { 750 }
    ::= { cadSysProcPolicingConfig 11 }

cadSysProcIsisPacketRate OBJECT-TYPE
    SYNTAX      Unsigned32 (0..65535)
    UNITS       "packets/second"
    MAX-ACCESS  read-write
    STATUS      current
    DESCRIPTION 
        "The IS-IS packet rate to the processor."
    DEFVAL { 750 }
    ::= { cadSysProcPolicingConfig 12 }

cadSysProcNdPacketRate OBJECT-TYPE
    SYNTAX      Unsigned32 (0..65535)
    UNITS       "packets/second"
    MAX-ACCESS  read-write
    STATUS      current
    DESCRIPTION 
        "The maximum permitted Neighbor Discover (ND) packet throttle
         rate to the Router Control processor.  This includes IPv6 Router
         Solicitation, Router Advertise, Neighbor Solicitation, Neighbor 
         Advertise, and Redirect messages."
    DEFVAL { 700 }
    ::= { cadSysProcPolicingConfig 13 }

cadSysProcDhcpIpv6PacketRate OBJECT-TYPE
    SYNTAX      Unsigned32 (0..65535)
    UNITS       "packets/second"
    MAX-ACCESS  read-write
    STATUS      current
    DESCRIPTION 
        "The maximum permitted DHCP (Ipv6) packet throttle 
         rate to the Router Control processor."
    DEFVAL { 500 }
    ::= { cadSysProcPolicingConfig 14 }

cadSysProcIcmpIpv6PacketRate OBJECT-TYPE
    SYNTAX      Unsigned32 (0..65535)
    UNITS       "packets/second"
    MAX-ACCESS  read-write
    STATUS      current
    DESCRIPTION 
        "The maximum permitted ICMP (Ipv6 other than Neighbor
         Discover and MLD) packet throttle rate to the Router 
         Control processor."
    DEFVAL { 500 }
    ::= { cadSysProcPolicingConfig 15 }

cadSysProcMldPacketRate OBJECT-TYPE
    SYNTAX      Unsigned32 (0..65535)
    UNITS       "packets/second"
    MAX-ACCESS  read-write
    STATUS      current
    DESCRIPTION 
        "The maximum permitted MLD (version 1 and version 2)
         packet throttle rate to the Router Control processor."
    DEFVAL { 500 }
    ::= { cadSysProcPolicingConfig 16 }

cadSysProcBgpPacketRate OBJECT-TYPE
    SYNTAX      Unsigned32 (0..65535)
    UNITS       "packets/second"
    MAX-ACCESS  read-write
    STATUS      current
    DESCRIPTION 
        "The maximum permitted BGP packet throttle rate to 
         the Router Control processor."
    DEFVAL { 500 }
    ::= { cadSysProcPolicingConfig 17 }

cadSysProcPimPacketRate OBJECT-TYPE
    SYNTAX      Unsigned32 (0..65535)
    UNITS       "packets/second"
    MAX-ACCESS  read-write
    STATUS      current
    DESCRIPTION 
        "The maximum permitted PIM packet throttle rate to 
         the Router Control processor."
    DEFVAL { 100 }
    ::= { cadSysProcPolicingConfig 18 }

cadSysProcSnmpCmPacketRate OBJECT-TYPE
    SYNTAX      Unsigned32 (0..65535)
    UNITS       "packets/second"
    MAX-ACCESS  read-write
    STATUS      current
    DESCRIPTION 
        "The maximum permitted SNMP (from CMs) packet throttle rate to 
         the Router Control processor."
    DEFVAL { 100 }
    ::= { cadSysProcPolicingConfig 19 }

cadSysProcCopsPacketRate OBJECT-TYPE
    SYNTAX      Unsigned32 (0..65535)
    UNITS       "packets/second"
    MAX-ACCESS  read-write
    STATUS      current
    DESCRIPTION 
        "The maximum permitted Cops packet throttle rate to 
         the Router Control processor."
    DEFVAL { 300 }
    ::= { cadSysProcPolicingConfig 20 }

cadSysProcTelnetPacketRate OBJECT-TYPE
    SYNTAX      Unsigned32 (0..65535)
    UNITS       "packets/second"
    MAX-ACCESS  read-write
    STATUS      current
    DESCRIPTION 
        "The maximum permitted Telnet packet throttle rate to 
         the Router Control processor."
    DEFVAL { 300 }
    ::= { cadSysProcPolicingConfig 21 }

cadSysProcOspfv3PacketRate OBJECT-TYPE
    SYNTAX      Unsigned32 (0..65535)
    UNITS       "packets/second"
    MAX-ACCESS  read-write
    STATUS      current
    DESCRIPTION 
        "The maximum permitted OSPFv3 packet rate to the Router Control processor."
    DEFVAL { 750 }
    ::= { cadSysProcPolicingConfig 22 }

cadSysProcTftpIpv6PacketRate OBJECT-TYPE
    SYNTAX      Unsigned32 (0..65535)
	UNITS       "packets/second"
    MAX-ACCESS  read-write
    STATUS      current
    DESCRIPTION "The TFTP (IPv6) packet rate to the processor."
    DEFVAL { 750 }
    ::= { cadSysProcPolicingConfig 23 }

cadSysProcEventIcmpPacketRate OBJECT-TYPE
    SYNTAX      Unsigned32 (0..65535)
    UNITS       "packets/second"
    MAX-ACCESS  read-write
    STATUS      current
    DESCRIPTION 
        "The maximum permitted ICMP event packet rate to the Router Control processor."
    DEFVAL { 700 }
    ::= { cadSysProcPolicingConfig 24 }
    
cadSysProcEventNoRoutePacketRate OBJECT-TYPE
    SYNTAX      Unsigned32 (0..65535)
    UNITS       "packets/second"
    MAX-ACCESS  read-write
    STATUS      current
    DESCRIPTION 
        "The maximum permitted No Route event packet rate to the Router Control processor."
    DEFVAL { 700 }
    ::= { cadSysProcPolicingConfig 25 }

cadSysProcEventIcmpIpv6PacketRate OBJECT-TYPE
    SYNTAX      Unsigned32 (0..65535)
    UNITS       "packets/second"
    MAX-ACCESS  read-write
    STATUS      current
    DESCRIPTION 
        "The maximum permitted ICMP (IPv6) event packet rate to the Router Control processor."
    DEFVAL { 700 }
    ::= { cadSysProcPolicingConfig 26 }

cadSysProcEventNoRouteIpv6PacketRate OBJECT-TYPE
    SYNTAX      Unsigned32 (0..65535)
    UNITS       "packets/second"
    MAX-ACCESS  read-write
    STATUS      current
    DESCRIPTION 
        "The maximum permitted No Route (IPv6) event packet rate to the Router Control processor."
    DEFVAL { 700 }
    ::= { cadSysProcPolicingConfig 27 }

cadSysProcEventArpPacketRate OBJECT-TYPE
    SYNTAX      Unsigned32 (0..65535)
    UNITS       "packets/second"
    MAX-ACCESS  read-write
    STATUS      current
    DESCRIPTION 
        "The maximum permitted ARP event packet rate to the Router Control processor."
    DEFVAL { 700 }
    ::= { cadSysProcPolicingConfig 28 }
    
cadSysProcEventNdPacketRate OBJECT-TYPE
    SYNTAX      Unsigned32 (0..65535)
    UNITS       "packets/second"
    MAX-ACCESS  read-write
    STATUS      current
    DESCRIPTION 
        "The maximum permitted ND event packet rate to the Router Control processor."
    DEFVAL { 700 }
    ::= { cadSysProcPolicingConfig 29 }

cadSysProcEventTtlPacketRate OBJECT-TYPE
    SYNTAX      Unsigned32 (0..65535)
    UNITS       "packets/second"
    MAX-ACCESS  read-write
    STATUS      current
    DESCRIPTION 
        "The maximum permitted TTL event packet rate to the Router Control processor."
    DEFVAL { 100 }
    ::= { cadSysProcPolicingConfig 30 }
  
cadSysProcEventTtlIpv6PacketRate OBJECT-TYPE
    SYNTAX      Unsigned32 (0..65535)
    UNITS       "packets/second"
    MAX-ACCESS  read-write
    STATUS      current
    DESCRIPTION 
        "The maximum permitted TTL (IPv6) event packet rate to the Router Control processor."
    DEFVAL { 100 }
    ::= { cadSysProcPolicingConfig 31 }

cadSysProcEventDadPacketRate OBJECT-TYPE
    SYNTAX      Unsigned32 (0..65535)
    UNITS       "packets/second"
    MAX-ACCESS  read-write
    STATUS      current
    DESCRIPTION 
        "The maximum permitted DAD event packet rate to the Router Control processor."
    DEFVAL { 500 }
    ::= { cadSysProcPolicingConfig 32 }

cadSysProcEventDefaultPacketRate OBJECT-TYPE
    SYNTAX      Unsigned32 (0..65535)
    UNITS       "packets/second"
    MAX-ACCESS  read-write
    STATUS      current
    DESCRIPTION 
        "The maximum permitted Default event packet rate to the Router Control processor."
    DEFVAL { 3000 }
    ::= { cadSysProcPolicingConfig 33 }

cadSysProcLdpPacketRate OBJECT-TYPE
    SYNTAX      Unsigned32 (0..65535)
	UNITS       "packets/second"
    MAX-ACCESS  read-write
    STATUS      current
    DESCRIPTION "The LDP (UDP and TCP) packet rate to the processor."
    DEFVAL { 750 }
    ::= { cadSysProcPolicingConfig 34 }

cadSysProcClearPolicingCounts OBJECT-TYPE
    SYNTAX      TruthValue
    MAX-ACCESS  read-write
    STATUS      current
    DESCRIPTION 
        "This variable always returns false(2) upon reading. 
         When set to true(1), all objects under cadSysProcPolicingCounts are cleared."

    ::= { cadSysProcPolicingConfig 35 }

cadSysProcLacpPacketRate OBJECT-TYPE
    SYNTAX      Unsigned32 (0..65535)
    UNITS       "packets/second"
    MAX-ACCESS  read-write
    STATUS      current
    DESCRIPTION "The total LACP packet rate to the processor."
    DEFVAL { 200 }
    ::= { cadSysProcPolicingConfig 36 }


cadSysProcVrepPacketRate OBJECT-TYPE
    SYNTAX      Unsigned32 (0..65535)
    UNITS       "packets/second"
    MAX-ACCESS  read-write
    STATUS      current
    DESCRIPTION "The maximum permitted D6/VREP packet rate to the processor."
    DEFVAL { 500 }
    ::= { cadSysProcPolicingConfig 37 }

cadSysProcVpmePacketRate OBJECT-TYPE
    SYNTAX      Unsigned32 (0..65535)
    UNITS       "packets/second"
    MAX-ACCESS  read-write
    STATUS      current
    DESCRIPTION "The maximum permitted VPME packet rate to the processor."
    DEFVAL { 30 }
    ::= { cadSysProcPolicingConfig 38 }

cadSysProcErmRpcPacketRate OBJECT-TYPE
    SYNTAX      Unsigned32 (0..65535)
    UNITS       "packets/second"
    MAX-ACCESS  read-write
    STATUS      current
    DESCRIPTION
        "The maximum permitted RPC packet rate from an RPC ERM processor."
    DEFVAL { 300 }
    ::= { cadSysProcPolicingConfig 39 }



--
-- count objects
--
cadSysProcRouterControlGlobalPacketsReceivedPassed OBJECT-TYPE
    SYNTAX      Counter32
    UNITS       "packets"
    MAX-ACCESS  read-only
    STATUS      current
    DESCRIPTION 
        "The number of packets received passed to the Router Control processor."
    ::= { cadSysProcPolicingCounts 1 }

cadSysProcRouterControlGlobalPacketsReceivedDropped OBJECT-TYPE
    SYNTAX      Counter32
    UNITS       "packets"
    MAX-ACCESS  read-only
    STATUS      current
    DESCRIPTION 
        "The number of packets received that are dropped by the Router Control processor."
    ::= { cadSysProcPolicingCounts 2 }

cadSysProcArpPacketsReceivedPassed OBJECT-TYPE
    SYNTAX      Counter32
    UNITS       "packets"
    MAX-ACCESS  read-only
    STATUS      current
    DESCRIPTION 
        "The number of ARP packets received passed to the processor."
    ::= { cadSysProcPolicingCounts 4 }

cadSysProcArpPacketsReceivedDropped OBJECT-TYPE
    SYNTAX      Counter32
    UNITS       "packets"
    MAX-ACCESS  read-only
    STATUS      current
    DESCRIPTION 
        "The number of ARP packets received that are dropped."
    ::= { cadSysProcPolicingCounts 5 }

cadSysProcDhcpPacketsReceivedPassed OBJECT-TYPE
    SYNTAX      Counter32
    UNITS       "packets"
    MAX-ACCESS  read-only
    STATUS      current
    DESCRIPTION 
        "The number of DHCP packets received passed to the processor."
    ::= { cadSysProcPolicingCounts 7 }

cadSysProcDhcpPacketsReceivedDropped OBJECT-TYPE
    SYNTAX      Counter32
    UNITS       "packets"
    MAX-ACCESS  read-only
    STATUS      current
    DESCRIPTION 
        "The number of DHCP packets received that are dropped."
    ::= { cadSysProcPolicingCounts 8 }

-- cadSysProcDhcpPacketsSent removed. do NOT reuse the OID
--    ::= { cadSysProcPolicingCounts 9 }

cadSysProcIcmpPacketsReceivedPassed OBJECT-TYPE
    SYNTAX      Counter32
    UNITS       "packets"
    MAX-ACCESS  read-only
    STATUS      current
    DESCRIPTION 
        "The number of ICMP packets received passed to the processor."
    ::= { cadSysProcPolicingCounts 10 }

cadSysProcIcmpPacketsReceivedDropped OBJECT-TYPE
    SYNTAX      Counter32
    UNITS       "packets"
    MAX-ACCESS  read-only
    STATUS      current
    DESCRIPTION 
        "The number of ICMP packets received that are dropped."
    ::= { cadSysProcPolicingCounts 11 }

cadSysProcOspfPacketsReceivedPassed OBJECT-TYPE
    SYNTAX      Counter32
    UNITS       "packets"
    MAX-ACCESS  read-only
    STATUS      current
    DESCRIPTION "The number of OSPFv2 packets received passed to the processor."
    ::= { cadSysProcPolicingCounts 13 }

cadSysProcOspfPacketsReceivedDropped OBJECT-TYPE
    SYNTAX      Counter32
    UNITS       "packets"
    MAX-ACCESS  read-only
    STATUS      current
    DESCRIPTION 
        "The number of OSPFv2 packets received that are dropped."
    ::= { cadSysProcPolicingCounts 14 }

cadSysProcRipPacketsReceivedPassed OBJECT-TYPE
    SYNTAX      Counter32
    UNITS       "packets"
    MAX-ACCESS  read-only
    STATUS      current
    DESCRIPTION "The number of RIP packets received passed to the processor."
    ::= { cadSysProcPolicingCounts 16 }

cadSysProcRipPacketsReceivedDropped OBJECT-TYPE
    SYNTAX      Counter32
    UNITS       "packets"
    MAX-ACCESS  read-only
    STATUS      current
    DESCRIPTION 
        "The number of RIP packets received that are dropped."
    ::= { cadSysProcPolicingCounts 17 }

cadSysProcIgmpPacketsReceivedPassed OBJECT-TYPE
    SYNTAX      Counter32
    UNITS       "packets"
    MAX-ACCESS  read-only
    STATUS      current
    DESCRIPTION "The number of IGMP packets received passed to the processor."
    ::= { cadSysProcPolicingCounts 19 }

cadSysProcIgmpPacketsReceivedDropped OBJECT-TYPE
    SYNTAX      Counter32
    UNITS       "packets"
    MAX-ACCESS  read-only
    STATUS      current
    DESCRIPTION "The number of IGMP packets received that are dropped."
    ::= { cadSysProcPolicingCounts 20 }

cadSysProcRouterControlOtherPacketsReceivedPassed OBJECT-TYPE
    SYNTAX      Counter32
    UNITS       "packets"
    MAX-ACCESS  read-only
    STATUS      current
    DESCRIPTION 
        "The number of other packets received passed to the Router Control processor."
    ::= { cadSysProcPolicingCounts 22 }

cadSysProcRouterControlOtherPacketsReceivedDropped OBJECT-TYPE
    SYNTAX      Counter32
    UNITS       "packets"
    MAX-ACCESS  read-only
    STATUS      current
    DESCRIPTION 
        "The number of other packets received that are dropped by the Router Control processor."
    ::= { cadSysProcPolicingCounts 23 }

cadSysProcSnmpPacketsReceivedPassed OBJECT-TYPE
    SYNTAX      Counter32
    UNITS       "packets"
    MAX-ACCESS  read-only
    STATUS      current
    DESCRIPTION 
        "The number of SNMP packets received passed to the System Control processor."
    ::= { cadSysProcPolicingCounts 25 }

cadSysProcSnmpPacketsReceivedDropped OBJECT-TYPE
    SYNTAX      Counter32
    UNITS       "packets"
    MAX-ACCESS  read-only
    STATUS      current
    DESCRIPTION 
        "The number of SNMP packets received that are dropped."
    ::= { cadSysProcPolicingCounts 26 }

cadSysProcTftpPacketsReceivedPassed OBJECT-TYPE
    SYNTAX      Counter32
    UNITS       "packets"
    MAX-ACCESS  read-only
    STATUS      current
    DESCRIPTION 
        "The number of TFTP packets received passed to the processor."
    ::= { cadSysProcPolicingCounts 28 }

cadSysProcTftpPacketsReceivedDropped OBJECT-TYPE
    SYNTAX      Counter32
    UNITS       "packets"
    MAX-ACCESS  read-only
    STATUS      current
    DESCRIPTION 
        "The number of TFTP packets received that are dropped."
    ::= { cadSysProcPolicingCounts 29 }

cadSysProcIsisPacketsReceivedPassed OBJECT-TYPE
    SYNTAX      Counter32
    UNITS       "packets"
    MAX-ACCESS  read-only
    STATUS      current
    DESCRIPTION 
        "The number of IS-IS packets received passed to the processor."
    ::= { cadSysProcPolicingCounts 31 }

cadSysProcIsisPacketsReceivedDropped OBJECT-TYPE
    SYNTAX      Counter32
    UNITS       "packets"
    MAX-ACCESS  read-only
    STATUS      current
    DESCRIPTION 
        "The number of IS-IS packets received that are dropped."
    ::= { cadSysProcPolicingCounts 32 }

cadSysProcNdPacketsReceivedPassed OBJECT-TYPE
    SYNTAX      Counter32
    UNITS       "packets"
    MAX-ACCESS  read-only
    STATUS      current
    DESCRIPTION 
        "The number of Neighbor Discover packets received passed to the processor."
    ::= { cadSysProcPolicingCounts 37 }

cadSysProcNdPacketsReceivedDropped OBJECT-TYPE
    SYNTAX      Counter32
    UNITS       "packets"
    MAX-ACCESS  read-only
    STATUS      current
    DESCRIPTION 
        "The number of Neighbor Discover packets received that are dropped."
    ::= { cadSysProcPolicingCounts 38 }

cadSysProcDhcpIpv6PacketsReceivedPassed OBJECT-TYPE
    SYNTAX      Counter32
    UNITS       "packets"
    MAX-ACCESS  read-only
    STATUS      current
    DESCRIPTION 
        "The number of DHCP(Ipv6) packets received passed to the processor."
    ::= { cadSysProcPolicingCounts 40 }

cadSysProcDhcpIpv6PacketsReceivedDropped OBJECT-TYPE
    SYNTAX      Counter32
    UNITS       "packets"
    MAX-ACCESS  read-only
    STATUS      current
    DESCRIPTION 
        "The number of DHCP(IPv6) packets received that are dropped."
    ::= { cadSysProcPolicingCounts 41 }

cadSysProcIcmpIpv6PacketsReceivedPassed OBJECT-TYPE
    SYNTAX      Counter32
    UNITS       "packets"
    MAX-ACCESS  read-only
    STATUS      current
    DESCRIPTION 
        "The number of ICMP(Ipv6) packets received passed to the processor."
    ::= { cadSysProcPolicingCounts 43 }

cadSysProcIcmpIpv6PacketsReceivedDropped OBJECT-TYPE
    SYNTAX      Counter32
    UNITS       "packets"
    MAX-ACCESS  read-only
    STATUS      current
    DESCRIPTION 
        "The number of ICMP(IPv6) packets received that are dropped."
    ::= { cadSysProcPolicingCounts 44 }

cadSysProcMldPacketsReceivedPassed OBJECT-TYPE
    SYNTAX      Counter32
    UNITS       "packets"
    MAX-ACCESS  read-only
    STATUS      current
    DESCRIPTION 
        "The number of MLD packets received passed to the processor."
    ::= { cadSysProcPolicingCounts 46 }

cadSysProcMldPacketsReceivedDropped OBJECT-TYPE
    SYNTAX      Counter32
    UNITS       "packets"
    MAX-ACCESS  read-only
    STATUS      current
    DESCRIPTION 
        "The number of MLD packets received that are dropped."
    ::= { cadSysProcPolicingCounts 47 }

cadSysProcBgpPacketsReceivedPassed OBJECT-TYPE
    SYNTAX      Counter32
    UNITS       "packets"
    MAX-ACCESS  read-only
    STATUS      current
    DESCRIPTION 
        "The number of BGP packets received passed to the processor."
    ::= { cadSysProcPolicingCounts 49 }

cadSysProcBgpPacketsReceivedDropped OBJECT-TYPE
    SYNTAX      Counter32
    UNITS       "packets"
    MAX-ACCESS  read-only
    STATUS      current
    DESCRIPTION 
        "The number of BGP packets received that are dropped."
    ::= { cadSysProcPolicingCounts 50 }

cadSysProcPimPacketsReceivedPassed OBJECT-TYPE
    SYNTAX      Counter32
    UNITS       "packets"
    MAX-ACCESS  read-only
    STATUS      current
    DESCRIPTION 
        "The number of PIM packets received passed to the processor."
    ::= { cadSysProcPolicingCounts 52 }

cadSysProcPimPacketsReceivedDropped OBJECT-TYPE
    SYNTAX      Counter32
    UNITS       "packets"
    MAX-ACCESS  read-only
    STATUS      current
    DESCRIPTION 
        "The number of PIM packets received that are dropped."
    ::= { cadSysProcPolicingCounts 53 }

cadSysProcSnmpCmPacketsReceivedPassed OBJECT-TYPE
    SYNTAX      Counter32
    UNITS       "packets"
    MAX-ACCESS  read-only
    STATUS      current
    DESCRIPTION 
        "The number of SNMP (from CMs) packets received passed to the processor."
    ::= { cadSysProcPolicingCounts 55 }

cadSysProcSnmpCmPacketsReceivedDropped OBJECT-TYPE
    SYNTAX      Counter32
    UNITS       "packets"
    MAX-ACCESS  read-only
    STATUS      current
    DESCRIPTION 
        "The number of SNMP (from CMs) packets received that are dropped."
    ::= { cadSysProcPolicingCounts 56 }

cadSysProcCopsPacketsReceivedPassed OBJECT-TYPE
    SYNTAX      Counter32
    UNITS       "packets"
    MAX-ACCESS  read-only
    STATUS      current
    DESCRIPTION 
        "The number of COPS packets received passed to the System Control processor."
    ::= { cadSysProcPolicingCounts 58 }

cadSysProcCopsPacketsReceivedDropped OBJECT-TYPE
    SYNTAX      Counter32
    UNITS       "packets"
    MAX-ACCESS  read-only
    STATUS      current
    DESCRIPTION 
        "The number of COPS packets received that are dropped."
    ::= { cadSysProcPolicingCounts 59 }

cadSysProcTelnetPacketsReceivedPassed OBJECT-TYPE
    SYNTAX      Counter32
    UNITS       "packets"
    MAX-ACCESS  read-only
    STATUS      current
    DESCRIPTION 
        "The number of TELNET packets received passed to the System Control processor."
    ::= { cadSysProcPolicingCounts 61 }

cadSysProcTelnetPacketsReceivedDropped OBJECT-TYPE
    SYNTAX      Counter32
    UNITS       "packets"
    MAX-ACCESS  read-only
    STATUS      current
    DESCRIPTION 
        "The number of TELNET packets received that are dropped."
    ::= { cadSysProcPolicingCounts 62 }

cadSysProcOspfv3PacketsReceivedPassed OBJECT-TYPE
    SYNTAX      Counter32
    UNITS       "packets"
    MAX-ACCESS  read-only
    STATUS      current
    DESCRIPTION "The number of OSPFv3 packets received passed to the processor."
    ::= { cadSysProcPolicingCounts 64 }

cadSysProcOspfv3PacketsReceivedDropped OBJECT-TYPE
    SYNTAX      Counter32
    UNITS       "packets"
    MAX-ACCESS  read-only
    STATUS      current
    DESCRIPTION 
        "The number of OSPFv3 packets received that are dropped."
    ::= { cadSysProcPolicingCounts 65 }

-- cadSysProcOspfv3PacketsSent removed
--    ::= { cadSysProcPolicingCounts 66 }

cadSysProcTftpIpv6PacketsReceivedPassed OBJECT-TYPE
    SYNTAX      Counter32
    UNITS       "packets"
    MAX-ACCESS  read-only
    STATUS      current
    DESCRIPTION "The number of TFTP (IPv6) packets received passed to the processor."
    ::= { cadSysProcPolicingCounts 67 }

cadSysProcTftpIpv6PacketsReceivedDropped OBJECT-TYPE
    SYNTAX      Counter32
    UNITS       "packets"
    MAX-ACCESS  read-only
    STATUS      current
    DESCRIPTION "The number of TFTP (IPv6) packets received that are dropped."
    ::= { cadSysProcPolicingCounts 68 }

-- cadSysProcTftpIpv6PacketsSent removed, do NOT reuse the OID
--    ::= { cadSysProcPolicingCounts 69 } 

cadSysProcLdpPacketsReceivedPassed OBJECT-TYPE
    SYNTAX      Counter32
    UNITS       "packets"
    MAX-ACCESS  read-only
    STATUS      current
    DESCRIPTION "The number of LDP (UDP and TCP) packets received passed to the processor."
    ::= { cadSysProcPolicingCounts 70 }

cadSysProcLdpPacketsReceivedDropped OBJECT-TYPE
    SYNTAX      Counter32
    UNITS       "packets"
    MAX-ACCESS  read-only
    STATUS      current
    DESCRIPTION "The number of LDP (UDP and TCP) packets received that are dropped."
    ::= { cadSysProcPolicingCounts 71 }

-- cadSysProcLdpPacketsSent removed, do NOT reuse the OID
--    ::= { cadSysProcPolicingCounts 72 } 
    
--=========== NPU events to the host Objects ==============================
cadSysProcEventIcmpPacketsReceivedPassed OBJECT-TYPE
    SYNTAX      Counter32
    UNITS       "packets"
    MAX-ACCESS  read-only
    STATUS      current
    DESCRIPTION "The number of ICMP event packets received passed to the processor."
    ::= { cadSysProcPolicingCounts 73 }

cadSysProcEventIcmpPacketsReceivedDropped OBJECT-TYPE
    SYNTAX      Counter32
    UNITS       "packets"
    MAX-ACCESS  read-only
    STATUS      current
    DESCRIPTION "The number of ICMP event packets received that are dropped."
    ::= { cadSysProcPolicingCounts 74 }

cadSysProcEventNoRoutePacketsReceivedPassed OBJECT-TYPE
    SYNTAX      Counter32
    UNITS       "packets"
    MAX-ACCESS  read-only
    STATUS      current
    DESCRIPTION "The number of No Route event packets received passed to the processor."
    ::= { cadSysProcPolicingCounts 75 }

cadSysProcEventNoRoutePacketsReceivedDropped OBJECT-TYPE
    SYNTAX      Counter32
    UNITS       "packets"
    MAX-ACCESS  read-only
    STATUS      current
    DESCRIPTION "The number of No Route event packets received that are dropped."
    ::= { cadSysProcPolicingCounts 76 }

cadSysProcEventIcmpIpv6PacketsReceivedPassed OBJECT-TYPE
    SYNTAX      Counter32
    UNITS       "packets"
    MAX-ACCESS  read-only
    STATUS      current
    DESCRIPTION "The number of ICMP (IPv6) event packets received passed to the processor."
    ::= { cadSysProcPolicingCounts 77 }

cadSysProcEventIcmpIpv6PacketsReceivedDropped OBJECT-TYPE
    SYNTAX      Counter32
    UNITS       "packets"
    MAX-ACCESS  read-only
    STATUS      current
    DESCRIPTION "The number of ICMP (IPv6) event packets received that are dropped."
    ::= { cadSysProcPolicingCounts 78 }
    
cadSysProcEventNoRouteIpv6PacketsReceivedPassed OBJECT-TYPE
    SYNTAX      Counter32
    UNITS       "packets"
    MAX-ACCESS  read-only
    STATUS      current
    DESCRIPTION "The number of No Route (IPv6) event packets received passed to the processor."
    ::= { cadSysProcPolicingCounts 79 }

cadSysProcEventNoRouteIpv6PacketsReceivedDropped OBJECT-TYPE
    SYNTAX      Counter32
    UNITS       "packets"
    MAX-ACCESS  read-only
    STATUS      current
    DESCRIPTION "The number of No Route (IPv6) event packets received that are dropped."
    ::= { cadSysProcPolicingCounts 80 }

cadSysProcEventArpPacketsReceivedPassed OBJECT-TYPE
    SYNTAX      Counter32
    UNITS       "packets"
    MAX-ACCESS  read-only
    STATUS      current
    DESCRIPTION "The number of ARP event packets received passed to the processor."
    ::= { cadSysProcPolicingCounts 81 }

cadSysProcEventArpPacketsReceivedDropped OBJECT-TYPE
    SYNTAX      Counter32
    UNITS       "packets"
    MAX-ACCESS  read-only
    STATUS      current
    DESCRIPTION "The number of ARP event packets received that are dropped."
    ::= { cadSysProcPolicingCounts 82 }

cadSysProcEventNdPacketsReceivedPassed OBJECT-TYPE
    SYNTAX      Counter32
    UNITS       "packets"
    MAX-ACCESS  read-only
    STATUS      current
    DESCRIPTION "The number of ND event packets received passed to the processor."
    ::= { cadSysProcPolicingCounts 83 }

cadSysProcEventNdPacketsReceivedDropped OBJECT-TYPE
    SYNTAX      Counter32
    UNITS       "packets"
    MAX-ACCESS  read-only
    STATUS      current
    DESCRIPTION "The number of ND event packets received that are dropped."
    ::= { cadSysProcPolicingCounts 84 }

cadSysProcEventTtlPacketsReceivedPassed OBJECT-TYPE
    SYNTAX      Counter32
    UNITS       "packets"
    MAX-ACCESS  read-only
    STATUS      current
    DESCRIPTION "The number of TTL event packets received passed to the processor."
    ::= { cadSysProcPolicingCounts 85 }

cadSysProcEventTtlPacketsReceivedDropped OBJECT-TYPE
    SYNTAX      Counter32
    UNITS       "packets"
    MAX-ACCESS  read-only
    STATUS      current
    DESCRIPTION "The number of TTL event packets received that are dropped."
    ::= { cadSysProcPolicingCounts 86 }

cadSysProcEventTtlIpv6PacketsReceivedPassed OBJECT-TYPE
    SYNTAX      Counter32
    UNITS       "packets"
    MAX-ACCESS  read-only
    STATUS      current
    DESCRIPTION "The number of TTL (IPv6) event packets received passed to the processor."
    ::= { cadSysProcPolicingCounts 87 }

cadSysProcEventTtlIpv6PacketsReceivedDropped OBJECT-TYPE
    SYNTAX      Counter32
    UNITS       "packets"
    MAX-ACCESS  read-only
    STATUS      current
    DESCRIPTION "The number of TTL (IPv6) event packets received that are dropped."
    ::= { cadSysProcPolicingCounts 88 }    

cadSysProcEventDadPacketsReceivedPassed OBJECT-TYPE
    SYNTAX      Counter32
    UNITS       "packets"
    MAX-ACCESS  read-only
    STATUS      current
    DESCRIPTION "The number of DAD event packets received passed to the processor."
    ::= { cadSysProcPolicingCounts 89 }

cadSysProcEventDadPacketsReceivedDropped OBJECT-TYPE
    SYNTAX      Counter32
    UNITS       "packets"
    MAX-ACCESS  read-only
    STATUS      current
    DESCRIPTION "The number of DAD event packets received that are dropped."
    ::= { cadSysProcPolicingCounts 90 }

cadSysProcEventDefaultPacketsReceivedPassed OBJECT-TYPE
    SYNTAX      Counter32
    UNITS       "packets"
    MAX-ACCESS  read-only
    STATUS      current
    DESCRIPTION "The number of Default event packets received passed to the processor."
    ::= { cadSysProcPolicingCounts 91 }

cadSysProcEventDefaultPacketsReceivedDropped OBJECT-TYPE
    SYNTAX      Counter32
    UNITS       "packets"
    MAX-ACCESS  read-only
    STATUS      current
    DESCRIPTION "The number of Default event packets received that are dropped."
    ::= { cadSysProcPolicingCounts 92 }
                
cadSysProcLacpPacketsReceivedPassed OBJECT-TYPE
    SYNTAX      Counter32
    UNITS       "packets"
    MAX-ACCESS  read-only
    STATUS      current
    DESCRIPTION "The number of LACP packets received passed to the processor."
    ::= { cadSysProcPolicingCounts 93 }

cadSysProcLacpPacketsReceivedDropped OBJECT-TYPE
    SYNTAX      Counter32
    UNITS       "packets"
    MAX-ACCESS  read-only
    STATUS      current
    DESCRIPTION "The number of LACP packets received that are dropped."
    ::= { cadSysProcPolicingCounts 94 }

cadSysProcVrepPacketsReceivedPassed OBJECT-TYPE
    SYNTAX      Counter32
    UNITS       "packets"
    MAX-ACCESS  read-only
    STATUS      current
    DESCRIPTION "The number of D6/VREP packets received passed to the processor."
    ::= { cadSysProcPolicingCounts 95 }

cadSysProcVrepPacketsReceivedDropped OBJECT-TYPE
    SYNTAX      Counter32
    UNITS       "packets"
    MAX-ACCESS  read-only
    STATUS      current
    DESCRIPTION "The number of D6/VREP packets received that are dropped."
    ::= { cadSysProcPolicingCounts 96 }

cadSysProcVpmePacketsReceivedPassed OBJECT-TYPE
    SYNTAX      Counter32
    UNITS       "packets"
    MAX-ACCESS  read-only
    STATUS      current
    DESCRIPTION "The number of VPME packets received passed to the processor."
    ::= { cadSysProcPolicingCounts 97 }

cadSysProcVpmePacketsReceivedDropped OBJECT-TYPE
    SYNTAX      Counter32
    UNITS       "packets"
    MAX-ACCESS  read-only
    STATUS      current
    DESCRIPTION "The number of VPME packets received that are dropped."
    ::= { cadSysProcPolicingCounts 98 }

cadSysProcErmRpcPacketsReceivedPassed OBJECT-TYPE
    SYNTAX      Counter32
    UNITS       "packets"
    MAX-ACCESS  read-only
    STATUS      current
    DESCRIPTION
        "The number of ERM RPC packets received passed to the processor."
    ::= { cadSysProcPolicingCounts 99 }

cadSysProcErmRpcPacketsReceivedDropped OBJECT-TYPE
    SYNTAX      Counter32
    UNITS       "packets"
    MAX-ACCESS  read-only
    STATUS      current
    DESCRIPTION
        "The number of ERM RPC packets received that are dropped."
    ::= { cadSysProcPolicingCounts 100 }


--=========== Banner Objects ==============================

cadSysBannerMotdTable OBJECT-TYPE
    SYNTAX SEQUENCE OF CadSysBannerMotdEntry
    MAX-ACCESS         not-accessible
    STATUS             current
    DESCRIPTION
        " Table describing the MOTD banner that is displayed before the login: prompt"
    ::= { cadSysBanner 1 }

cadSysBannerMotdEntry OBJECT-TYPE
    SYNTAX     CadSysBannerMotdEntry
    MAX-ACCESS not-accessible
    STATUS     current
    DESCRIPTION
        " Describes a line in the MOTD banner"
    INDEX      { cadSysBannerMotdLine }
    ::= { cadSysBannerMotdTable 1 }

CadSysBannerMotdEntry ::= SEQUENCE {
    cadSysBannerMotdLine            Integer32,
    cadSysBannerMotdText            DisplayString,
    cadSysBannerMotdRowStatus       RowStatus
}

cadSysBannerMotdLine OBJECT-TYPE
    SYNTAX     Integer32 (1..100)
    MAX-ACCESS not-accessible
    STATUS     current
    DESCRIPTION
        "The line number"
    ::= { cadSysBannerMotdEntry 1 }

cadSysBannerMotdText OBJECT-TYPE
    SYNTAX     DisplayString (SIZE (0..255))
    MAX-ACCESS read-create
    STATUS     current
    DESCRIPTION
        "The MOTD banner text"
    ::= { cadSysBannerMotdEntry 2 }

cadSysBannerMotdRowStatus OBJECT-TYPE
    SYNTAX     RowStatus
    MAX-ACCESS read-create
    STATUS     current
    DESCRIPTION
        "The row status variable used according to row installation
         and removal convention. In our case, we have simplified this
         to the usage of only the following states - active, createAndGo,
         and destroy. Other three states notInService, notReady and
         createAndWait are not permitted."
    ::= { cadSysBannerMotdEntry 3 }

cadSysBannerLoginTable OBJECT-TYPE
    SYNTAX SEQUENCE OF CadSysBannerLoginEntry
    MAX-ACCESS         not-accessible
    STATUS             current
    DESCRIPTION
        " Table describing the login banner that is displayed after the MOTD banner and before the login: prompt"
    ::= { cadSysBanner 2 }

cadSysBannerLoginEntry OBJECT-TYPE
    SYNTAX     CadSysBannerLoginEntry
    MAX-ACCESS not-accessible
    STATUS     current
    DESCRIPTION
        " Describes a line in the login banner"
    INDEX      { cadSysBannerLoginLine }
    ::= { cadSysBannerLoginTable 1 }

CadSysBannerLoginEntry ::= SEQUENCE {
    cadSysBannerLoginLine           Integer32,
    cadSysBannerLoginText           DisplayString,
    cadSysBannerLoginRowStatus      RowStatus
}

cadSysBannerLoginLine OBJECT-TYPE
    SYNTAX     Integer32 (1..100)
    MAX-ACCESS not-accessible
    STATUS     current
    DESCRIPTION
        "The line number"
    ::= { cadSysBannerLoginEntry 1 }

cadSysBannerLoginText OBJECT-TYPE
    SYNTAX     DisplayString (SIZE (0..255))
    MAX-ACCESS read-create
    STATUS     current
    DESCRIPTION
        "The login banner text"
    ::= { cadSysBannerLoginEntry 2 }

cadSysBannerLoginRowStatus OBJECT-TYPE
    SYNTAX     RowStatus
    MAX-ACCESS read-create
    STATUS     current
    DESCRIPTION
        "The row status variable used according to row installation
         and removal convention. In our case, we have simplified this
         to the usage of only the following states - active, createAndGo,
         and destroy. Other three states notInService, notReady and
         createAndWait are not permitted."
    ::= { cadSysBannerLoginEntry 3 }

cadSysBannerExecTable OBJECT-TYPE
    SYNTAX SEQUENCE OF CadSysBannerExecEntry
    MAX-ACCESS         not-accessible
    STATUS             current
    DESCRIPTION 
        ""
    ::= { cadSysBanner 3 }

cadSysBannerExecEntry OBJECT-TYPE
    SYNTAX     CadSysBannerExecEntry
    MAX-ACCESS not-accessible
    STATUS     current
    DESCRIPTION
        ""
    INDEX      { cadSysBannerExecLine }
    ::= { cadSysBannerExecTable 1 }

CadSysBannerExecEntry ::= SEQUENCE {
    cadSysBannerExecLine           Integer32,
    cadSysBannerExecText           DisplayString,
    cadSysBannerExecRowStatus      RowStatus
}

cadSysBannerExecLine OBJECT-TYPE
    SYNTAX     Integer32 (1..25)
    MAX-ACCESS not-accessible
    STATUS     current
    DESCRIPTION
        "Index of this banner line."
    ::= { cadSysBannerExecEntry 1 }

cadSysBannerExecText OBJECT-TYPE
    SYNTAX     DisplayString (SIZE (0..255))
    MAX-ACCESS read-create
    STATUS     current
    DESCRIPTION
        "Ascii text of this banner line."
    ::= { cadSysBannerExecEntry 2 }

cadSysBannerExecRowStatus OBJECT-TYPE
    SYNTAX     RowStatus
    MAX-ACCESS read-create
    STATUS     current
    DESCRIPTION
        "The row status variable used according to row installation
         and removal convention. In our case, we have simplified this
         to the usage of only the following states - active, createAndGo,
         and destroy. Other three states notInService, notReady and
         createAndWait are not permitted."
    ::= { cadSysBannerExecEntry 3 }

cadSysBannerIncomingTable OBJECT-TYPE
    SYNTAX SEQUENCE OF CadSysBannerIncomingEntry
    MAX-ACCESS         not-accessible
    STATUS             current
    DESCRIPTION
        ""
    ::= { cadSysBanner 4 }

cadSysBannerIncomingEntry OBJECT-TYPE
    SYNTAX     CadSysBannerIncomingEntry
    MAX-ACCESS not-accessible
    STATUS     current
    DESCRIPTION
        ""
    INDEX      { cadSysBannerIncomingLine }
    ::= { cadSysBannerIncomingTable 1 }

CadSysBannerIncomingEntry ::= SEQUENCE {
    cadSysBannerIncomingLine           Integer32,
    cadSysBannerIncomingText            DisplayString,
    cadSysBannerIncomingRowStatus       RowStatus
}

cadSysBannerIncomingLine OBJECT-TYPE
    SYNTAX     Integer32 (1..25)
    MAX-ACCESS not-accessible
    STATUS     current
    DESCRIPTION
        ""
    ::= { cadSysBannerIncomingEntry 1 }

cadSysBannerIncomingText OBJECT-TYPE
    SYNTAX     DisplayString (SIZE (0..255))
    MAX-ACCESS read-create
    STATUS     current
    DESCRIPTION
        ""
    ::= { cadSysBannerIncomingEntry 2 }

cadSysBannerIncomingRowStatus OBJECT-TYPE
    SYNTAX     RowStatus
    MAX-ACCESS read-create
    STATUS     current
    DESCRIPTION
        "The row status variable used according to row installation
         and removal convention. In our case, we have simplified this
         to the usage of only the following states - active, createAndGo,
         and destroy. Other three states notInService, notReady and
         createAndWait are not permitted."
    ::= { cadSysBannerIncomingEntry 3 }

--=========== Server Objects ==============================

cadSysServerTable OBJECT-TYPE
    SYNTAX SEQUENCE OF CadSysServerEntry
    MAX-ACCESS         not-accessible
    STATUS             current
    DESCRIPTION
        " Table describing the (INET) services that should run on the SCM."
    ::= { cadSysServer 1 }

cadSysServerEntry OBJECT-TYPE
    SYNTAX     CadSysServerEntry
    MAX-ACCESS not-accessible
    STATUS     current
    DESCRIPTION
        " Describes an INET service and whether it is enabled "
    INDEX      { cadSysServerType }
    ::= { cadSysServerTable 1 }

CadSysServerEntry ::= SEQUENCE {
    cadSysServerType           ServerType,
    cadSysServerAdminState     AdminState
}

cadSysServerType OBJECT-TYPE
    SYNTAX     ServerType
    MAX-ACCESS not-accessible
    STATUS     current
    DESCRIPTION
        "The service type"
    ::= { cadSysServerEntry 1 }

cadSysServerAdminState OBJECT-TYPE
    SYNTAX     AdminState
    MAX-ACCESS read-create
    STATUS     current
    DESCRIPTION
        "The administrative state of the server."
    DEFVAL { up }
    ::= { cadSysServerEntry 2 }


--=========== Patch Parameter Objects =============================

cadSysPatchParamTable OBJECT-TYPE
    SYNTAX  SEQUENCE OF CadSysPatchParamEntry
    MAX-ACCESS not-accessible
    STATUS current
    DESCRIPTION
        "Table of patch parameters."
    ::= { cadSysPatchParams 1 }

cadSysPatchParamEntry OBJECT-TYPE
    SYNTAX CadSysPatchParamEntry
    MAX-ACCESS not-accessible
    STATUS current
    DESCRIPTION
        "Entry of an individual patch parameter."
    INDEX { cadSysPatchParamIndex }
    ::= { cadSysPatchParamTable 1 }

CadSysPatchParamEntry ::= SEQUENCE {
    cadSysPatchParamIndex              Integer32,
    cadSysPatchParamName               DisplayString,
    cadSysPatchParamValue              DisplayString,
    cadSysPatchParamDescription        DisplayString,
    cadSysPatchParamRowStatus          RowStatus
}

cadSysPatchParamIndex OBJECT-TYPE
    SYNTAX Integer32 (1..1000)
    MAX-ACCESS not-accessible
    STATUS current
    DESCRIPTION
        "The patch parameter index."
    ::= { cadSysPatchParamEntry 1 }

cadSysPatchParamName OBJECT-TYPE
    SYNTAX DisplayString (SIZE (0..64))
    MAX-ACCESS read-create
    STATUS current
    DESCRIPTION
        "The patch parameter name."
    ::= { cadSysPatchParamEntry 2 }

cadSysPatchParamValue OBJECT-TYPE
    SYNTAX DisplayString (SIZE (0..64))
    MAX-ACCESS read-create
    STATUS current
    DESCRIPTION
        "The patch parameter value."
    ::= { cadSysPatchParamEntry 3 }

cadSysPatchParamDescription OBJECT-TYPE
    SYNTAX DisplayString (SIZE (0..64))
    MAX-ACCESS read-create
    STATUS current
    DESCRIPTION
        "The patch parameter description."
    ::= { cadSysPatchParamEntry 4 }

cadSysPatchParamRowStatus OBJECT-TYPE
    SYNTAX     RowStatus
    MAX-ACCESS read-create
    STATUS     current
    DESCRIPTION
        "The row status variable used according to row installation
         and removal convention. In our case, we have simplified this
         to the usage of only the following states - active, createAndGo,
         and destroy. Other three states notInService, notReady and
         createAndWait are not permitted."
    ::= { cadSysPatchParamEntry 5 }


--=========== Maintenance Configuration ==============================

cadSysMtceStatusCloneMonitorThreshold OBJECT-TYPE
    SYNTAX     Unsigned32 (2750..6250)
    UNITS      "milliseconds"
    MAX-ACCESS read-write
    STATUS     current
    DESCRIPTION
        "Timeout during normal operation."
    DEFVAL { 6000 }
    ::= { cadSysMtceParams 8 }

cadSysMtceStatusCloneInitThreshold OBJECT-TYPE
    SYNTAX     Unsigned32 (3000..9000)
    UNITS      "milliseconds"
    MAX-ACCESS read-write
    STATUS     current
    DESCRIPTION
        "Timeout on initialization for first status message."
    DEFVAL { 7500 }
    ::= { cadSysMtceParams 9 }

cadSysMtceStatusCloneRcvyThreshold OBJECT-TYPE
    SYNTAX     Unsigned32 (120000..360000)
    UNITS      "milliseconds"
    MAX-ACCESS read-write
    STATUS     current
    DESCRIPTION
        "Timeout following clone side recovery."
    DEFVAL { 240000 }
    ::= { cadSysMtceParams 10 }

cadSysMtceBasePingRate OBJECT-TYPE
    SYNTAX     Unsigned32 (750..2250)
    UNITS      "milliseconds"
    MAX-ACCESS read-write
    STATUS     current
    DESCRIPTION
        "Interval between system maintenance polling of monitored threads."
    DEFVAL { 2000 }
    ::= { cadSysMtceParams 11 }

cadSysMtceOvSensitivity OBJECT-TYPE
    SYNTAX     OverloadThreshold
    MAX-ACCESS read-write
    STATUS     current
    DESCRIPTION
        "Defines the sensitivity of user overload to changes in
         internal work load.  Higher sensitivity results in more
         rapid change of user overload in response to a change in
         the internal work load."
    DEFVAL { med }
    ::= { cadSysMtceParams 12 }

cadSysMtceOvThreshold OBJECT-TYPE
    SYNTAX     OverloadThreshold
    MAX-ACCESS read-write
    STATUS     current
    DESCRIPTION
        "Defines the overall threshold of user overload transitions.
         Higher thresholds require a longer time in an internal overload
         state before user overload transitions occur."
    DEFVAL { med }
    ::= { cadSysMtceParams 13 }

cadSysMtceDULPacketInterval OBJECT-TYPE
    SYNTAX     Unsigned32(0|10000..900000)
    UNITS      "milliseconds"
    MAX-ACCESS read-write
    STATUS     current
    DESCRIPTION
        "Interval between maintenance polling of monitored BroadCom devices.
         Setting the value to zero will disable BroadCom device monitoring."
    DEFVAL { 10000 }
    ::= { cadSysMtceParams 14 }


--=========== Data Management ==============================--

cadSysDataServerDataTimeout OBJECT-TYPE
    SYNTAX     Unsigned32 (50000..500000)
    UNITS      "milliseconds"
    MAX-ACCESS read-write
    STATUS     current
    DESCRIPTION
        "Time allowed for Data Query/Update to be processed."
    DEFVAL { 50000 }
    ::= { cadSysDataServer 1 }


cadSysDataServerDataEventsPerCycle OBJECT-TYPE
    SYNTAX     Unsigned32 (10..200)
    UNITS      "events/cycle"
    MAX-ACCESS read-write
    STATUS     current
    DESCRIPTION
        "Number of data events allowed per cycle."
    DEFVAL { 40 }
    ::= { cadSysDataServer 2 }

cadSysDataServerDataSyncTimeout OBJECT-TYPE
    SYNTAX     Unsigned32 (8000..100000)
    UNITS      "milliseconds"
    MAX-ACCESS read-write
    STATUS     current
    DESCRIPTION
        "Number of data events allowed per cycle."
    DEFVAL { 80000 }
    ::= { cadSysDataServer 3 }

cadSysDataServerSnmpReadAheadEnable OBJECT-TYPE
    SYNTAX      TruthValue
    MAX-ACCESS read-write
    STATUS     current
    DESCRIPTION
        "When this value is set to true Snmp read ahead
         is performed."
    DEFVAL { true }
    ::= { cadSysDataServer 4 }

cadSysDataServerSnmpReadAheadMax OBJECT-TYPE
    SYNTAX     Unsigned32 (0..20)
    MAX-ACCESS read-write
    STATUS     current
    DESCRIPTION
        "This value is the maximum number of records to read ahead"
    DEFVAL { 1 }
    ::= { cadSysDataServer 5 }

cadSysDataServerSnmpRefreshTime OBJECT-TYPE
    SYNTAX     Unsigned32 (1..1200)
    UNITS      "seconds"
    MAX-ACCESS read-write
    STATUS     current
    DESCRIPTION
        "This value represents how old a database record can be to be used."
    DEFVAL { 1 }
    ::= { cadSysDataServer 6 }


cadSysDataServerSyncDataEventsPerCycle OBJECT-TYPE
    SYNTAX     Unsigned32 (40..100)
    UNITS      "events/cycle"
    MAX-ACCESS read-write
    STATUS     current
    DESCRIPTION
        "This value is the maximum number of Sync events that will be 
         processed per cycle."
    DEFVAL { 40 }
    ::= { cadSysDataServer 7 }


cadSysDataServerLoPriDataEventsPerCycle OBJECT-TYPE
    SYNTAX     Unsigned32 (10..100)
    UNITS      "events/cycle"
    MAX-ACCESS read-write
    STATUS     current
    DESCRIPTION
        "This value is the maximum number of Low Priority Sync events
         to be processed per cycle."
    DEFVAL { 10 }
    ::= { cadSysDataServer 8 }

--============================ Source Interface and Address ===========================

cadSysSourceAddressTable OBJECT-TYPE
    SYNTAX      SEQUENCE OF CadSysSourceAddressEntry
    MAX-ACCESS  not-accessible
    STATUS      current
    DESCRIPTION 
        "Table of source interface addresses for administrative services"
    ::= { cadSysSourceAddress 1 }

cadSysSourceAddressEntry OBJECT-TYPE
    SYNTAX          CadSysSourceAddressEntry
    MAX-ACCESS      not-accessible
    STATUS          current
    DESCRIPTION     "This entry contains the configured source IPv4 and/or IPv6 address for each administrative service. 
                     If configured, it also contains the global default address."
    INDEX { cadSysSourceAddressIndex }
    ::= { cadSysSourceAddressTable 1 }

CadSysSourceAddressEntry ::= SEQUENCE {
    cadSysSourceAddressIndex          AdminSrcAddrType,
    cadSysSourceInterfaceIpv4IfIndex  InterfaceIndexOrZero,  
    cadSysSourceAddressIpv4Address    InetAddressIPv4,
    cadSysSourceInterfaceIpv6IfIndex  InterfaceIndexOrZero,
    cadSysSourceAddressIpv6Address    InetAddressIPv6
}

cadSysSourceAddressIndex OBJECT-TYPE
    SYNTAX      AdminSrcAddrType
    MAX-ACCESS  not-accessible
    STATUS      current
    DESCRIPTION 
        "The type of administrative service."
    ::= { cadSysSourceAddressEntry 1 }

cadSysSourceInterfaceIpv4IfIndex OBJECT-TYPE
    SYNTAX      InterfaceIndexOrZero
    MAX-ACCESS  read-write
    STATUS      current
    DESCRIPTION
        "The ifIndex of the interface from which all IPv4 packets are sourced.
          For a server service, it is also the only DIP allowed for incoming requests.
          A value of 0 indicates no source interface override." 
    DEFVAL { 0 }
    ::= { cadSysSourceAddressEntry 2 }

cadSysSourceAddressIpv4Address OBJECT-TYPE
    SYNTAX      InetAddressIPv4
    MAX-ACCESS  read-only
    STATUS      current
    DESCRIPTION
        "The IPv4 address of the IPv4 interface at the time the row ipv4 ifIndex was populated.
         Used as the source address for the service if the state is in-service. 
         For a server service, it is also the only DIP allowed for incoming requests.
         A value of null indicates no source address has been assigned." 
       
    DEFVAL { "" }
    ::= { cadSysSourceAddressEntry 3 }


cadSysSourceInterfaceIpv6IfIndex OBJECT-TYPE
    SYNTAX      InterfaceIndexOrZero
    MAX-ACCESS  read-write
    STATUS      current
    DESCRIPTION
        "The ifIndex of the interface from which all IPv6 packets are sourced (not currently supported). 
          For a server service, it is also the only DIP allowed for incoming requests.
          A value of 0 indicates no source interface override." 
    DEFVAL { 0 }
    ::= { cadSysSourceAddressEntry 4 }

cadSysSourceAddressIpv6Address OBJECT-TYPE
    SYNTAX      InetAddressIPv6
    MAX-ACCESS  read-only
    STATUS      current
    DESCRIPTION
        "The IPv6 address of the IPv6 interface 
         at the time the ipv6 ifIndex was populated.
         Used as the source address for the service if the state is in-service.  
         For a server service, it is also the only DIP allowed for incoming requests.
         A value of null indicates no source address has been assigned." 

    DEFVAL { "" }
    ::= { cadSysSourceAddressEntry 5}

--========================== License Control ==========================--

cadSysLicenseCardId  OBJECT-TYPE
    SYNTAX      CardId
    MAX-ACCESS  not-accessible
    STATUS      current
    DESCRIPTION
        "CAM to be licensed."
    DEFVAL { 0 }
    ::= { cadSysLicenseControl 1 }

cadSysLicenseKey  OBJECT-TYPE
    SYNTAX      OCTET STRING (SIZE (16))
    MAX-ACCESS  not-accessible
    STATUS      current
    DESCRIPTION
        "License key to apply to the CAM."
    DEFVAL { ''h }
    ::= { cadSysLicenseControl 2 }

cadSysLicensePorts  OBJECT-TYPE
    SYNTAX      Integer32(0..5000)
    MAX-ACCESS  not-accessible
    STATUS      current
    DESCRIPTION
        "Number of CAM ports associated with the license."
    DEFVAL { 0 }
    ::= { cadSysLicenseControl 3 }

cadSysLicenseAnnex           OBJECT-TYPE
    SYNTAX      INTEGER {
         unknown(1),
         other(2),
         annexA(3),
         annexB(4),
         annexC(5)
        }
    MAX-ACCESS  not-accessible
    STATUS      current
    DESCRIPTION
        "This attribute defines the ITU-J-83 Annex being used
          for this E6000 CMTS License."
    DEFVAL { unknown }
    ::= { cadSysLicenseControl 4 }

cadSysLicenseStatus  OBJECT-TYPE
    SYNTAX      INTEGER
        {
            success(1),
            fail(2),
            pending(3),
            none(4)
        }
    MAX-ACCESS  read-only
    STATUS      current
    DESCRIPTION
        "Current status of licensing operation."
    DEFVAL { none }
    ::= { cadSysLicenseControl 5 }


--============================ LAES Mediation Device Timestamp Mode Table ===========================

cadLaesMdTimestampModeTable OBJECT-TYPE
    SYNTAX      SEQUENCE OF CadLaesMdTimestampModeEntry
    MAX-ACCESS  not-accessible
    STATUS      current
    DESCRIPTION 
        "Table of LAES Mediation Device Timestamp mode table"
    ::= { cadLaesMdTimestampMode 1 }

cadLaesMdTimestampModeEntry OBJECT-TYPE
    SYNTAX          CadLaesMdTimestampModeEntry
    MAX-ACCESS      not-accessible
    STATUS          current
    DESCRIPTION     "This entry contains the configured MD IPv4. 
                     If configured, then all encapsulated tap packets going to that MD will contain 
                     a timestamp in the tap header."
    INDEX { cadLaesMdTimestampModeInetAddrType,  cadLaesMdTimestampModeInetAddr}
    ::= { cadLaesMdTimestampModeTable 1 }

CadLaesMdTimestampModeEntry ::= SEQUENCE {
    cadLaesMdTimestampModeInetAddrType InetAddressType,
    cadLaesMdTimestampModeInetAddr     InetAddress,  
    cadLaesMdTimestampModRowStatus     RowStatus
}

cadLaesMdTimestampModeInetAddrType OBJECT-TYPE
    SYNTAX      InetAddressType
    MAX-ACCESS  not-accessible
    STATUS      current
    DESCRIPTION 
        "The IP Address type of Mediation Device"
    ::= { cadLaesMdTimestampModeEntry 1 }

cadLaesMdTimestampModeInetAddr OBJECT-TYPE
    SYNTAX      InetAddress
    MAX-ACCESS  not-accessible
    STATUS      current
    DESCRIPTION 
        "The IP Address of the Mediation Device."
    ::= { cadLaesMdTimestampModeEntry 2 }

cadLaesMdTimestampModRowStatus OBJECT-TYPE
    SYNTAX      RowStatus
    MAX-ACCESS  read-create
    STATUS      current
    DESCRIPTION
        "The row status of this entry" 
    ::= { cadLaesMdTimestampModeEntry 3 }

---========================= cadSysMICSecondarySecretTable ==========================--

cadSysMICSecondarySecretTable OBJECT-TYPE
    SYNTAX  SEQUENCE OF CadSysMICSecondarySecretEntry
    MAX-ACCESS not-accessible
    STATUS current
    DESCRIPTION
        "Table containing secondary shared secret strings for
         cable modem configuration file authentication. This
         table is not used unless cadSysMICEnable is set to
         true."
    ::= { cadSysSharedSecret 1 }

cadSysMICSecondarySecretEntry OBJECT-TYPE
    SYNTAX CadSysMICSecondarySecretEntry
    MAX-ACCESS not-accessible
    STATUS current
    DESCRIPTION
        "Entry containing secondary shared secret strings for
         cable modem configuration file authentication."
    INDEX { cadSysMICSecondarySecretIndex }
    ::= { cadSysMICSecondarySecretTable 1 }

CadSysMICSecondarySecretEntry ::= SEQUENCE {
    cadSysMICSecondarySecretIndex     INTEGER,
    cadSysMICSecondarySecretString    OCTET STRING,
    cadSysMICSecondarySecretStatus    RowStatus
}

cadSysMICSecondarySecretIndex OBJECT-TYPE
    SYNTAX INTEGER (1..1)
    MAX-ACCESS not-accessible
    STATUS current
    DESCRIPTION 
        "Internal index for this MIB row."
    ::= { cadSysMICSecondarySecretEntry 1 }

cadSysMICSecondarySecretString OBJECT-TYPE
    SYNTAX OCTET STRING (SIZE (0..64))
    MAX-ACCESS read-create
    STATUS current
    DESCRIPTION 
        " Encrypted MIC Authentication shared secret string."
    ::= { cadSysMICSecondarySecretEntry 2 }

cadSysMICSecondarySecretStatus OBJECT-TYPE
    SYNTAX RowStatus
    MAX-ACCESS read-create
    STATUS current
    DESCRIPTION 
        "The status of this conceptual row."
    ::= { cadSysMICSecondarySecretEntry 3 }

---
--- Conformance information
---
cadSystemMibConformance OBJECT IDENTIFIER ::= { cadSystemMib 12 } 
cadSystemCompliances OBJECT IDENTIFIER ::= { cadSystemMibConformance 1 } 
cadSystemGroups OBJECT IDENTIFIER ::= { cadSystemMibConformance 2 } 

cadSystemCompliance MODULE-COMPLIANCE
    STATUS current
    DESCRIPTION
        "Compliance statement for entities implementing the Cadant System Mib."
    MODULE -- this module
    MANDATORY-GROUPS { 
        cadSysParamsGroup, cadSysSystemGroup,
        cadSysControlGroup, cadSysSnmpGroup,
        cadSysBootParamsGroup, cadSysReloadGroup,
        cadSysImageGroup, cadSysDataServerGroup,
        cadSysSourceAddressGroup }

    ::= { cadSystemCompliances 1 }

cadSysParamsGroup OBJECT-GROUP
    OBJECTS {
        cadSysSyncInterval,
        cadSysUCDInterval,
        cadSysMaxMAPPending,
        cadSysRangingInterval,
        cadSysInvitedRangingRetries,
        cadSysRegistrationRequestRetries,
        cadSysCMMAPProcessingTime,
        cadSysCMConfiguration,
        cadSysT5Timeout,
        cadSysT6Timeout,
        cadSysMiniSlotSize,
        cadSysDSxRequestRetries,
        cadSysT7Timeout,
        cadSysT8Timeout,
        cadSysT9Timeout,
        cadSysT10Timeout,
        cadSysT11Timeout,
        cadSysT13Timeout,
        cadSysDCCREQRetries,
        cadSysMICEnable,
        cadSysMICAuthString,
        cadSysAutoRecoveryEnable,
        cadSysActiveIpAddress,
        cadSysSpOperMode,
        cadSysMaxQoSActiveTimeout,
        cadSysMaxQoSAdmittedTimeout,
        cadSysAllow10CmConcatenation,
        cadSysAllow10CmFragmentation,
        cadSysPercentAddtlDsBwAllocated,
        cadSysMaxTrafBurstFor11CMs,
        cadSysRemoteFSEnable,
        cadSysRemotePortEnable,
        cadSysTcpSmoothingValue1D8U,
        cadSysTcpSmoothingValue2D12U,
        cadSysModemLossThreshold,
        cadSysPeakTrafRateFor11CMs,
        cadSysCpeHostAuthorization
    }
    STATUS current
    DESCRIPTION 
        "System parameter objects"
    ::= { cadSystemGroups 1 }

cadSysSystemGroup OBJECT-GROUP
    OBJECTS {
        cadSysContact,
        cadSysName,
        cadSysLocation
    }
    STATUS current
    DESCRIPTION 
        "System description objects"
    ::= { cadSystemGroups 2 }

cadSysControlGroup OBJECT-GROUP
    OBJECTS {
        cadSysWriteMem,
        cadSysEraseMem
    }
    STATUS deprecated
    DESCRIPTION 
        "System control objects"
    ::= { cadSystemGroups 3 }

cadSysSnmpGroup OBJECT-GROUP
    OBJECTS {
        cadSysEnableAuthenTraps,
        cadSysSnmpReadAheadMax,
        cadSysSnmpRefreshTime
    }
    STATUS current
    DESCRIPTION 
        "System snmp control object"
    ::= { cadSystemGroups 4 }

cadSysBootParamsGroup OBJECT-GROUP
    OBJECTS {
        cadSysBootMacAddress,
        cadSysBootFpIpAddress,
        cadSysBootFpSubnetMask,
        cadSysBootDefaultGateway,
        cadSysBootTimeOffset,
        cadSysBootTimeServer,
        cadSysBootTimeServerConnType,
        cadSysBootStartupApplication,
        cadSysBootStartupDelay,
        cadSysBootSelection
    }
    STATUS current
    DESCRIPTION 
        "System boot parameters objects"
    ::= { cadSystemGroups 5 }

cadSysReloadGroup OBJECT-GROUP
    OBJECTS {
        cadSysReloadImageName,
        cadSysReloadOperation,
        cadSysReloadStatus
    }
    STATUS current
    DESCRIPTION 
        "System reload control objects"
    ::= { cadSystemGroups 6 }

cadSysImageGroup OBJECT-GROUP
    OBJECTS {
        cadSysImageFile,
        cadSysImageId,
        cadSysImageName,
        cadSysImageComponentCount
    }
    STATUS current
    DESCRIPTION 
        "System image status objects"
    ::= { cadSystemGroups 7 }

cadSysConfigurationGroup OBJECT-GROUP
    OBJECTS {
        cadSysConfigSaveTime
    }
    STATUS current
    DESCRIPTION 
        "Configuration objects"
    ::= { cadSystemGroups 8 }


cadSysDataServerGroup OBJECT-GROUP
    OBJECTS {
        cadSysDataServerDataTimeout,
        cadSysDataServerDataEventsPerCycle,
        cadSysDataServerDataSyncTimeout,
        cadSysDataServerSnmpReadAheadEnable,
        cadSysDataServerSnmpReadAheadMax,
        cadSysDataServerSnmpRefreshTime,
        cadSysDataServerSyncDataEventsPerCycle,
        cadSysDataServerLoPriDataEventsPerCycle
    }
    STATUS current
    DESCRIPTION 
        "Configuration objects"
    ::= { cadSystemGroups 9 }

cadSysSourceAddressGroup OBJECT-GROUP
    OBJECTS {
        cadSysSourceInterfaceIpv4IfIndex,
        cadSysSourceAddressIpv4Address,
        cadSysSourceInterfaceIpv6IfIndex,
        cadSysSourceAddressIpv6Address
    }
    STATUS current
    DESCRIPTION 
        "Source Interface objects."
    ::= { cadSystemGroups 10 }

END -- end of CADANT-CMTS-SYSTEM-MIB
