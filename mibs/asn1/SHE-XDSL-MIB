--
-- she-xdsl-mib.mib
-- MIB generated by MG-SOFT Visual MIB Builder Version 6.0  Build 88
-- Tuesday, August 11, 2009 at 09:38:53
--

-- Start of ClearCase branch-information of current release:
-- she-xdsl-mib.mib   /main/she_main_grf/34
-- End of ClearCase branch-information.
-- 

	SHE-XDSL-MIB DEFINITIONS ::= BEGIN
 
		IMPORTS
			she			
				FROM AN-MIB			
			HCPerfValidIntervals, HCPerfInvalidIntervals, HCPerfTimeElapsed, HCPerfCurrentCount, HCPerfIntervalCount, 
			HCPerfIntervalThreshold			
				FROM HC-PerfHist-TC-MIB			
			ifIndex, InterfaceIndex			
				FROM IF-MIB			
			sheAlarmTimeAndDate, sheAlarmReportingSource, sheAlarmReportingSourceType, sheAlarmSeverity, SheAlarmSevProfileIndex			
				FROM SHE-ALARMING-MIB			
			SheControlStatusType			
				FROM SHE-TC-MIB			
			SnmpAdminString			
				FROM SNMP-FRAMEWORK-MIB			
			OBJECT-GROUP, MODULE-COMPLIANCE, NOTIFICATION-GROUP			
				FROM SNMPv2-CONF			
			Integer32, Unsigned32, Gauge32, Counter32, Counter64, 
			OBJECT-TYPE, MODULE-IDENTITY, NOTIFICATION-TYPE			
				FROM SNMPv2-SMI			
			TruthValue, TEXTUAL-CONVENTION			
				FROM SNMPv2-TC;
	
	
		sheXdslMib MODULE-IDENTITY 
			LAST-UPDATED "200908111600Z"		-- August 11, 2009 at 16:00 GMT
			ORGANIZATION 
				"Nokia Siemens Networks"
			CONTACT-INFO 
				"Gerd Barchmann
				COO BCS BBA RD SDE HW1
				
				gerd.barchmann@nsn.com
				+49 3834 555654"
			DESCRIPTION 
				"The MIB module defining objects for the management of a pair 
				of xDSL transceivers at each end of the xDSL line.  Each such
				line has an entry in an ifTable with ifType 97 (VDSL) or 230 (ADSL2)
				An agent may reside at either end of the xDSL line. However, the MIB
				is designed to require no management communication between them beyond
				that inherent in the low-level xDSL line protocol. The agent may monitor
				and control this protocol for its needs.
				
				xDSL lines may support optional more then one channel.
				
				Naming Conventions:
				    Xtuc -- transceiver at near (Central) end of line
				    Xtur -- transceiver at Remote end of line
				    Xtu  -- One of either Xtuc or Xtur
				    Curr -- Current
				    Prev -- Previous
				    Atn  -- Attenuation
				    ES   -- Errored Second.
				    SES  -- Severely Errored Second
				    UAS  -- Unavailable Second
				    LCS  -- Line Code Specific
				    Lof  -- Loss of Frame
				    Lol  -- Loss of Link
				    Los  -- Loss of Signal
				    Lpr  -- Loss of Power
				    xxxs -- Sum of Seconds in which xxx has occured
				            (e.g., xxx = Lof, Los, Lpr, Lol)
				    Max  -- Maximum
				    Mgn  -- Margin
				    Min  -- Minimum
				    Psd  -- Power Spectral Density
				    Snr  -- Signal to Noise Ratio
				    Tx   -- Transmit
				    Blks -- Blocks
				
				"
			REVISION "200612151440Z"		-- December 15, 2006 at 14:40 GMT
			DESCRIPTION 
				"Modify handling for DSL-Channel configuration (UseChannelProfiles).
				Modify DSLLineProfile configuration.
				Restrict range for DownPboFMin/Max in extension profile.
				Restrict range for sheXdslPsdMaskProfileSubcarrierIndex.
				Restrict range for sheXdslCustomNotchProfileStartIndex/StopIndex.
				Add value for GsAction - switching in lineTable.
				Add HW port alarm.
				Modify range and description for sheXdslLineConfExtnCustomSubcarrierMask."
			REVISION "200701181315Z"		-- January 18, 2007 at 13:15 GMT
			DESCRIPTION 
				"Move RateTreshold configuration from AlarmProfile to ChannelProfile according G997.1 standard.
				Use new ChannelRateThreshold trap's.
				Add Ranges for sheXdslLineDeltStatusControlSCGxx parameters.
				Correct Unit and Ranges for L2-ATPR and L2-ATPRT in extension profile.
				Reduce range for MaxXXNomPsd in extension profile."
			REVISION "200701231252Z"		-- January 23, 2007 at 12:52 GMT
			DESCRIPTION 
				"Change BaseOID to 14 because numbering conflict with china specific MIB."
			REVISION "200702051011Z"		-- February 05, 2007 at 10:11 GMT
			DESCRIPTION 
				"Correct description for sheXdslChannelProfileMaxBerUs.
				Add status parameter sheXdslLineUpPboKLE to lineTable.
				Add enum showTimeLock to SheXdslLineGsActionType.
				Correct description of xdslChannel InterleaveDelay and inp
				configuration and add some preconditions. 
				Correct range for xdslChannelInterleaveDelay parameter."
			REVISION "200703071106Z"		-- March 07, 2007 at 11:06 GMT
			DESCRIPTION 
				"Add new possible VDSL2 bandplan values to SheVdsl2BandPlanType.
				Correct description for sheXdslLineConfExtnUpPboA and sheXdslLineConfExtnUpPboB.
				Correct description for sheXdslLineConfUseVdsl2ProfileNumber."
			REVISION "200703210827Z"		-- March 21, 2007 at 08:27 GMT
			DESCRIPTION 
				"New SHE R2.5.2 version.
				Add sheXdslLinePMSF value to line-table.
				Move ChannelProfile assignment from lineProfile directly to lineTable.
				Add sheXdslVccTpPerformance-Table.
				Add name to sheXdslPsdMaskProfileCreated trap."
			REVISION "200704111543Z"		-- April 11, 2007 at 15:43 GMT
			DESCRIPTION 
				"Modifications after review of AFI MIB release.
				Add new testvalue to GSAction parameter.
				Support configuration of minimum overhead rate via extn. profile."
			REVISION "200705091116Z"		-- May 09, 2007 at 11:16 GMT
			DESCRIPTION 
				"Correct some referenz descriptions."
			REVISION "200705141452Z"		-- May 14, 2007 at 14:52 GMT
			DESCRIPTION 
				"Expand Channel-Table's with atm status and performance parameters."
			REVISION "200706111445Z"		-- June 11, 2007 at 14:45 GMT
			DESCRIPTION 
				"Modify description for sheXdslLineConfExtnCustomSubcarrierMask.
				Add UsPSDMaskSelection to extn. profile for Adsl annex M support (with RP2 of R2.6).
				Add UsSubcarrierMask to extn. profile (with RP2 of R2.6). "
			REVISION "200707091127Z"		-- July 09, 2007 at 11:27 GMT
			DESCRIPTION 
				"Expand enum for VDSL2 bandplan configuration.
				Add sheXdslSCDnStatusTss/sheXdslSCUpStatusTss parameter to sheXdslSCxxStatusTable (RP2).
				Add sheXdslShowtimeStatusMRefPsdDs/sheXdslShowtimeStatusMRefPsdUs parameter to sheXdslLineDeltStatusControl(RP2).
				Remove support for sheXdslLineConfExtnDownPboMof in extnProfileTable(RP2)."
			REVISION "200707191013Z"		-- July 19, 2007 at 10:13 GMT
			DESCRIPTION 
				"Add support of xdsl standard ansiT1413.
				Modify description for INP=0.
				Add statusvariable for last transmitted state to sheXdslPhysTable (RP2).
				Correct ranges for DPBOFMin and DPBOFMAx in extension profile (RP2).
				Add support of indiviual SC group sizes for each SCGxxStatusTable entry (RP2)."
			REVISION "200708210949Z"		-- August 21, 2007 at 09:49 GMT
			DESCRIPTION 
				"Add new paramter: 
				- ACTPSD to phys. table, 
				- SNRMODE and TXREFVN to extn. profile.
				Modify description for bandtable parameters and
				define an additional special value for outOfRange."
			REVISION "200709200935Z"		-- September 20, 2007 at 09:35 GMT
			DESCRIPTION 
				"Small descriptional modifications for extn. profile SubcarrierMask parameters.
				Correct syntax for Hlin status parameters."
			REVISION "200710171152Z"		-- October 17, 2007 at 11:52 GMT
			DESCRIPTION 
				"New release SHE R2.7 supported.
				Storage of line and channel history performance counter intervals could be switched on/off.
				Counting of vccTp performance could be switched on/off."
			REVISION "200711151453Z"		-- November 15, 2007 at 14:53 GMT
			DESCRIPTION 
				"Add support for linestandard g992.3 and g992.5 Annex J.
				New default profilename for VDSL over Pots cards.
				Correct references for physTable parameters.
				Correct syntax for sheXdslPhysCurrOutputPwr.
				Correct syntax and range for sheXdslShowtimeStatusMRefPsdxx."
			REVISION "200711231108Z"		-- November 23, 2007 at 11:08 GMT
			DESCRIPTION 
				"Modify comment for usable VccTp VCI range under special conditions."
			REVISION "200712051247Z"		-- December 05, 2007 at 12:47 GMT
			DESCRIPTION 
				"Add selftest result to phys table (CO hiX13602).
				Move Tssi Statusparameter from XdslSCxxStatusTable to XdslLineStatusControlGroup."
			REVISION "200802221349Z"		-- February 22, 2008 at 13:49 GMT
			DESCRIPTION 
				"Correct description of minInp value 0 -> null!"
			REVISION "200803191051Z"		-- March 19, 2008 at 10:51 GMT
			DESCRIPTION 
				"- Add parameters sheXdslSCDnStatusTss and sheXdslSCUpStatusTss for backward compatibility.
				They are obsolete and will not be used by R2.7 and followings.
				- Add detailed failure returncode definitions to ReqResult enum. 
				The scheduled support release is not defined yet."
			REVISION "200804071308Z"		-- April 07, 2008 at 13:08 GMT
			DESCRIPTION 
				"Rename LineRate parameters in sheXdslPhysTable - NO functional modification!
				Modify description of sheXdslPhysCurrStatus parameter."
			REVISION "200804251115Z"		-- April 25, 2008 at 11:15 GMT
			DESCRIPTION 
				"Correct description for sheXdslChannelProfileMaxInterleaveDelayxx.
				Correct description for AlarmThreshold configuration."
			REVISION "200804281049Z"		-- April 28, 2008 at 10:49 GMT
			DESCRIPTION 
				"Correct description for sheXdslChannelProfileMaxInterleaveDelayxx again."
			REVISION "200805211207Z"		-- May 21, 2008 at 12:07 GMT
			DESCRIPTION 
				"Add new default lineprofile for AnnexJ support."
			REVISION "200805301145Z"		-- May 30, 2008 at 11:45 GMT
			DESCRIPTION 
				"Add timestamp parameter to 24h interval tables."
			REVISION "200807241003Z"		-- July 24, 2008 at 10:03 GMT
			DESCRIPTION 
				"Modify syntax for sheXdslChanCurrInp parameter."
			REVISION "200809181541Z"		-- September 18, 2008 at 15:41 GMT
			DESCRIPTION 
				"Correct syntax for CurrentINP value."
			REVISION "200810081009Z"		-- October 08, 2008 at 10:09 GMT
			DESCRIPTION 
				"Add new detailed ReqResult failure code definitions."
			REVISION "200810201501Z"		-- October 20, 2008 at 15:01 GMT
			DESCRIPTION 
				"Modify parameter range for PSDMaskProfile subcarrier configuration."
			REVISION "200901300836Z"		-- January 30, 2009 at 08:36 GMT
			DESCRIPTION 
				"Modify some descriptions. No functional changes."
			REVISION "200902241535Z"		-- February 24, 2009 at 15:35 GMT
			DESCRIPTION 
				"Correct coding for VN configuration. "
			REVISION "200906031443Z"		-- June 03, 2009 at 14:43 GMT
			DESCRIPTION 
				"Expand range for MaxSnr configuration."
			REVISION "200908111628Z"		-- August 11, 2009 at 16:28 GMT
			DESCRIPTION 
				"Replace bandplan-type definition bandPlanAnnexB997E17M2XNUS0(108) with
				bandPlanAnnexB997E17M2XA(108) because of G993.2 definition update.
				Add parameter and control to enable config violation checks via alarm profile.
				Correct description for indeces of sheXdslSCDnStatusTable and sheXdslSCUpStatusTable. "
			::= { she 14 }

		
	
--
-- Type definitions
--
	
		SheXdslLineGsActionType ::= INTEGER
			{
			startup(0),
			forcePMSL2(2),
			spectrumReverb(5),
			atmLb(10),
			spectrumMedley(26),
			showTimeLock(39),
			returnLoss(40)
			}

--  info - IMPL: ..AnnexJ R2.7->
		SheXdslLineStandardType ::= BITS
			{
			ansiT1413(0),
			g9921AdslPotsNonOverlapped(2),
			g9921AdslIsdnNonOverlapped(4),
			g9923Adsl2PotsNonOverlapped(18),
			g9923Adsl2IsdnNonOverlapped(20),
			g9923ADMAdsl2NonOverlappedAnnexJ(30),
			g9923ReachExtAdsl2PotsNonOverlappedM1(34),
			g9923ReachExtAdsl2PotsNonOverlappedM2(35),
			g9923ExtUpAdsl2PotsNonOverlapped(38),
			g9925Adsl2PlusPotsNonOverlapped(40),
			g9925Adsl2PlusIsdnNonOverlapped(42),
			g9925ADMAdsl2PlusNonOverlappedAnnexJ(48),
			g9925ExtUpAdsl2PlusPotsNonOverlapped(50),
			g9932Vdsl2NonOverlappedRegionA(56),
			g9932Vdsl2NonOverlappedRegionB(57),
			g9932Vdsl2NonOverlappedRegionC(58)
			}

		SheXdslLineRfiBandMaskType ::= BITS
			{
			amateurBand1(1),
			amateurBand2(2),
			amateurBand3(3),
			amateurBand4(4),
			amateurBand5(5),
			gmdssBand1(6),
			gmdssBand2(7),
			gmdssBand3(8)
			}

		SheXdslControlRequestType ::= INTEGER
			{
			noRequest(1),
			createXdslLineConfProfile(150),
			modifyXdslLineConfProfile(151),
			deleteXdslLineConfProfile(152),
			modifyXdslLineConfExtnProfile(153),
			modifyXdslLineEntry(201),
			modifyXdslLineAlarmConfProfileEntry(202),
			modifyXdslLineDeltState(205),
			getXdslLineDeltResult(206),
			getXdslLineShowtimeStatusResult(207),
			setXdslLineDownPsdMaskProfileEntry(210),
			setXdslLineUpPsdMaskProfileEntry(211),
			setXdslLineNotchConfiguration(212),
			modifyXdslLinePMSFState(215),
			setXdslLineForceInpConfiguration(220),
			setXdslLineChannelProfileConfiguration(221),
			modifyXdslLinePerformanceHistory(222),
			createXdslLineAlarmConfProfile(250),
			modifyXdslLineAlarmConfProfile(251),
			deleteXdslLineAlarmConfProfile(252),
			createXdslPsdMaskProfile(340),
			modifyXdslPsdMaskProfile(341),
			deleteXdslPsdMaskProfile(342),
			createXdslCustomNotchProfile(350),
			modifyXdslCustomNotchProfile(351),
			deleteXdslCustomNotchProfile(352),
			createXdslChannelProfileEntry(401),
			modifyXdslChannelProfileEntry(402),
			deleteXdslChannelProfileEntry(403)
			}

--  info - IMPL: detailed Results R2.8 ->
		SheXdslControlRequestResultType ::= INTEGER
			{
			noRequest(1),
			comExecStarted(30),
			paramFaulty(31),
			requestBusy(32),
			setDataFailed(34),
			aswTimeout(35),
			commandFailed(36),
			commandSucceeded(37),
			profileAssignmentFailed(51),
			profileNameStringUnknown(2001),
			profileNameToLong(2002),
			profileNameAlreadyExist(2003),
			maxNumberOfProfilesReached(2004),
			profileNotExist(2005),
			profileAssignFailOnActivePort(2006),
			profileTypDefaultCouldNotModified(2010),
			profileModifyFailOnInvalidArguments(2012),
			profileModifyFailOnInvalidMarginSettings(2013),
			profileModifyFailOnInvalidDataRateSettings(2014),
			profileVdslProfileTypModifyFailOnAssignedProfiles(2015),
			profileGsStandardModifyFailOnAssignedProfiles(2016),
			profileModifyFailOnSelectedGsStandardConflict(2017),
			profileDpboModifyFailOnInvalidParameters(2018),
			internalFailureWriteToDataBase(2020),
			internalFailureReadFromDataBase(2021),
			profileUsedByActivePorts(2022),
			profileInUseCouldNotBeDeleted(2023),
			internalFailureDuringIuCommunication(2030),
			portNumberNotExist(2040),
			portNumberHasWrongDSLType(2041),
			profileChannel1ProfileMissing(2051),
			profileChannelRatioSetFailed(2052),
			profileMinBitRateToHighForADSL(2053),
			internalFailurePortNotDualLatency(2054),
			internalFailureIuNotAvailable(2060),
			assignmentFailureOnActivePorts(2061),
			requestFailureOnDisabledPorts(2062),
			requestFailureOnDataNotAvailable(2065),
			requestFailureOnDeltTestNotCompleted(2066),
			profileNotchConfigFailedOnTooMuchNotches(2070),
			profileNotchConfigFailedOnInvalidNotches(2071),
			profilePsdConfigFailedOnTooMuchBreakpoints(2075),
			profilePsdConfigFailedOnInvalidBreakpoints(2076),
			profileConfigFailedOnProfileInUse(2080)
			}

		SheXdslPwrMgmtStateType ::= INTEGER
			{
			syncL0(0),
			pwrDownL1(1),
			pwrDownL2(2),
			noPwrL3(3)
			}

		SheXdslChanCurrAtmStatusType ::= BITS
			{
			noDefect(0),
			ncd(1),
			lcd(2)
			}

		SheXdslProfileRateModeType ::= INTEGER
			{
			fixed(1),
			adaptAtInit(2),
			adaptAtRuntime(3)
			}

		SheXdslEnableType ::= INTEGER
			{
			enable(1),
			disable(2)
			}

		SheXdslXtucPwrMgmtModeType ::= INTEGER
			{
			disable(0),
			l3Enabled(1),
			l1l2Enabled(2),
			l1l2l3Enabled(3)
			}

		SheXdslLineConfUsPSDMaskSelectionType ::= INTEGER
			{
			adlu32eu32(1),
			adlu36eu36(2),
			adlu40eu40(3),
			adlu44eu44(4),
			adlu48eu48(5),
			adlu52eu52(6),
			adlu56eu56(7),
			adlu60eu60(8),
			adlu64eu64(9)
			}

		SheXdsl2LineDirectionType ::= INTEGER
			{
			downstream(1),
			upstream(2)
			}

		SheXdslLineBandNumberType ::= INTEGER
			{
			band0(1),
			band1(2),
			band2(3),
			band3(4),
			band4(5)
			}

		SheXdslConfMinInpType ::= INTEGER
			{
			null(0),
			use1Symbol(1),
			use2Symbols(2),
			use3Symbols(3),
			use4Symbols(4),
			use5Symbols(5),
			use6Symbols(6),
			use7Symbols(7),
			use8Symbols(8),
			use9Symbols(9),
			use10Symbols(10),
			use11Symbols(11),
			use12Symbols(12),
			use13Symbols(13),
			use14Symbols(14),
			use15Symbols(15),
			use16Symbols(16),
			useHalfSymbol(50)
			}

		SheXdslMaxErrorRateType ::= INTEGER
			{
			eMinus3(0),
			eMinus5(1),
			eMinus7(2)
			}

		SheXdslVccTpEncapsulationType ::= INTEGER
			{
			llc(1),
			vcMux(2)
			}

		SheXdslOamLoopTestType ::= INTEGER
			{
			none(0),
			endToEnd(2)
			}

		SheXdslVccTpLoopTestResultType ::= INTEGER
			{
			endToEndSuccess(2),
			endToEndFailure(3),
			aborted(4),
			progress(5),
			notAvailable(65535)
			}

		SheXdslVccControlRequestType ::= INTEGER
			{
			noRequest(1),
			createDslVccTp(301),
			deleteDslVccTp(302),
			modifyDslVccTp(303),
			modifyDslVccTpLoopTest(304),
			modifyDslVccTpAdminState(305),
			modifyDslVccTpUsedDslChannel(311),
			deleteDslVccTpPerformanceCounters(315),
			modifyDslVccTpPerformanceCountEnable(316)
			}

		SheXdslLineConfAdslPresenceType ::= INTEGER
			{
			none(1),
			adslOverPots(2),
			adslOverISDN(3)
			}

		SheXdslLineConfRfiBandMaskType ::= BITS
			{
			customNotchProfile(0),
			amateurBand1(1),
			amateurBand2(2),
			amateurBand3(3),
			amateurBand4(4),
			amateurBand5(5),
			gmdssBand1(6),
			gmdssBand2(7),
			gmdssBand3(8)
			}

	
--
-- Textual conventions
--
	
		SheXdslLineLdsfType ::= TEXTUAL-CONVENTION
			STATUS current
			DESCRIPTION 
				"Attributes with this syntax are configuration parameters
				that control the Loop Diagnostic mode for the xDSL2 link.
				The possible values are:
				  inhibit (0)  - Inhibit Loop Diagnostic mode
				  force   (1)  - Force/Initiate Loop Diagnostic mode"
			SYNTAX INTEGER
				{
				inhibit(0),
				force(1)
				}

		SheXdslLineLdsfResultType ::= TEXTUAL-CONVENTION
			STATUS current
			DESCRIPTION 
				"Possible failure reasons associated with performing
				Dual Ended Loop Test (DELT) on a DSL line.
				Possible values are:
				 none        (1) - The default value in case LDSF was never
				                   requested for the associated line.
				 success     (2) - The recent command completed
				                   successfully.
				 inProgress  (3) - The Loop Diagnostics process is in
				                   progress.
				 unsupported (4) - The NE or the line card doesn't support
				                   LDSF.
				 cannotRun   (5) - The NE cannot initiate the command, due
				                   to a non specific reason.
				 aborted     (6) - The Loop Diagnostics process aborted.
				 failed      (7) - The Loop Diagnostics process failed.
				 illegalMode (8) - The NE cannot initiate the command, due
				                   to the specific mode of the relevant
				                   line.
				 adminUp     (9) - The NE cannot initiate the command, as
				                   the relevant line is administratively
				                   'Up'.
				 tableFull   (10)- The NE cannot initiate the command, due
				                   to reaching the maximum number of rows
				                   in the results table.
				 noResources (11)- The NE cannot initiate the command, due
				                   to lack of internal memory resources."
			SYNTAX INTEGER
				{
				none(1),
				success(2),
				inProgress(3),
				unsupported(4),
				cannotRun(5),
				aborted(6),
				failed(7),
				illegalMode(8),
				adminUp(9),
				noResources(11)
				}

		SheXdslPMSFType ::= TEXTUAL-CONVENTION
			STATUS current
			DESCRIPTION 
				"L3 mode --> no traffic
				L0 mode --> line runs in normal power
				L2 mode --> line runs in reduced power"
			SYNTAX INTEGER
				{
				none(0),
				pmsfL0ToL2StateForce(1),
				pmsfL2ToL0StateForce(3)
				}

		SheXdslLineEntity ::= TEXTUAL-CONVENTION
			STATUS current
			DESCRIPTION 
				"Identifies a transceiver as being either Xtuc or Xtur.  
				A XDSL line consists of two transcievers, a Xtuc and a 
				Xtur. Attributes with this syntax reference the two sides 
				of a line.  Specified as an INTEGER, the two values are:
				
				xtuc(1)  -- central site transceiver
				xtur(2)  -- remote site transceiver"
			SYNTAX INTEGER
				{
				xtuc(1),
				xtur(2)
				}

		SheXdslPhysCurrStatusType ::= TEXTUAL-CONVENTION
			STATUS current
			DESCRIPTION 
				"The various bit positions are:
				
				0   noDefect             There are no defects on the line.
				
				1   lossOfFraming        xtu failure due to not receiving a valid frame.
				
				2   lossOfSignal         xtu failure due to not receiving signal.
				
				3   lossOfPower          xtu failure due to loss of power.
				
				4   lossOfSignalQuality  Loss of Signal Quality is declared when the Noise Margin falls below 
				                         the Minimum Noise Margin, or the bit-error-rate exceeds the configured BER value.
				
				5   lossOfLink           xtu failure due to inability to link with peer xtu. Set whenever
				                         the transceiver is in the 'Warm Start' state.
				
				6   dataInitFailure      xtu failure during initialization due to bit errors corrupting
				                         startup exchange data.
				
				7   configInitFailure    xtu failure during initialization due to peer xtu not able to 
				                         support requested configuration. That will map to 'That will map to
				                         'Configuration not feasible on the line' (2) failure from
				                         G997.1 chapter 7.5.1.6.
				
				8   protocolInitFailure  xtu failure during initialization due to incompatible protocol used 
				                         by the peer xtu. That will map to 'communication problem' (3) failure
				                         from G997.1 chapter 7.5.1.6.
				
				9   noPeerVtuPresent     xtu failure during initialization due to no activation sequence 
				                         detected from peer xtu. That will map to 'No peer xTU detected' (4) failure
				                         from G997.1 chapter 7.5.1.6.
				
				All failures with no single mapping to G997.1 parameters should be understand as a more detailed map to
				'Any other or unknown Initialization Failure cause' (5) from G997.1 chapter 7.5.1.6."
			SYNTAX BITS
				{
				noDefect(0),
				lossOfFraming(1),
				lossOfSignal(2),
				lossOfPower(3),
				lossOfSignalQuality(4),
				lossOfLink(5),
				dataInitFailure(6),
				configInitFailure(7),
				protocolInitFailure(8),
				noPeerVtuPresent(9)
				}

		SheXdslPhysCurrOperationalStateType ::= TEXTUAL-CONVENTION
			STATUS current
			DESCRIPTION 
				"Indicates current operational state of the Xtu line."
			SYNTAX INTEGER
				{
				notInitialized(0),
				exception(1),
				idleRequest(255),
				idle(256),
				silentRequest(511),
				silent(512),
				handshake(768),
				fullInit(896),
				discovery(1024),
				training(1280),
				analysis(1536),
				exchange(1792),
				showtimeNoSync(2048),
				showtimeSync(2049),
				fastRetrain(2304),
				lowPowerL2(2560),
				loopActive(2816),
				loopDataExchange(2832),
				loopComplete(3072),
				resync(3328),
				test(16777216),
				lowPowerL3(33554432),
				unknown(50331648)
				}

		SheXdslLastStateTransmittedType ::= TEXTUAL-CONVENTION
			STATUS current
			DESCRIPTION 
				"This parameter must be interpreted along with the xDSL Transmission
				System. Last_TX_State.
				
				NOTE:
				State 0 .. 11 are identical for central office and remote side.
				State 12 .. 32 have different meanings on central office and remote side."
			SYNTAX INTEGER
				{
				g9941(0),
				quiet1(1),
				comb1(2),
				quiet2(3),
				comb2(4),
				icomb1(5),
				lineprobe(6),
				quiet3(7),
				comb3(8),
				icomb2(9),
				msgfmt(10),
				msgpcb(11),
				cQuiet4rReverb1(12),
				cReverb1rQuiet4(13),
				cTref1rReverb2(14),
				cReverb2rQuiet5(15),
				cEctrReverb3(16),
				cReverb3rEct(17),
				cTref2rReverb4(18),
				cReverb4rSegue1(19),
				cSegue1rReverb5(20),
				cMsg1rSegue2(21),
				cReverb5rMsg1(22),
				cSegue2rMedley(23),
				cMedleyrExchmarker(24),
				cExchmarkerrMsg2(25),
				cMsg2rReverb6(26),
				cReverb6rSegue3(27),
				cSegue3rParams(28),
				cParamsrReverb7(29),
				cReverb7rSegue4(30),
				cSegue4rShowtime(31),
				cShowtime(32),
				notAvailable(255)
				}

		SheXdslChannelNumType ::= TEXTUAL-CONVENTION
			STATUS current
			DESCRIPTION 
				"The used dsl bearer channel number."
			SYNTAX INTEGER
				{
				channel1(1),
				channel2(2)
				}

		SheVdsl2BandPlanType ::= TEXTUAL-CONVENTION
			STATUS current
			DESCRIPTION 
				"VDSL2 Band plan notation according to G993.2 Annex B.
				
				Short Name                                  Long Name
				former notation   current notation          Band plan
				                  according to G.993.2	
				
				B-1               B7-1	                    997-M1c-A-7
				B-2               B7-2	                    997-M1x-M-8
				B-3               B7-3	                    997-M1x-M
				B-4               B7-4	                    997-M2x-M-8
				B-5               B7-5	                    997-M2x-A
				B-6               B7-6	                    997-M2x-M
				B-7               B8-1	                    998-M1x-A
				B-8               B8-2	                    998-M1x-B
				B-9               B8-3	                    998-M1x-NUS0
				B-10              B8-4	                    998-M2x-A
				B-11              B8-5	                    998-M2x-M
				B-11-17                                     998-M2x-M17
				B-12              B8-6	                    998-M2x-B
				B-12-17                                     998-M2x-B17
				B-13              B8-7	                    998-M2x-NUS0
				B-13-17                                     998-M2x-NUS017
				                  B7-10                     997E30-M2x-NUS0
				                                            998E17-M2x-A
				                  B8-8                      998E17-M2x-NUS0
				
				NEW:
				                                            ANNEXA_M1_EU32
				                                            ANNEXA_M2_EU36
				                                            ANNEXA_M3_EU40
				                                            ANNEXA_M4_EU44
				                                            ANNEXA_M5_EU48
				                                            ANNEXA_M6_EU52
				                                            ANNEXA_M7_EU56
				                                            ANNEXA_M8_EU60
				                                            ANNEXA_M9_EU64
				                                            ANNEXA_EU128
				                                                            
				                                            ANNEXA_M1_ADLU32
				                                            ANNEXA_M2_ADLU36
				                                            ANNEXA_M3_ADLU40
				                                            ANNEXA_M4_ADLU44
				                                            ANNEXA_M5_ADLU48
				                                            ANNEXA_M6_ADLU52
				                                            ANNEXA_M7_ADLU56
				                                            ANNEXA_M8_ADLU60
				                                            ANNEXA_M9_ADLU64
				                                            ANNEXA_ADLU128
				 
				                                            ANNEXB_B7_1_997_M1C_A_7
				                                            ANNEXB_B7_2_997_M1X_M_8
				                                            ANNEXB_B7_3_997_M1X_M
				                                            ANNEXB_B7_4_997_M2X_M_8
				                                            ANNEXB_B7_5_997_M2X_A
				                                            ANNEXB_B7_6_997_M2X_M
				                                            ANNEXB_B7_7_HPE17_M1_NUS0
				                                            ANNEXB_B7_8_HPE30_M1_NUS0
				                                            ANNEXB_B7_9_997E17_M2X_A     (replaced _NUS0 with R2.8 MIB 327)
				                                            ANNEXB_B7_10_997E30_M2X_NUS0
				 
				                                            ANNEXB_B8_1_998_M1X_A
				                                            ANNEXB_B8_2_998_M1X_B
				                                            ANNEXB_B8_3_998_M1X_NUS0
				                                            ANNEXB_B8_4_998_M2X_A
				                                            ANNEXB_B8_5_998_M2X_M
				                                            ANNEXB_B8_6_998_M2X_B
				                                            ANNEXB_B8_7_998_M2X_NUS0
				                                            ANNEXB_B8_8_998E17_M2X_NUS0
				                                            ANNEXB_B8_9_998E17_M2X_NUS0_M
				                                            ANNEXB_B8_10_998ADE17_M2X_NUS0_M
				                                            ANNEXB_B8_11_998ADE17_M2X_A
				                                            ANNEXB_B8_12_998ADE17_M2X_B
				                                            ANNEXB_B8_13_998E30_M2X_NUS0
				                                            ANNEXB_B8_14_998E30_M2X_NUS0_M
				                                            ANNEXB_B8_15_998ADE30_M2X_NUS0_M
				                                            ANNEXB_B8_16_998ADE30_M2X_NUS0_A
				 
				                                            ANNEXB_998ADE17_M2X_M
				                                            ANNEXB_998E17_M2X_A"
			SYNTAX INTEGER
				{
				bandPlanItuAnnexAM1EU32(0),
				bandPlanItuAnnexAM9EU64(1),
				bandPlanItuAnnexAM1ADLU32(2),
				bandPlanItuAnnexAM9ADLU64(3),
				bandPlan997M1cA7(4),
				bandPlan997M1xM8(5),
				bandPlan997M1xM(6),
				bandPlan997M2xM8(7),
				bandPlan997M2xA(8),
				bandPlan997M2xM(9),
				bandPlan998M1xA(10),
				bandPlan998M1xB(11),
				bandPlan998M1xNUS0(12),
				bandPlan998M2xA(13),
				bandPlan998M2xM(14),
				bandPlan998M2xM17(15),
				bandPlan998M2xB(16),
				bandPlan998M2xB17(17),
				bandPlan998M2xNUS0(18),
				bandPlan998M2xNUS017(19),
				bandPlan997E30M2xNUS0(22),
				bandPlan998E17M2xA(25),
				bandPlan998E17M2xNUS0(26),
				bandPlanAnfpCal0Long(27),
				bandPlanAnfpCal0Medium(28),
				bandPlanAnfpCal0Short(29),
				bandPlanAnfpCal0EShort(30),
				bandPlanItuAnnexAM10EU128(40),
				bandPlanAnnexAM1Eu32(50),
				bandPlanAnnexAM2Eu36(51),
				bandPlanAnnexAM3Eu40(52),
				bandPlanAnnexAM4Eu44(53),
				bandPlanAnnexAM5Eu48(54),
				bandPlanAnnexAM6Eu52(55),
				bandPlanAnnexAM7Eu56(56),
				bandPlanAnnexAM8Eu60(57),
				bandPlanAnnexAM9Eu64(58),
				bandPlanAnnexAEu128(59),
				bandPlanAnnexAM1Adlu32(70),
				bandPlanAnnexAM2Adlu36(71),
				bandPlanAnnexAM3Adlu40(72),
				bandPlanAnnexAM4Adlu44(73),
				bandPlanAnnexAM5Adlu48(74),
				bandPlanAnnexAM6Adlu52(75),
				bandPlanAnnexAM7Adlu56(76),
				bandPlanAnnexAM8Adlu60(77),
				bandPlanAnnexAM9Adlu64(78),
				bandPlanAnnexAAdlu128(79),
				bandPlanAnnexB997M1CA7(100),
				bandPlanAnnexB997M1XM8(101),
				bandPlanAnnexB997M1XM(102),
				bandPlanAnnexB997M2XM8(103),
				bandPlanAnnexB997M2XA(104),
				bandPlanAnnexB997M2XM(105),
				bandPlanAnnexB997HPE17M1NUS0(106),
				bandPlanAnnexB997HPE30M1NUS0(107),
				bandPlanAnnexB997E17M2XA(108),
				bandPlanAnnexB997E30M2XNUS0(109),
				bandPlanAnnexB998M1XA(120),
				bandPlanAnnexB998M1XB(121),
				bandPlanAnnexB998M1XNUS0(122),
				bandPlanAnnexB998M2XA(123),
				bandPlanAnnexB998M2XM(124),
				bandPlanAnnexB998M2XB(125),
				bandPlanAnnexB998M2XNUS0(126),
				bandPlanAnnexB998E17M2XNUS0(127),
				bandPlanAnnexB998E17M2XNUS0M(128),
				bandPlanAnnexB998ADE17M2XNUS0M(129),
				bandPlanAnnexB998ADE17M2XA(130),
				bandPlanAnnexB998ADE17M2XB(131),
				bandPlanAnnexB998E30M2XNUS0(132),
				bandPlanAnnexB998E30M2XNUS0M(133),
				bandPlanAnnexB998ADE30M2XNUS0M(134),
				bandPlanAnnexB998ADE30M2XNUS0A(135),
				bandPlanAnnexB998ADE17M2XM(140),
				bandPlanAnnexB998E17M2XA(141)
				}

		SheVdsl2ProfileType ::= TEXTUAL-CONVENTION
			STATUS current
			DESCRIPTION 
				"VDSL2 profile numbers."
			REFERENCE 
				"g993.2 chapter 6"
			SYNTAX INTEGER
				{
				dslProfile8A(0),
				dslProfile8B(1),
				dslProfile8C(2),
				dslProfile8D(3),
				dslProfile12A(4),
				dslProfile12B(5),
				dslProfile17A(6),
				dslProfile30A(7),
				dslProfile17B(8)
				}

		SheXdslSnrModeType ::= TEXTUAL-CONVENTION
			STATUS current
			DESCRIPTION 
				"If set to 1, the virtual noise is disabled. If set to 2, the virtual noise is enabled."
			SYNTAX INTEGER
				{
				virtualNoiseDisabled(1),
				virtualNoiseEnabled(2)
				}

		SheXdslCustomePsdMaskProfileUsageType ::= TEXTUAL-CONVENTION
			STATUS current
			DESCRIPTION 
				"Define the usage of a created custome psd mask profile for upstream or downstream
				direction."
			SYNTAX INTEGER
				{
				downstream(0),
				upstream(1)
				}

		SheXdslLineDeltStatusSCGGroupSizeType ::= TEXTUAL-CONVENTION
			STATUS current
			DESCRIPTION 
				"The number of subcarriers in one subcarrier-group shall be equal to the highest
				power of 2 not greather than ceil((maxUsedCarrier+1)/512), where maxUsedCarrier
				is the index of the highest frequency subcarrier such that all higher-index
				subcarriers either have a channel characteristic Hlog lower than -96 dB or do not
				 belong to the passband.
				Valid values are 1, 2, 4 or 8. 0 means value is not available."
			REFERENCE 
				"ITU-T G.993.2, paragraph 11.4.1 "
			SYNTAX INTEGER
				{
				notAvailable(0),
				oneSubcarrier(1),
				twoSubcarrier(2),
				fourSubcarrier(4),
				eigthSubcarrier(8)
				}

		SheXdslCustomPsdMaskUseType ::= TEXTUAL-CONVENTION
			STATUS current
			DESCRIPTION 
				"Select the usage of custom psd mask profiles from PsdMaskProfile-table for 
				upstream and/or downstream direction."
			SYNTAX INTEGER
				{
				none(0),
				useDownStream(1),
				useUpStream(2),
				useDownAndUpStream(3)
				}

		SheXdslConfigViolationCheckType ::= TEXTUAL-CONVENTION
			STATUS current
			DESCRIPTION 
				"This type is new with R2.8 maintenance release.
				It is used to configure enable/disable config violation check's via alarm profile and define the
				action if a violation was detected. "
			SYNTAX BITS
				{
				featureNotSupported(0),
				checkMinINP(1),
				abortOnINPViolation(2)
				}

	
--
-- Node definitions
--
	
		sheXdslLineMib OBJECT IDENTIFIER ::= { sheXdslMib 1 }

		
		sheXdslMibObjects OBJECT IDENTIFIER ::= { sheXdslLineMib 1 }

		
		sheXdslLineTable OBJECT-TYPE
			SYNTAX SEQUENCE OF SheXdslLineEntry
			MAX-ACCESS not-accessible
			STATUS current
			DESCRIPTION
				"This table includes common attributes describing
				both ends of the line.  It is required for all XDSL
				physical interfaces.  XDSL physical interfaces are
				those ifEntries where ifType is equal to xdsl(97)."
			::= { sheXdslMibObjects 1 }

		
		sheXdslLineEntry OBJECT-TYPE
			SYNTAX SheXdslLineEntry
			MAX-ACCESS not-accessible
			STATUS current
			DESCRIPTION
				"An entry in the xdslLineTable."
			INDEX { ifIndex }
			::= { sheXdslLineTable 1 }

		
		SheXdslLineEntry ::=
			SEQUENCE { 
				sheXdslLineGsAction
					SheXdslLineGsActionType,
				sheXdslLineConfProfile
					SnmpAdminString,
				sheXdslLineAlarmConfProfile
					SnmpAdminString,
				sheXdslLineXtucCapability
					SheXdslLineStandardType,
				sheXdslLineXturCapability
					SheXdslLineStandardType,
				sheXdslLineXtuCurrCapability
					SheXdslLineStandardType,
				sheXdslLineLdsf
					SheXdslLineLdsfType,
				sheXdslLineLdsfResult
					SheXdslLineLdsfResultType,
				sheXdslLineCustomDownPsdMaskProfile
					OCTET STRING,
				sheXdslLineCustomUpPsdMaskProfile
					OCTET STRING,
				sheXdslLineCustomNotchProfile
					OCTET STRING,
				sheXdslLineRfiBandMask
					SheXdslLineRfiBandMaskType,
				sheXdslLineGsStandard
					SheXdslLineStandardType,
				sheXdslLineUpPboKLE
					Unsigned32,
				sheXdslLinePMSF
					SheXdslPMSFType,
				sheXdslLineForceINPDs
					TruthValue,
				sheXdslLineForceINPUs
					TruthValue,
				sheXdslLineChan1ConfProfile
					SnmpAdminString,
				sheXdslLineChan1RaRatioDs
					Unsigned32,
				sheXdslLineChan1RaRatioUs
					Unsigned32,
				sheXdslLineChan2ConfProfile
					SnmpAdminString,
				sheXdslLinePerformance15MinHistoryEnabled
					TruthValue,
				sheXdslLinePerformance1DayHistoryEnabled
					TruthValue,
				sheXdslLineConfigViolationCheckStatus
					SheXdslConfigViolationCheckType
			 }

		sheXdslLineGsAction OBJECT-TYPE
			SYNTAX SheXdslLineGsActionType
			MAX-ACCESS read-only
			STATUS current
			DESCRIPTION
				"This object indicates parameter that allows actions on a per line basis. 
				These actions include abort, startup, and tests.
				Valid values:
				startup(0)          -> normal operation (default)
				spectrumReverb(5)   -> Testmode
				spectrumMedley(26)  -> Testmode
				showTimeLock(39)    -> Testmode - This feature can be used for measurement of the PSD.
				returnLoss(40)      -> Testmode. "
			DEFVAL { startup }
			::= { sheXdslLineEntry 3 }

		
		sheXdslLineConfProfile OBJECT-TYPE
			SYNTAX SnmpAdminString (SIZE (1..32))
			MAX-ACCESS read-only
			STATUS current
			DESCRIPTION
				"The value of this object identifies the row in the XDSL
				Line Configuration Profile Table, xdslLineConfProfileTable,
				which applies for this XDSL line, and channels if 
				applicable.
				This object MUST be maintained in a persistent manner."
			DEFVAL { "DEFVAL" }
			::= { sheXdslLineEntry 4 }

		
		sheXdslLineAlarmConfProfile OBJECT-TYPE
			SYNTAX SnmpAdminString (SIZE (1..32))
			MAX-ACCESS read-only
			STATUS current
			DESCRIPTION
				"The value of this object identifies the row in the XDSL
				Line Alarm Configuration Profile Table, 
				xdslLineAlarmConfProfileTable, which applies to this
				XDSL line, and channels if applicable.
				
				This object MUST be maintained in a persistent manner."
			DEFVAL { "DEFVAL" }
			::= { sheXdslLineEntry 5 }

		
		sheXdslLineXtucCapability OBJECT-TYPE
			SYNTAX SheXdslLineStandardType
			MAX-ACCESS read-only
			STATUS current
			DESCRIPTION
				"The capability of co-side. Be aware that multiple bits could be set! Each bit set to 1 means,
				that the corresponding standard is supported."
			REFERENCE
				"G997.1 chapter 7.4.11"
			::= { sheXdslLineEntry 6 }

		
		sheXdslLineXturCapability OBJECT-TYPE
			SYNTAX SheXdslLineStandardType
			MAX-ACCESS read-only
			STATUS current
			DESCRIPTION
				"The capability of remote-side. Only available if line has trained - otherwise 0.
				Be aware that multiple bits could be set! Each bit set to 1 means,
				that the corresponding standart is supported."
			REFERENCE
				"G997.1 chapter 7.4.12"
			::= { sheXdslLineEntry 7 }

		
		sheXdslLineXtuCurrCapability OBJECT-TYPE
			SYNTAX SheXdslLineStandardType
			MAX-ACCESS read-only
			STATUS current
			DESCRIPTION
				"The current used capability of the line. Only available if line has trained - otherwise 0.
				Only one bit could be set and means that the corresponding standard is supported."
			REFERENCE
				"G997.1 chapter 7.5.1.1"
			::= { sheXdslLineEntry 8 }

		
		sheXdslLineLdsf OBJECT-TYPE
			SYNTAX SheXdslLineLdsfType
			MAX-ACCESS read-only
			STATUS current
			DESCRIPTION
				"Loop diagnostics mode forced (LDSF).
				Defines whether the line should be forced into the loop diagnostics mode by
				the near-end xTU on this line or only be responsive to loop diagnostics
				initiated by the far-end xTU."
			REFERENCE
				"ITU-T G.997.1, paragraph 7.3.1.1.8"
			DEFVAL { inhibit }
			::= { sheXdslLineEntry 9 }

		
		sheXdslLineLdsfResult OBJECT-TYPE
			SYNTAX SheXdslLineLdsfResultType
			MAX-ACCESS read-only
			STATUS current
			DESCRIPTION
				"The status of the recent occasion the Loop diagnostics mode
				forced (LDSF) was issued for the associated line.  Possible
				values are:
				   none        (1) - The default value in case LDSF was never
				                     requested for the associated line.
				   success     (2) - The recent command completed
				                     successfully.
				   inProgress  (3) - The Loop Diagnostics process is in
				                     progress.
				   unsupported (4) - The NE or the line card doesn't support
				                     LDSF.
				   cannotRun   (5) - The NE cannot initiate the command, due
				                     to a non specific reason.
				   aborted     (6) - The Loop Diagnostics process aborted.
				   failed      (7) - The Loop Diagnostics process failed.
				   illegalMode (8) - The NE cannot initiate the command, due
				                     to the specific mode of the relevant
				                     line.
				   adminUp     (9) - The NE cannot initiate the command, as
				                     the relevant line is administratively
				                     'Up'.
				   noResources (11)- The NE cannot initiate the command, due
				                     to lack of internal memory resources."
			DEFVAL { none }
			::= { sheXdslLineEntry 10 }

		
		sheXdslLineCustomDownPsdMaskProfile OBJECT-TYPE
			SYNTAX OCTET STRING (SIZE (0..32))
			MAX-ACCESS read-only
			STATUS current
			DESCRIPTION
				"Specifies the name of the used custom psd mask profile from sheXdslPsdMaskProfileTable
				for DOWNSTREAM direction.
				If not used the value is a empty string(default). 
				The management system should also set a empty string if no profile is used and all existing profiles
				should be deleted.Only profiles with profile usage set to downstream could be configured here.
				
				IMPORTANT NOTE:
				SHE release since R1.42 will only support psdmask profile, notch profile and rfi-band configuration directly
				via linetable. The NE will support a automatic convertion of R1.41 databases.
				This convertion will perform the following steps:
				1. Copy psdmask, rfi-band and notchprofile configuration for all used lineprofiles to all
				   corresponding linetableentrys (only if usedflag's for psdmask or notch profile
				   are set in lineprofile).
				2. Reset usedflags and profilenames (empty string) in all lineprofiles to default value!
				
				If usedflag's or psdmask or notchprofile parameter will be set by TMN during extention profile modification,
				the NE will ignore these settings and return always the default values.
				No reject message will be send!
				"
			REFERENCE
				"g.997.1 chapter 7.3.1.2.9 "
			::= { sheXdslLineEntry 11 }

		
		sheXdslLineCustomUpPsdMaskProfile OBJECT-TYPE
			SYNTAX OCTET STRING (SIZE (0..32))
			MAX-ACCESS read-only
			STATUS current
			DESCRIPTION
				"Specifies the name of the used custom psd mask profile from sheXdslPsdMaskProfileTable
				for UPSTREAM direction.
				If not used the value is a empty string(default). 
				The management system should also set a empty string if no profile is used and all existing profiles
				should be deleted.Only profiles with profile usage set to upstream could be configured here.
				
				IMPORTANT NOTE:
				SHE release since R1.42 will only support psdmask profile, notch profile and rfi-band configuration directly
				via linetable. The NE will support a automatic convertion of R1.41 databases.
				This convertion will perform the following steps:
				1. Copy psdmask, rfi-band and notchprofile configuration for all used lineprofiles to all
				   corresponding linetableentrys (only if usedflag's for psdmask or notch profile
				   are set in lineprofile).
				2. Reset usedflags and profilenames (empty string) in all lineprofiles to default value!
				
				If usedflag's or psdmask or notchprofile parameter will be set by TMN during extention profile modification,
				the NE will ignore these settings and return always the default values.
				No reject message will be send!
				"
			REFERENCE
				"g.997.1 chapter 7.3.1.2.12"
			::= { sheXdslLineEntry 12 }

		
		sheXdslLineCustomNotchProfile OBJECT-TYPE
			SYNTAX OCTET STRING (SIZE (0..32))
			MAX-ACCESS read-only
			STATUS current
			DESCRIPTION
				"Specifies the name of the used custom notch profile from sheXdslCustomNotchProfileTable if usage of custom notch is enabled.
				If not used or no NotchProfile exist in NE the value is a empty string(default).
				The management system should also set a empty string if no profile is used and all existing
				profiles should be deleted. 
				
				Be aware, that the NE can handle only 16 notches per line at time. 
				If all free defined notches in  a customNotchProfile should be used, it is not
				allowed to enable additional predefined notches from the RFIBandMask for this line!!
				If such notches are already activ, it is not possible to assign a notchprofile to such
				a line if the total amount of notches (RFIBand's + UsedNotches in profile) is greater then 16. 
				
				IMPORTANT NOTE:
				SHE release since R1.42 NE will only support psdmask profile, notch profile and rfi-band configuration directly
				via linetable. The NE will support a automatic convertion of R1.41 databases.
				This convertion will perform the following steps:
				1. Copy psdmask, rfi-band and notchprofile configuration for all used lineprofiles to all
				   corresponding linetableentrys (only if usedflag's for psdmask or notch profile
				   are set in lineprofile).
				2. Reset usedflags and profilenames (empty string) in all lineprofiles to default value!
				
				If usedflag's or psdmask or notchprofile parameter will be set by TMN during extention profile modification,
				the NE will ignore these settings and return always the default values.
				No reject message will be send!
				"
			REFERENCE
				"g.997.1 chapter 7.3.1.2.10"
			::= { sheXdslLineEntry 13 }

		
		sheXdslLineRfiBandMask OBJECT-TYPE
			SYNTAX SheXdslLineRfiBandMaskType
			MAX-ACCESS read-only
			STATUS current
			DESCRIPTION
				"The transmit power spectral density mask code, used to avoid interference with
				HAM (Handheld Amateur Radio) radio bands by introducing power control (notching)
				in one or more of these bands.
				
				
				Amateur radio band notching is defined in the DSL
				spectrum as follows:
				
				  Start Frequency     Stop Frequency
				  ----------------    ------------------------------
				1. 1800 kHz            2000 kHz
				2. 3500 kHz            3800 kHz 
				3. 7000 kHz            7200 kHz 
				4. 10100 kHz           10150 kHz
				5. 14000 kHz           14350 kHz
				
				GMDSS - Frequency's:
				6. 2173 kHz            2191 kHz
				7. 4200 kHz            4215 kHz
				8. 6300 kHz            6320 kHz
				
				
				This standard notches representing the following subcarrier-indices
				if a spacing of 4.3125 kHz is used (VDSL2 profiles 8A .. 17A or ADSL):
				
				  Start-Carrier  Stop-Carrier
				  ------------   -----------------
				1. 417		464
				2. 811		881
				3. 1623		1670
				4. 2342		2354
				5. 3246		3328
				
				6. 504		508
				7. 974		977
				8. 1461		1466
				
				
				VDSL2 Profile 30A  use a different spacing of 8.625 kHz:
				  Start-Carrier   Stop-Carrier
				  -------------   -----------------
				1. 209		232
				2. 406		441
				3. 812		835
				4. 1171		1177
				5. 1623		1664
				
				6. 252		254
				7. 487		489
				8. 730		733
				
				Notching for each standard band can be enabled or disabled via the bit mask.
				
				Be aware, that the NE can handle only 16 notches per line at time. 
				If all free defined notches in  a customNotchProfile should be used, it is not
				allowed to enable additional predefined notches from the RFIBandMask!! If such
				notches are already activ, it is not possible to assign a notchprofile to such
				a line if the total amount of notches (RFIBand's + UsedNotches) is greater then 16. 
				"
			REFERENCE
				"g.993.2 chapter 7.2.1.2"
			::= { sheXdslLineEntry 14 }

		
		sheXdslLineGsStandard OBJECT-TYPE
			SYNTAX SheXdslLineStandardType
			MAX-ACCESS read-only
			STATUS current
			DESCRIPTION
				"Shows the preferred used standard compliance. see g.997.1 clause 7.3.1.1.1 (ATSE).
				The following bits are possible:
					g9921AdslPotsNonOverlapped(2),
					g9921AdslIsdnNonOverlapped(4),
					g9923Adsl2PotsNonOverlapped(18),
					g9923Adsl2IsdnNonOverlapped(20),
					g9923ADMAdsl2NonOverlappedAnnexJ(30),
					g9923ReachExtAdsl2PotsNonOverlappedM1(34),
					g9923ReachExtAdsl2PotsNonOverlappedM2(35),
					g9923ExtUpAdsl2PotsNonOverlapped(38),
					g9925Adsl2PlusPotsNonOverlapped(40),
					g9925Adsl2PlusIsdnNonOverlapped(42),
					g9925ADMAdsl2PlusNonOverlappedAnnexJ(48),
					g9925ExtUpAdsl2PlusPotsNonOverlapped(50),
					g9932Vdsl2NonOverlappedRegionB(57),
				
				The configuration is done via LineProfile."
			DEFVAL { { g9932Vdsl2NonOverlappedRegionB } }
			::= { sheXdslLineEntry 15 }

		
		sheXdslLineUpPboKLE OBJECT-TYPE
			SYNTAX Unsigned32 (0..1280 | 32768)
			UNITS "0.1 dB"
			MAX-ACCESS read-only
			STATUS current
			DESCRIPTION
				"Estimated Upstream Power Backoff Electrical Loop Length (UPBOKLE). This parameter
				contains the estimated electrical loop length expressed in dB at 1MHz, kle.
				This is the final electrical loop length that should be sent from the xTU-C to
				xTU-R if the loop length is not forced by the CO-MIB (see 12.2.4.2.1.2/G.993.2).
				The value shall be coded in the range 0 (coded as 0) to 128 dB (coded as 1280)
				in steps of 0.1 dB. 
				The corresponding values line length to the damping in dB is about 10 dB per 500 m.
				A value of 0x8000 (32768) means that the current value is not available.
				"
			REFERENCE
				"g.997 chapter 7.5.1.23"
			DEFVAL { 32768 }
			::= { sheXdslLineEntry 16 }

		
		sheXdslLinePMSF OBJECT-TYPE
			SYNTAX SheXdslPMSFType
			MAX-ACCESS read-only
			STATUS current
			DESCRIPTION
				"This object indicates the action that forces a change in the line state of
				power management. (Not available for ADSL, G992.1)
				The following changes are valid:
				pmsfL0ToL2StateForce(1) -> Force the line to transition from L0 full power to L2 low power
				                           state. This transition requires the entry into L2 mode. This is an 
				                           out-of-service test value for triggering the L2 mode. Only valid if
				                           line run's L0 mode already.
				
				pmsfL2ToL0StateForce(3) -> Force the line to transition from L2 low power to L0 full power
				                           state. This transition requires the entry into L0 mode. This stops
				                           the out-of-service test and triggering the line to go back to normal 
				                           operation. Only valid if line run's L2 mode already.
				
				The transitions pmsfL3ToL0StateForce (unlock) and pmsfL3StateForce (lock) should always
				be done via ifAdminState setting.
				
				This is valid only for Recommendations supporting L2 mode otherwise don't care!
				
				"
			REFERENCE
				"G997.1 chapter 7.3.1.1.3"
			DEFVAL { none }
			::= { sheXdslLineEntry 17 }

		
		sheXdslLineForceINPDs OBJECT-TYPE
			SYNTAX TruthValue
			MAX-ACCESS read-only
			STATUS current
			DESCRIPTION
				"This parameter indicates that the framer settings of the bearer shall be selected such that the impulse
				noise protection computed according to the formula specified in the relevant Recommendation is
				greater than or equal to the minimal impulse noise protection requirement.
				
				This flag shall have the same value for all the bearers of one line in the same direction.
				This parameter specifies the value for downstream direction."
			REFERENCE
				"ITU-T G.997.1, chapter 7.3.2.5"
			DEFVAL { false }
			::= { sheXdslLineEntry 18 }

		
		sheXdslLineForceINPUs OBJECT-TYPE
			SYNTAX TruthValue
			MAX-ACCESS read-only
			STATUS current
			DESCRIPTION
				"This parameter indicates that the framer settings of the bearer shall be selected such that the impulse
				noise protection computed according to the formula specified in the relevant Recommendation is
				greater than or equal to the minimal impulse noise protection requirement.
				
				This flag shall have the same value for all the bearers of one line in the same direction.
				This parameter specifies the value for upstream direction."
			REFERENCE
				"ITU-T G.997.1, chapter 7.3.2.5"
			DEFVAL { false }
			::= { sheXdslLineEntry 19 }

		
		sheXdslLineChan1ConfProfile OBJECT-TYPE
			SYNTAX SnmpAdminString (SIZE (1..32))
			MAX-ACCESS read-only
			STATUS current
			DESCRIPTION
				"The value of this object identifies the row in the XDSL channel configuration
				Profile Table,(sheXdslChannelProfileTable) that applies to DSL bearer
				channel #1. The channel profile name specified here must
				match the name of an existing row in the sheXdslChannelProfileTable table."
			DEFVAL { "DEFVAL" }
			::= { sheXdslLineEntry 20 }

		
		sheXdslLineChan1RaRatioDs OBJECT-TYPE
			SYNTAX Unsigned32 (0..100)
			UNITS "percents"
			MAX-ACCESS read-only
			STATUS current
			DESCRIPTION
				"Rate Adaptation Ratio. The ratio (in %) that should be taken
				into account for the bearer channel #1 when performing rate
				adaptation on Downstream. The ratio refers to the available
				data rate in excess of the Minimum Data Rate, summed over all
				bearer channels. Also, the 100 - sheXdslLineChan1RaRatioDs
				is the ratio of excess data rate to be assigned to all other bearer
				channels on Downstream direction. The sum of rate adaptation ratios
				over all bearers on the same direction shall be equal to 100%."
			REFERENCE
				"ITU-T G.997.1, paragraph 7.3.2.1"
			DEFVAL { 100 }
			::= { sheXdslLineEntry 21 }

		
		sheXdslLineChan1RaRatioUs OBJECT-TYPE
			SYNTAX Unsigned32 (0..100)
			UNITS "percents"
			MAX-ACCESS read-only
			STATUS current
			DESCRIPTION
				"Rate Adaptation Ratio. The ratio (in %) that should be taken
				into account for the bearer channel #1 when performing rate
				adaptation on Upstream. The ratio refers to the available
				data rate in excess of the Minimum Data Rate, summed over all
				bearer channels. Also, the 100 - sheXdslConfChan1RaRatioUs
				is the ratio of excess data rate to be assigned to all other
				bearer channels on Upstream direction. The sum of rate adaptation
				ratios over all bearers on the same direction shall be equal to 100 %."
			REFERENCE
				"ITU-T G.997.1, paragraph 7.3.2.1"
			DEFVAL { 100 }
			::= { sheXdslLineEntry 22 }

		
		sheXdslLineChan2ConfProfile OBJECT-TYPE
			SYNTAX SnmpAdminString (SIZE (0..32))
			MAX-ACCESS read-only
			STATUS current
			DESCRIPTION
				"The value of this object identifies the row in the XDSL channel configuration
				Profile Table, (sheXdslChannelProfileTable) that applies to DSL bearer
				channel #2. If the channel is unused, then the object is set
				to a zero length string."
			DEFVAL { "" }
			::= { sheXdslLineEntry 23 }

		
--  info - IMPL: R2.7->
		sheXdslLinePerformance15MinHistoryEnabled OBJECT-TYPE
			SYNTAX TruthValue
			MAX-ACCESS read-only
			STATUS current
			DESCRIPTION
				"Configure, if the counted 15Min history performance entrys should be stored for that line.
				
				Remark:
				Be aware, that there is a NE restriction to store performance entrys for a maximum number
				of 450 lines at the same time. Support with SHE R2.7."
			DEFVAL { false }
			::= { sheXdslLineEntry 24 }

		
--  info - IMPL: R2.7->
		sheXdslLinePerformance1DayHistoryEnabled OBJECT-TYPE
			SYNTAX TruthValue
			MAX-ACCESS read-only
			STATUS current
			DESCRIPTION
				"Configure, if the counted 1Day history performance entrys should be stored for that line.
				
				Remark:
				Be aware, that there is a NE restriction to store performance entrys for a maximum number
				of 450 lines at the same time. Support with SHE R2.7."
			DEFVAL { false }
			::= { sheXdslLineEntry 25 }

		
		sheXdslLineConfigViolationCheckStatus OBJECT-TYPE
			SYNTAX SheXdslConfigViolationCheckType
			MAX-ACCESS read-only
			STATUS current
			DESCRIPTION
				"If config violation check was enabled, this parameter will show the type of detected violations.
				It is DSL firmware depended if the line support this status information.
				The NE will set featureNotSupported(0) BIT to 1 in case the status information is not available
				for this line at all.
				
				Valid information:
				featureNotSupported(0) -> BIT is 1 -> the ConfigViolationCheck feature is not supported by this line
				checkMinINP(1)         -> BIT is 1 -> the minINP-Check has detected a violation
				
				Note:
				New parameter with R2.8 maintenance. "
			DEFVAL { { featureNotSupported } }
			::= { sheXdslLineEntry 35 }

		
		sheXdslLineControl OBJECT IDENTIFIER ::= { sheXdslMibObjects 2 }

		
		sheXdslLineControlRequest OBJECT-TYPE
			SYNTAX SheXdslControlRequestType
			MAX-ACCESS read-write
			STATUS current
			DESCRIPTION
				"modifyXdslLineEntry:
				sheXdslLineControlIndex
				sheXdslLineControlGsAction
				sheXdslLineControlConfProfile
				
				modifyXdslLineAlarmConfProfileEntry:
				sheXdslLineControlIndex
				sheXdslLineControlAlarmConfProfile
				
				modifyXdslLineDeltState:
				sheXdslLineControlIndex
				sheXdslLineControlLdsf
				
				setXdslLineDownPsdMaskProfileEntry:
				sheXdslLineControlIndex
				sheXdslLineControlCustomDownPsdMaskProfile
				
				
				setXdslLineUpPsdMaskProfileEntry:
				sheXdslLineControlIndex
				sheXdslLineControlCustomUpPsdMaskProfile
				
				setXdslLineNotchConfiguration:
				sheXdslLineControlIndex
				sheXdslLineControlCustomNotchProfile
				sheXdslLineControlRfiBandMask
				
				# New in SHE R2.6
				modifyXdslLinePMSFState:
				sheXdslLineControlIndex
				sheXdslLineControlPMSF
				
				setXdslLineForceInpConfiguration
				sheXdslLineControlIndex
				sheXdslLineControlForceINPDs
				sheXdslLineControlForceINPUs
				
				setXdslLineChannelProfileConfiguration
				sheXdslLineControlIndex
				sheXdslLineControlChan1ConfProfile
				sheXdslLineControlChan1RaRatioDs
				sheXdslLineControlChan1RaRatioUs
				sheXdslLineControlChan2ConfProfile
				
				# New in SHE R2.7
				modifyXdslLinePerformanceHistory:
				sheXdslLineControlIndex
				sheXdslLineControlPerformance15MinHistoryEnabled
				sheXdslLineControlPerformance1DayHistoryEnabled"
			::= { sheXdslLineControl 1 }

		
		sheXdslLineControlIndex OBJECT-TYPE
			SYNTAX Integer32
			MAX-ACCESS read-write
			STATUS current
			DESCRIPTION
				"IfIndex of the configured xdsl-interface."
			::= { sheXdslLineControl 2 }

		
		sheXdslLineControlStatus OBJECT-TYPE
			SYNTAX SheControlStatusType
			MAX-ACCESS read-only
			STATUS current
			DESCRIPTION
				"The status of a user command. 
				"
			::= { sheXdslLineControl 3 }

		
		sheXdslLineControlTimer OBJECT-TYPE
			SYNTAX Gauge32
			MAX-ACCESS read-only
			STATUS current
			DESCRIPTION
				"The maximum wait time for the manager for a long running user command. 
				"
			::= { sheXdslLineControl 4 }

		
		sheXdslLineControlReqResult OBJECT-TYPE
			SYNTAX SheXdslControlRequestResultType
			MAX-ACCESS read-only
			STATUS current
			DESCRIPTION
				"The result of the last user command."
			::= { sheXdslLineControl 5 }

		
		sheXdslLineControlTimeStamp OBJECT-TYPE
			SYNTAX Unsigned32
			UNITS "sec"
			MAX-ACCESS read-only
			STATUS current
			DESCRIPTION
				"The time stamp of the last command (end of command)."
			::= { sheXdslLineControl 6 }

		
		sheXdslLineControlGsAction OBJECT-TYPE
			SYNTAX SheXdslLineGsActionType
			MAX-ACCESS read-write
			STATUS current
			DESCRIPTION
				"look at table"
			::= { sheXdslLineControl 7 }

		
		sheXdslLineControlConfProfile OBJECT-TYPE
			SYNTAX SnmpAdminString (SIZE (1..32))
			MAX-ACCESS read-write
			STATUS current
			DESCRIPTION
				"The value of this object identifies the row
				in the XDSL Line Configuration Profile Table,
				which applies for this XDSL line, and channels if applicable.
				
				For the used `dynamic' mode, in the case which the
				configuration profile has not been set, the
				value will be set to `DEFVAL'.
				
				"
			::= { sheXdslLineControl 8 }

		
		sheXdslLineControlAlarmConfProfile OBJECT-TYPE
			SYNTAX SnmpAdminString (SIZE (1..32))
			MAX-ACCESS read-write
			STATUS current
			DESCRIPTION
				"The value of this object identifies the row
				in the XDSL Line Alarm Configuration Profile Table,
				which applies to this XDSL line, and channels if applicable.
				
				For the used `dynamic' mode, in the case which the
				alarm profile has not been set, the
				value will be set to `DEFVAL'.
				
				"
			::= { sheXdslLineControl 9 }

		
		sheXdslLineControlLdsf OBJECT-TYPE
			SYNTAX SheXdslLineLdsfType
			MAX-ACCESS read-write
			STATUS current
			DESCRIPTION
				"look at table."
			::= { sheXdslLineControl 10 }

		
		sheXdslLineControlCustomDownPsdMaskProfile OBJECT-TYPE
			SYNTAX OCTET STRING (SIZE (0..32))
			MAX-ACCESS read-write
			STATUS current
			DESCRIPTION
				"look at table"
			::= { sheXdslLineControl 11 }

		
		sheXdslLineControlCustomUpPsdMaskProfile OBJECT-TYPE
			SYNTAX OCTET STRING (SIZE (0..32))
			MAX-ACCESS read-write
			STATUS current
			DESCRIPTION
				"look at table"
			::= { sheXdslLineControl 12 }

		
		sheXdslLineControlCustomNotchProfile OBJECT-TYPE
			SYNTAX OCTET STRING (SIZE (0..32))
			MAX-ACCESS read-write
			STATUS current
			DESCRIPTION
				"look at table"
			::= { sheXdslLineControl 13 }

		
		sheXdslLineControlRfiBandMask OBJECT-TYPE
			SYNTAX SheXdslLineRfiBandMaskType
			MAX-ACCESS read-write
			STATUS current
			DESCRIPTION
				"look at table"
			::= { sheXdslLineControl 14 }

		
		sheXdslLineControlPMSF OBJECT-TYPE
			SYNTAX SheXdslPMSFType
			MAX-ACCESS read-write
			STATUS current
			DESCRIPTION
				"look at table
				
				The transitions pmsfL3ToL0StateForce (unlock) and pmsfL3StateForce (lock) should always
				be done via ifAdminState setting.
				"
			::= { sheXdslLineControl 15 }

		
		sheXdslLineControlForceINPDs OBJECT-TYPE
			SYNTAX TruthValue
			MAX-ACCESS read-write
			STATUS current
			DESCRIPTION
				"look at table"
			::= { sheXdslLineControl 16 }

		
		sheXdslLineControlForceINPUs OBJECT-TYPE
			SYNTAX TruthValue
			MAX-ACCESS read-write
			STATUS current
			DESCRIPTION
				"look at table"
			::= { sheXdslLineControl 17 }

		
		sheXdslLineControlChan1ConfProfile OBJECT-TYPE
			SYNTAX SnmpAdminString (SIZE (1..32))
			MAX-ACCESS read-write
			STATUS current
			DESCRIPTION
				"The channel profile name specified here must match the name of an existing
				row in the sheXdslChannelProfileTable table."
			::= { sheXdslLineControl 18 }

		
		sheXdslLineControlChan1RaRatioDs OBJECT-TYPE
			SYNTAX Unsigned32 (0..100)
			UNITS "percents"
			MAX-ACCESS read-write
			STATUS current
			DESCRIPTION
				"Look at table."
			::= { sheXdslLineControl 19 }

		
		sheXdslLineControlChan1RaRatioUs OBJECT-TYPE
			SYNTAX Unsigned32 (0..100)
			UNITS "percents"
			MAX-ACCESS read-write
			STATUS current
			DESCRIPTION
				"Look at table"
			::= { sheXdslLineControl 20 }

		
		sheXdslLineControlChan2ConfProfile OBJECT-TYPE
			SYNTAX SnmpAdminString (SIZE (0..32))
			MAX-ACCESS read-write
			STATUS current
			DESCRIPTION
				"The channel profile name specified here must match the name of an existing
				row in the sheXdslChannelProfileTable table or should be an emty string if no 
				channel 2 is used."
			::= { sheXdslLineControl 21 }

		
--  info - IMPL: R2.7->
		sheXdslLineControlPerformance15MinHistoryEnabled OBJECT-TYPE
			SYNTAX TruthValue
			MAX-ACCESS read-write
			STATUS current
			DESCRIPTION
				"Configure, if the counted 15Min history performance entrys should be stored for that line.
				
				Remark:
				Be aware, that there is a NE restriction to store performance entrys for a maximum number
				of 450 lines at the same time. Support with SHE R2.7."
			::= { sheXdslLineControl 22 }

		
--  info - IMPL: R2.7->
		sheXdslLineControlPerformance1DayHistoryEnabled OBJECT-TYPE
			SYNTAX TruthValue
			MAX-ACCESS read-write
			STATUS current
			DESCRIPTION
				"Configure, if the counted 1Day history performance entrys should be stored for that line.
				
				Remark:
				Be aware, that there is a NE restriction to store performance entrys for a maximum number
				of 450 lines at the same time. Support with SHE R2.7."
			::= { sheXdslLineControl 23 }

		
		sheXdslPhysTable OBJECT-TYPE
			SYNTAX SEQUENCE OF SheXdslPhysEntry
			MAX-ACCESS not-accessible
			STATUS current
			DESCRIPTION
				"This table provides one row for each xtu. Each row contains the Physical Layer Parameters
				table for that xtu. XDSL physical interfaces are those ifEntries where 
				ifType is equal to vdsl(97) or ADSL2 (230)."
			::= { sheXdslMibObjects 3 }

		
		sheXdslPhysEntry OBJECT-TYPE
			SYNTAX SheXdslPhysEntry
			MAX-ACCESS not-accessible
			STATUS current
			DESCRIPTION
				"An entry in the xdslPhysTable."
			INDEX { ifIndex, sheXdslPhysSide }
			::= { sheXdslPhysTable 1 }

		
		SheXdslPhysEntry ::=
			SEQUENCE { 
				sheXdslPhysSide
					SheXdslLineEntity,
				sheXdslPhysInvSerialNumber
					SnmpAdminString,
				sheXdslPhysInvHSVendorID
					SnmpAdminString,
				sheXdslPhysInvVersionNumber
					SnmpAdminString,
				sheXdslPhysCurrStatus
					SheXdslPhysCurrStatusType,
				sheXdslPhysCurrOutputPwr
					Integer32,
				sheXdslPhysCurrAttainableDataRate
					Gauge32,
				sheXdslPhysCurrDataRate
					Gauge32,
				sheXdslPhysActualStandard
					SheXdslLineStandardType,
				sheXdslPhysPrevDataRate
					Gauge32,
				sheXdslPhysInvSystemVendorID
					SnmpAdminString,
				sheXdslPhysCurrOperationalState
					SheXdslPhysCurrOperationalStateType,
				sheXdslPhysPwrMgmtState
					SheXdslPwrMgmtStateType,
				sheXdslPhysLastStateTransmitted
					SheXdslLastStateTransmittedType,
				sheXdslPhysActualPsd
					Integer32,
				sheXdslPhysSelfTestResult
					Integer32
			 }

		sheXdslPhysSide OBJECT-TYPE
			SYNTAX SheXdslLineEntity
			MAX-ACCESS read-only
			STATUS current
			DESCRIPTION
				"Identifies whether the transceiver is the Xtuc or Xtur."
			::= { sheXdslPhysEntry 1 }

		
		sheXdslPhysInvSerialNumber OBJECT-TYPE
			SYNTAX SnmpAdminString (SIZE (0..32))
			MAX-ACCESS read-only
			STATUS current
			DESCRIPTION
				"The vendor specific string that identifies the vendor equipment.
				The serial number consists of up to 32 ascii characters.
				
				Note: The content of this attribute is not longer applicable for xtuc-side."
			REFERENCE
				"g.997.1 chapter 7.4.7 / 7.4.8"
			::= { sheXdslPhysEntry 2 }

		
		sheXdslPhysInvHSVendorID OBJECT-TYPE
			SYNTAX SnmpAdminString (SIZE (0..8))
			MAX-ACCESS read-only
			STATUS current
			DESCRIPTION
				"The vendor ID code is a copy of the binary vendor 
				identification field expressed as readable characters
				in hexadecimal notation. This field contain the g994.1 Vendor ID."
			REFERENCE
				"g.997.1 chapter 7.4.1 / 7.4.2"
			::= { sheXdslPhysEntry 3 }

		
		sheXdslPhysInvVersionNumber OBJECT-TYPE
			SYNTAX SnmpAdminString (SIZE (0..16))
			MAX-ACCESS read-only
			STATUS current
			DESCRIPTION
				"The vendor specific version number sent by this xtu
				as part of the initialization messages.  It is a copy
				of the binary version number field expressed as 
				readable characters in hexadecimal notation.
				
				Note: The content of this attribute is not longer applicable for xtuc-side."
			REFERENCE
				"g.997.1 chapter 7.4.5 / 7.4.6"
			::= { sheXdslPhysEntry 4 }

		
		sheXdslPhysCurrStatus OBJECT-TYPE
			SYNTAX SheXdslPhysCurrStatusType
			MAX-ACCESS read-only
			STATUS current
			DESCRIPTION
				"Indicates current state of the xtu line. This is a bit-map of possible conditions.
				The various bit positions are:
				
				0   noDefect             There are no defects on the line.
				
				1   lossOfFraming        xtu failure due to not receiving a valid frame.
				
				2   lossOfSignal         xtu failure due to not receiving signal.
				
				3   lossOfPower          xtu failure due to loss of power.
				
				4   lossOfSignalQuality  Loss of Signal Quality is declared when the Noise Margin falls below 
				                         the Minimum Noise Margin, or the bit-error-rate exceeds the configured BER value.
				
				5   lossOfLink           xtu failure due to inability to link with peer xtu. Set whenever
				                         the transceiver is in the 'Warm Start' state.
				
				6   dataInitFailure      xtu failure during initialization due to bit errors corrupting
				                         startup exchange data. That will map to 'Configuration error' (1) failure
				                         from G997.1 chapter 7.5.1.6.
				
				7   configInitFailure    xtu failure during initialization due to peer xtu not able to 
				                         support requested configuration. That will map to
				                         'Configuration not feasible on the line' (2) failure from
				                         G997.1 chapter 7.5.1.6.
				
				8   protocolInitFailure  xtu failure during initialization due to incompatible protocol used 
				                         by the peer xtu. That will map to 'communication problem' (3) failure
				                         from G997.1 chapter 7.5.1.6.
				
				9   noPeerVtuPresent     xtu failure during initialization due to no activation sequence 
				                         detected from peer xtu. That will map to 'No peer xTU detected' (4) failure
				                         from G997.1 chapter 7.5.1.6.
				
				All failures with no single mapping to G997.1 parameters should be understand as a more detailed map to
				'Any other or unknown Initialization Failure cause' (5) from G997.1 chapter 7.5.1.6.
				Only xtu-c side can always deliever trusted information, because most failures will force a line interruption.
				
				This is intended to supplement ifOperStatus."
			REFERENCE
				"G997.1 chapter 7.5.1.6"
			::= { sheXdslPhysEntry 7 }

		
		sheXdslPhysCurrOutputPwr OBJECT-TYPE
			SYNTAX Integer32 (-512 | -311 | -310..310)
			UNITS "0.1dBm"
			MAX-ACCESS read-only
			STATUS current
			DESCRIPTION
				"Measured total output power transmitted by this xTU (ACTATP).
				This is the measurement that was reported during the last activation sequence.
				Special values of -512 or -311 represent, that the transmit power is out of range."
			REFERENCE
				"g.997.1 chapter 7.5.1.24 / 7.5.1.25"
			::= { sheXdslPhysEntry 8 }

		
		sheXdslPhysCurrAttainableDataRate OBJECT-TYPE
			SYNTAX Gauge32
			UNITS "kbps"
			MAX-ACCESS read-only
			STATUS current
			DESCRIPTION
				"Indicates the maximum currently attainable net data rate
				in steps of 1000 bits/second by the xtu.  This value 
				will be equal to or greater than xdslPhysCurrDataRate.
				Note:
				1 kbps = 1000 bps."
			REFERENCE
				"g.997.1 chapter 7.5.1.19 / 7.5.1.20"
			::= { sheXdslPhysEntry 9 }

		
		sheXdslPhysCurrDataRate OBJECT-TYPE
			SYNTAX Gauge32
			UNITS "kbps"
			MAX-ACCESS read-only
			STATUS current
			DESCRIPTION
				"Indicates the current net data rate in steps of 1000
				bits/second by the xtu.  This value will be less than
				or equal to xdslPhysCurrAttainableDataRate.  
				Note: 1 kbps = 1000 bps."
			::= { sheXdslPhysEntry 10 }

		
		sheXdslPhysActualStandard OBJECT-TYPE
			SYNTAX SheXdslLineStandardType
			MAX-ACCESS read-only
			STATUS current
			DESCRIPTION
				"Actual standard used for the connection.
				Only one bit could be set and means, that the corresponding standard is supported."
			REFERENCE
				"g.997.1 chapter 7.5.1.1"
			::= { sheXdslPhysEntry 11 }

		
		sheXdslPhysPrevDataRate OBJECT-TYPE
			SYNTAX Gauge32
			UNITS "kbps"
			MAX-ACCESS read-only
			STATUS current
			DESCRIPTION
				"The net data rate at the time of the last xdslRateChangeTrap event.
				It is also set at initialization to prevent a trap being sent."
			::= { sheXdslPhysEntry 12 }

		
		sheXdslPhysInvSystemVendorID OBJECT-TYPE
			SYNTAX SnmpAdminString (SIZE (0..8))
			MAX-ACCESS read-only
			STATUS current
			DESCRIPTION
				"The vendor ID code is a copy of the binary vendor 
				identification field expressed as readable characters
				in hexadecimal notation. This field contain the system
				vendor ID.
				
				Note: The content of this attribute is not longer applicable for xtuc-side."
			REFERENCE
				"g.997.1 chapter 7.4.3 / 7.4.4"
			::= { sheXdslPhysEntry 13 }

		
		sheXdslPhysCurrOperationalState OBJECT-TYPE
			SYNTAX SheXdslPhysCurrOperationalStateType
			MAX-ACCESS read-only
			STATUS current
			DESCRIPTION
				"Indicates current operational state of the xtu line. Values
				include idle,handshake, training, etc. Only valid for xtu-C side.
				Following states are supported:
				    DSL_OPERSTATE_NOT_INITIALIZED    = 0x00000000,
				    DSL_OPERSTATE_EXCEPTION,         = 0x00000001,
				    DSL_OPERSTATE_IDLE_REQUEST       = 0x000000FF,
				    DSL_OPERSTATE_IDLE               = 0x00000100,
				    DSL_OPERSTATE_SILENT_REQUEST     = 0x000001FF,
				    DSL_OPERSTATE_SILENT             = 0x00000200,
				    DSL_OPERSTATE_HANDSHAKE          = 0x00000300,
				    DSL_OPERSTATE_FULL_INIT          = 0x00000380,
				    DSL_OPERSTATE_DISCOVERY          = 0x00000400,
				    DSL_OPERSTATE_TRAINING           = 0x00000500,
				    DSL_OPERSTATE_ANALYSIS           = 0x00000600,
				    DSL_OPERSTATE_EXCHANGE           = 0x00000700,
				    DSL_OPERSTATE_SHOWTIME_NO_SYNC   = 0x00000800,
				    DSL_OPERSTATE_SHOWTIME_TC_SYNC   = 0x00000801,
				    DSL_OPERSTATE_FASTRETRAIN        = 0x00000900,
				    DSL_OPERSTATE_LOWPOWER_L2        = 0x00000A00,
				    DSL_OPERSTATE_LOOP_ACTIVE        = 0x00000B00,
				    DSL_OPERSTATE_LOOP_DATA_EXCHANGE = 0x00000B10,
				    DSL_OPERSTATE_LOOP_COMPLETE      = 0x00000C00,
				    DSL_OPERSTATE_RESYNC             = 0x00000D00,
				    DSL_OPERSTATE_TEST               = 0x01000000,
				    DSL_OPERSTATE_LOWPOWER_L3        = 0x02000000,
				    DSL_OPERSTATE_UNKNOWN            = 0x03000000
				
				
				"
			::= { sheXdslPhysEntry 14 }

		
		sheXdslPhysPwrMgmtState OBJECT-TYPE
			SYNTAX SheXdslPwrMgmtStateType
			MAX-ACCESS read-only
			STATUS current
			DESCRIPTION
				"Line Power Management State. Only valid for XTUC - side. XTUR will always show
				identical values like XTUC. 
				
				Valid states:
				syncL0(0)    - full transmission
				pwrDownL1(1) - reduced data rate (G992.2 only)
				pwrDownL2(2) - reduced data rate (G992.3, G992.4  and G992.5)
				noPwrL3(3)   - no power transmitted"
			REFERENCE
				"G997.1 chapter 7.5.1.2"
			::= { sheXdslPhysEntry 15 }

		
		sheXdslPhysLastStateTransmitted OBJECT-TYPE
			SYNTAX SheXdslLastStateTransmittedType
			MAX-ACCESS read-only
			STATUS current
			DESCRIPTION
				"This parameter represents the last successful transmitted initialization state in the correspondig
				direction in the last full initialization performed on the line. Initialization states are defined in the
				individual xDSL Recommendations and are counted from 0 (if G.994.1 is used) or 1 (if G.994.1 is
				not used) up to showtime. This parameter must be interpreted along with the xDSL Transmission
				System.
				
				NOTE:
				State 0 .. 11 are identical for central office (xtuc) and remote side (xtur).
				State 12 .. 32 have different meanings on central office and remote side.
				Example: cQuiet4rReverb1(12) -> xtuc has state cQuiet4 and xtur has state rReverb1.
				
				State notAvailable(255) will be reported if the information is not available on IU."
			REFERENCE
				"G997.1 chapter 7.5.1.7 / 7.5.1.8"
			::= { sheXdslPhysEntry 16 }

		
		sheXdslPhysActualPsd OBJECT-TYPE
			SYNTAX Integer32 (-901 | -900..0)
			UNITS "0.1 dBm/Hz"
			MAX-ACCESS read-only
			STATUS current
			DESCRIPTION
				"This parameter is the average transmit PSD over the used subcarriers (subcarriers to
				which user data are allocated) for the corresponding direction 
				(xTU-C for downstream and xTU-R for upstream) at the U-C reference point,
				at the instant of measurement. The PSD level ranges from -90 dBm/Hz (coded as -900) 
				to 0 dBm/Hz (coded as 0) with 0.1 dB steps.
				A special value (coded as -901) indicates the parameter is out of range to be represented. 
				NOTE: The actual power spectrum density is the sum (in dB) of the REFPSD and
				RMSGI. See § 8.5.1/G.992.3.
				
				Note: Only valid for ADSL2 and ADSL2+ mode."
			REFERENCE
				"G997.1 chapter 7.5.1.21 / 7.5.1.22"
			::= { sheXdslPhysEntry 17 }

		
--  info - IMPL: R2.7->
		sheXdslPhysSelfTestResult OBJECT-TYPE
			SYNTAX Integer32
			MAX-ACCESS read-only
			STATUS current
			DESCRIPTION
				"This parameter defines the xTU self-test result. It is coded as a 32-bit integer. The most
				significant octet of the self-test result is 00hex if the self-test passed and 01hex if the self-test failed.
				The interpretation of the other octets is vendor discretionary and can be interpreted in combination
				with G.994.1 and system Vendor IDs."
			REFERENCE
				"G997.1 chapter 7.4.9 / 7.4.10"
			::= { sheXdslPhysEntry 18 }

		
		sheXdslChanTable OBJECT-TYPE
			SYNTAX SEQUENCE OF SheXdslChanEntry
			MAX-ACCESS not-accessible
			STATUS current
			DESCRIPTION
				"This table provides one row for each xtu channel.
				"
			::= { sheXdslMibObjects 4 }

		
		sheXdslChanEntry OBJECT-TYPE
			SYNTAX SheXdslChanEntry
			MAX-ACCESS not-accessible
			STATUS current
			DESCRIPTION
				"An entry in the xdslChanTable.
				Indexed by ifIndex - PhysSide - ChanNum."
			INDEX { ifIndex, sheXdslPhysSide, sheXdslChanNum }
			::= { sheXdslChanTable 1 }

		
		SheXdslChanEntry ::=
			SEQUENCE { 
				sheXdslChanInterleaveDelay
					Gauge32,
				sheXdslChanCurrCrc
					Gauge32,
				sheXdslChanCurrTxRate
					Gauge32,
				sheXdslChanCurrInp
					Integer32,
				sheXdslChanCurrFec
					Gauge32,
				sheXdslChanCurrAtmStatus
					SheXdslChanCurrAtmStatusType,
				sheXdslChanNum
					SheXdslChannelNumType,
				sheXdslChanCurrHec
					Gauge32
			 }

		sheXdslChanInterleaveDelay OBJECT-TYPE
			SYNTAX Gauge32
			UNITS "milliseconds"
			MAX-ACCESS read-only
			STATUS current
			DESCRIPTION
				"Interleave Delay for this channel.
				
				Interleave delay applies only to the interleave 
				(slow) channel and defines the mapping (relative 
				spacing) between subsequent input bytes at the 
				interleaver input and their placement in the bit 
				stream at the interleaver output.  Larger numbers 
				provide greater separation between consecutive 
				input bytes in the output bit stream allowing for 
				improved impulse noise immunity at the expense of 
				payload latency.
				
				In the case where the channel type is fast, return
				a value of zero."
			REFERENCE
				"g.997.1 chapter 7.5.2.3"
			::= { sheXdslChanEntry 1 }

		
		sheXdslChanCurrCrc OBJECT-TYPE
			SYNTAX Gauge32
			MAX-ACCESS read-only
			STATUS current
			DESCRIPTION
				"Actual CRC error count."
			REFERENCE
				"g.997.1 chapter 7.2.2.1.1/7.2.2.2.1"
			::= { sheXdslChanEntry 2 }

		
		sheXdslChanCurrTxRate OBJECT-TYPE
			SYNTAX Gauge32
			UNITS "kbps"
			MAX-ACCESS read-only
			STATUS current
			DESCRIPTION
				"Actual transmit data rate on this channel.  Note: 1
				kbps = 1000 bps."
			REFERENCE
				"g.997.1 chapter 7.5.2.1"
			::= { sheXdslChanEntry 3 }

		
		sheXdslChanCurrInp OBJECT-TYPE
			SYNTAX Integer32 (0..254 | 255)
			UNITS "0.1 symbols"
			MAX-ACCESS read-only
			STATUS current
			DESCRIPTION
				"This parameter reports the actual impulse noise protection (INP) on the bearer channel in the L0
				state. In the L1 or L2 state, the parameter contains the INP in the previous L0 state.
				The value is coded in fractions of DMT symbols with a granularity of 0.1 symbols.
				The range is from 0 to 25.4. A special value 255 indicates an ACTINP higher than 25.4."
			REFERENCE
				"g.997.1 chapter 7.5.2.4"
			::= { sheXdslChanEntry 4 }

		
		sheXdslChanCurrFec OBJECT-TYPE
			SYNTAX Gauge32
			MAX-ACCESS read-only
			STATUS current
			DESCRIPTION
				"Actual Forward Error Correction (FEC)."
			REFERENCE
				"g.997.1 chapter 7.2.2.1.2/7.2.2.2.2"
			::= { sheXdslChanEntry 5 }

		
		sheXdslChanCurrAtmStatus OBJECT-TYPE
			SYNTAX SheXdslChanCurrAtmStatusType
			MAX-ACCESS read-only
			STATUS current
			DESCRIPTION
				"ncd or lcd failure status. This parameter is only valid for lines running ADSL mode. "
			::= { sheXdslChanEntry 6 }

		
		sheXdslChanNum OBJECT-TYPE
			SYNTAX SheXdslChannelNumType
			MAX-ACCESS read-only
			STATUS current
			DESCRIPTION
				"Explains the number of used channel entry!
				
				(1) channel 1
				(2) channel 2 (if exist)"
			::= { sheXdslChanEntry 7 }

		
		sheXdslChanCurrHec OBJECT-TYPE
			SYNTAX Gauge32
			MAX-ACCESS read-only
			STATUS current
			DESCRIPTION
				"The HEC_violation_count performance parameter is a count of the number of occurrences
				of a HEC anomaly in the ATM Data Path."
			REFERENCE
				"g.997.1 chapter 7.2.4.1.1/7.2.4.2.1"
			::= { sheXdslChanEntry 8 }

		
		sheXdslPerfDataTable OBJECT-TYPE
			SYNTAX SEQUENCE OF SheXdslPerfDataEntry
			MAX-ACCESS not-accessible
			STATUS current
			DESCRIPTION
				"This table provides one row for each XDSL physical
				interface.  XDSL physical interfaces are those ifEntries
				where ifType is equal to xdsl(97)."
			::= { sheXdslMibObjects 5 }

		
		sheXdslPerfDataEntry OBJECT-TYPE
			SYNTAX SheXdslPerfDataEntry
			MAX-ACCESS not-accessible
			STATUS current
			DESCRIPTION
				"An entry in the xdslPerfDataTable."
			INDEX { ifIndex, sheXdslPhysSide }
			::= { sheXdslPerfDataTable 1 }

		
		SheXdslPerfDataEntry ::=
			SEQUENCE { 
				sheXdslPerfDataValidIntervals
					HCPerfValidIntervals,
				sheXdslPerfDataInvalidIntervals
					HCPerfInvalidIntervals,
				sheXdslPerfDataLofs
					Unsigned32,
				sheXdslPerfDataLoss
					Unsigned32,
				sheXdslPerfDataLprs
					Unsigned32,
				sheXdslPerfDataLols
					Unsigned32,
				sheXdslPerfDataESs
					Unsigned32,
				sheXdslPerfDataSESs
					Unsigned32,
				sheXdslPerfDataUASs
					Unsigned32,
				sheXdslPerfDataInits
					Unsigned32,
				sheXdslPerfDataCurr15MinTimeElapsed
					Unsigned32,
				sheXdslPerfDataCurr15MinLofs
					Unsigned32,
				sheXdslPerfDataCurr15MinLoss
					Unsigned32,
				sheXdslPerfDataCurr15MinLprs
					Unsigned32,
				sheXdslPerfDataCurr15MinLols
					Unsigned32,
				sheXdslPerfDataCurr15MinESs
					Unsigned32,
				sheXdslPerfDataCurr15MinSESs
					Unsigned32,
				sheXdslPerfDataCurr15MinUASs
					Unsigned32,
				sheXdslPerfDataCurr15MinInits
					Unsigned32,
				sheXdslPerfData1DayValidIntervals
					HCPerfValidIntervals,
				sheXdslPerfData1DayInvalidIntervals
					HCPerfInvalidIntervals,
				sheXdslPerfDataCurr1DayTimeElapsed
					Unsigned32,
				sheXdslPerfDataCurr1DayLofs
					Unsigned32,
				sheXdslPerfDataCurr1DayLoss
					Unsigned32,
				sheXdslPerfDataCurr1DayLprs
					Unsigned32,
				sheXdslPerfDataCurr1DayLols
					Unsigned32,
				sheXdslPerfDataCurr1DayESs
					Unsigned32,
				sheXdslPerfDataCurr1DaySESs
					Unsigned32,
				sheXdslPerfDataCurr1DayUASs
					Unsigned32,
				sheXdslPerfDataCurr1DayInits
					Unsigned32
			 }

		sheXdslPerfDataValidIntervals OBJECT-TYPE
			SYNTAX HCPerfValidIntervals
			UNITS "intervals"
			MAX-ACCESS read-only
			STATUS current
			DESCRIPTION
				"Valid Intervals per definition found in 
				HC-PerfHist-TC-MIB."
			::= { sheXdslPerfDataEntry 1 }

		
		sheXdslPerfDataInvalidIntervals OBJECT-TYPE
			SYNTAX HCPerfInvalidIntervals
			UNITS "intervals"
			MAX-ACCESS read-only
			STATUS current
			DESCRIPTION
				"Invalid Intervals per definition found in 
				HC-PerfHist-TC-MIB."
			::= { sheXdslPerfDataEntry 2 }

		
		sheXdslPerfDataLofs OBJECT-TYPE
			SYNTAX Unsigned32
			UNITS "seconds"
			MAX-ACCESS read-only
			STATUS current
			DESCRIPTION
				"Count of seconds since the unit was last reset that there was Loss of Framing."
			::= { sheXdslPerfDataEntry 3 }

		
		sheXdslPerfDataLoss OBJECT-TYPE
			SYNTAX Unsigned32
			UNITS "seconds"
			MAX-ACCESS read-only
			STATUS current
			DESCRIPTION
				"Count of seconds since the unit was last reset that there was Loss of Signal."
			REFERENCE
				"g.997.1 chapter 7.2.1.1.4/7.2.1.2.4"
			::= { sheXdslPerfDataEntry 4 }

		
		sheXdslPerfDataLprs OBJECT-TYPE
			SYNTAX Unsigned32
			UNITS "seconds"
			MAX-ACCESS read-only
			STATUS current
			DESCRIPTION
				"Count of seconds since the unit was last reset that there was Loss of Power."
			::= { sheXdslPerfDataEntry 5 }

		
		sheXdslPerfDataLols OBJECT-TYPE
			SYNTAX Unsigned32
			UNITS "seconds"
			MAX-ACCESS read-only
			STATUS current
			DESCRIPTION
				"Count of seconds since the unit was last reset that there was Loss of Link."
			::= { sheXdslPerfDataEntry 6 }

		
		sheXdslPerfDataESs OBJECT-TYPE
			SYNTAX Unsigned32
			UNITS "seconds"
			MAX-ACCESS read-only
			STATUS current
			DESCRIPTION
				"Count of Errored Seconds since the unit was last reset.
				An Errored Second is a one-second interval containing one or more CRC anomalies,
				or one or more LOS or LOF defects."
			REFERENCE
				"g.997.1 chapter 7.2.1.1.2/7.2.1.2.2"
			::= { sheXdslPerfDataEntry 7 }

		
		sheXdslPerfDataSESs OBJECT-TYPE
			SYNTAX Unsigned32
			UNITS "seconds"
			MAX-ACCESS read-only
			STATUS current
			DESCRIPTION
				"Count of Severely Errored Seconds since the unit was last reset.
				An SES is declared if, during a 1-second interval, there are 18 or more CRC-8 anomalies
				in one or more of the received bearer channels, or one or more LOS defects, or one or more
				SEF defects, or one or more LPR defects."
			REFERENCE
				"g.997.1 chapter 7.2.1.1.3/7.2.1.2.3"
			::= { sheXdslPerfDataEntry 8 }

		
		sheXdslPerfDataUASs OBJECT-TYPE
			SYNTAX Unsigned32
			UNITS "seconds"
			MAX-ACCESS read-only
			STATUS current
			DESCRIPTION
				"Count of Unavailable Seconds since the unit was last reset.
				The xDSL line becomes unavailable at the onset of 10 contiguous SES-Ls. These 10 SES-Ls shall be
				included in unavailable time. Once unavailable, the xDSL line becomes available at the onset of
				10 contiguous seconds with no SES-Ls."
			REFERENCE
				"g.997.1 chapter 7.2.1.1.5/7.2.1.2.5"
			::= { sheXdslPerfDataEntry 9 }

		
		sheXdslPerfDataInits OBJECT-TYPE
			SYNTAX Unsigned32
			UNITS "occurences"
			MAX-ACCESS read-only
			STATUS current
			DESCRIPTION
				"Count of the line initialization attempts since the unit was last reset.
				This count includes both successful and failed attempts.
				
				Remark: 
				This parameter is shown for near and far end side because of table index design.
				Only the reported value for xtuc side is requested by the standard and should be used."
			REFERENCE
				"g.997.1 chapter 7.2.1.3.1"
			::= { sheXdslPerfDataEntry 10 }

		
		sheXdslPerfDataCurr15MinTimeElapsed OBJECT-TYPE
			SYNTAX Unsigned32
			UNITS "seconds"
			MAX-ACCESS read-only
			STATUS current
			DESCRIPTION
				"Total elapsed seconds in this interval."
			::= { sheXdslPerfDataEntry 11 }

		
		sheXdslPerfDataCurr15MinLofs OBJECT-TYPE
			SYNTAX Unsigned32
			UNITS "seconds"
			MAX-ACCESS read-only
			STATUS current
			DESCRIPTION
				"Count of seconds during this interval that there was Loss of Framing."
			::= { sheXdslPerfDataEntry 12 }

		
		sheXdslPerfDataCurr15MinLoss OBJECT-TYPE
			SYNTAX Unsigned32
			UNITS "seconds"
			MAX-ACCESS read-only
			STATUS current
			DESCRIPTION
				"Count of seconds during this interval that there was Loss of Signal."
			REFERENCE
				"T"
			::= { sheXdslPerfDataEntry 13 }

		
		sheXdslPerfDataCurr15MinLprs OBJECT-TYPE
			SYNTAX Unsigned32
			UNITS "seconds"
			MAX-ACCESS read-only
			STATUS current
			DESCRIPTION
				"Count of seconds during this interval that there was Loss of Power."
			::= { sheXdslPerfDataEntry 14 }

		
		sheXdslPerfDataCurr15MinLols OBJECT-TYPE
			SYNTAX Unsigned32
			UNITS "seconds"
			MAX-ACCESS read-only
			STATUS current
			DESCRIPTION
				"Count of seconds during this interval that there was Loss of Link."
			::= { sheXdslPerfDataEntry 15 }

		
		sheXdslPerfDataCurr15MinESs OBJECT-TYPE
			SYNTAX Unsigned32
			UNITS "seconds"
			MAX-ACCESS read-only
			STATUS current
			DESCRIPTION
				"Count of Errored Seconds during this interval.  
				An Errored Second is a one-second interval containing one or more CRC anomalies, or one or more LOS or LOF defects."
			::= { sheXdslPerfDataEntry 16 }

		
		sheXdslPerfDataCurr15MinSESs OBJECT-TYPE
			SYNTAX Unsigned32
			UNITS "seconds"
			MAX-ACCESS read-only
			STATUS current
			DESCRIPTION
				"Count of Severely Errored Seconds during this interval."
			::= { sheXdslPerfDataEntry 17 }

		
		sheXdslPerfDataCurr15MinUASs OBJECT-TYPE
			SYNTAX Unsigned32
			UNITS "seconds"
			MAX-ACCESS read-only
			STATUS current
			DESCRIPTION
				"Count of Unavailable Seconds during this interval."
			::= { sheXdslPerfDataEntry 18 }

		
		sheXdslPerfDataCurr15MinInits OBJECT-TYPE
			SYNTAX Unsigned32
			UNITS "occurences"
			MAX-ACCESS read-only
			STATUS current
			DESCRIPTION
				"Count of the line initialization attempts during this interval.  
				This count includes both successful and failed attempts.
				
				Remark: 
				This parameter is shown for near and far end side because of table index design.
				Only the reported value for xtuc side is requested by the standard and should be used."
			::= { sheXdslPerfDataEntry 19 }

		
		sheXdslPerfData1DayValidIntervals OBJECT-TYPE
			SYNTAX HCPerfValidIntervals
			UNITS "intervals"
			MAX-ACCESS read-only
			STATUS current
			DESCRIPTION
				"Valid Intervals per definition found in
				HC-PerfHist-TC-MIB."
			::= { sheXdslPerfDataEntry 20 }

		
		sheXdslPerfData1DayInvalidIntervals OBJECT-TYPE
			SYNTAX HCPerfInvalidIntervals
			UNITS "intervals"
			MAX-ACCESS read-only
			STATUS current
			DESCRIPTION
				"Invalid Intervals per definition found in 
				HC-PerfHist-TC-MIB."
			::= { sheXdslPerfDataEntry 21 }

		
		sheXdslPerfDataCurr1DayTimeElapsed OBJECT-TYPE
			SYNTAX Unsigned32
			UNITS "seconds"
			MAX-ACCESS read-only
			STATUS current
			DESCRIPTION
				"Number of seconds that have elapsed since the beginning
				of the current 1-day interval."
			::= { sheXdslPerfDataEntry 22 }

		
		sheXdslPerfDataCurr1DayLofs OBJECT-TYPE
			SYNTAX Unsigned32
			UNITS "seconds"
			MAX-ACCESS read-only
			STATUS current
			DESCRIPTION
				"Count of Loss of Framing (LOF) Seconds since the beginning of the current 1-day interval."
			::= { sheXdslPerfDataEntry 23 }

		
		sheXdslPerfDataCurr1DayLoss OBJECT-TYPE
			SYNTAX Unsigned32
			UNITS "seconds"
			MAX-ACCESS read-only
			STATUS current
			DESCRIPTION
				"Count of Loss of Signal (LOS) Seconds since the beginning of the current 1-day interval."
			::= { sheXdslPerfDataEntry 24 }

		
		sheXdslPerfDataCurr1DayLprs OBJECT-TYPE
			SYNTAX Unsigned32
			UNITS "seconds"
			MAX-ACCESS read-only
			STATUS current
			DESCRIPTION
				"Count of Loss of Power (LPR) Seconds since the beginning of the current 1-day interval."
			::= { sheXdslPerfDataEntry 25 }

		
		sheXdslPerfDataCurr1DayLols OBJECT-TYPE
			SYNTAX Unsigned32
			UNITS "seconds"
			MAX-ACCESS read-only
			STATUS current
			DESCRIPTION
				"Count of Loss of Link (LOL) Seconds since the beginning of the current 1-day interval."
			::= { sheXdslPerfDataEntry 26 }

		
		sheXdslPerfDataCurr1DayESs OBJECT-TYPE
			SYNTAX Unsigned32
			UNITS "seconds"
			MAX-ACCESS read-only
			STATUS current
			DESCRIPTION
				"Count of Errored Seconds (ES) since the beginning of the current 1-day interval."
			::= { sheXdslPerfDataEntry 27 }

		
		sheXdslPerfDataCurr1DaySESs OBJECT-TYPE
			SYNTAX Unsigned32
			UNITS "seconds"
			MAX-ACCESS read-only
			STATUS current
			DESCRIPTION
				"Count of Severely Errored Seconds (SES) since the beginning of the current 1-day interval."
			::= { sheXdslPerfDataEntry 28 }

		
		sheXdslPerfDataCurr1DayUASs OBJECT-TYPE
			SYNTAX Unsigned32
			UNITS "seconds"
			MAX-ACCESS read-only
			STATUS current
			DESCRIPTION
				"Count of Unavailable Seconds (UAS) since the beginning of the current 1-day interval."
			::= { sheXdslPerfDataEntry 29 }

		
		sheXdslPerfDataCurr1DayInits OBJECT-TYPE
			SYNTAX Unsigned32
			UNITS "occurences"
			MAX-ACCESS read-only
			STATUS current
			DESCRIPTION
				"Count of the line initialization attempts since the beginning of the current 1-day interval.
				This count includes both successful and failed attempts.
				
				Remark: 
				This parameter is shown for near and far end side because of table index design.
				Only the reported value for xtuc side is requested by the standard and should be used."
			::= { sheXdslPerfDataEntry 30 }

		
		sheXdslPerfIntervalTable OBJECT-TYPE
			SYNTAX SEQUENCE OF SheXdslPerfIntervalEntry
			MAX-ACCESS not-accessible
			STATUS current
			DESCRIPTION
				"This table provides one row for each xtu performance 
				data collection interval.  XDSL physical interfaces are
				those ifEntries where ifType is equal to xdsl(97) or adsl2 (230)."
			::= { sheXdslMibObjects 6 }

		
		sheXdslPerfIntervalEntry OBJECT-TYPE
			SYNTAX SheXdslPerfIntervalEntry
			MAX-ACCESS not-accessible
			STATUS current
			DESCRIPTION
				"An entry in the xdslPerfIntervalTable."
			INDEX { ifIndex, sheXdslPhysSide, sheXdslPerfIntervalNumber }
			::= { sheXdslPerfIntervalTable 1 }

		
		SheXdslPerfIntervalEntry ::=
			SEQUENCE { 
				sheXdslPerfIntervalNumber
					Unsigned32,
				sheXdslPerfIntervalValidData
					TruthValue,
				sheXdslPerfIntervalEndTime
					Unsigned32,
				sheXdslPerfIntervalLofs
					Unsigned32,
				sheXdslPerfIntervalLoss
					Unsigned32,
				sheXdslPerfIntervalLprs
					Unsigned32,
				sheXdslPerfIntervalLols
					Unsigned32,
				sheXdslPerfIntervalESs
					Unsigned32,
				sheXdslPerfIntervalSESs
					Unsigned32,
				sheXdslPerfIntervalUASs
					Unsigned32,
				sheXdslPerfIntervalInits
					Unsigned32
			 }

		sheXdslPerfIntervalNumber OBJECT-TYPE
			SYNTAX Unsigned32 (1..96)
			MAX-ACCESS read-only
			STATUS current
			DESCRIPTION
				"Performance Data Interval number 1 is the most recent 
				previous interval; interval 96 is 24 hours ago.  
				Intervals 2 to 96 are optional."
			::= { sheXdslPerfIntervalEntry 1 }

		
		sheXdslPerfIntervalValidData OBJECT-TYPE
			SYNTAX TruthValue
			MAX-ACCESS read-only
			STATUS current
			DESCRIPTION
				"This variable indicates if the data for this interval is valid."
			::= { sheXdslPerfIntervalEntry 2 }

		
		sheXdslPerfIntervalEndTime OBJECT-TYPE
			SYNTAX Unsigned32
			UNITS "seconds"
			MAX-ACCESS read-only
			STATUS current
			DESCRIPTION
				"This variable indicates the time of storing this interval."
			::= { sheXdslPerfIntervalEntry 3 }

		
		sheXdslPerfIntervalLofs OBJECT-TYPE
			SYNTAX Unsigned32
			UNITS "seconds"
			MAX-ACCESS read-only
			STATUS current
			DESCRIPTION
				"Count of seconds in the interval when there was Loss of Framing."
			::= { sheXdslPerfIntervalEntry 4 }

		
		sheXdslPerfIntervalLoss OBJECT-TYPE
			SYNTAX Unsigned32
			UNITS "seconds"
			MAX-ACCESS read-only
			STATUS current
			DESCRIPTION
				"Count of seconds in the interval when there was Loss of Signal."
			::= { sheXdslPerfIntervalEntry 5 }

		
		sheXdslPerfIntervalLprs OBJECT-TYPE
			SYNTAX Unsigned32
			UNITS "seconds"
			MAX-ACCESS read-only
			STATUS current
			DESCRIPTION
				"Count of seconds in the interval when there was Loss of Power."
			::= { sheXdslPerfIntervalEntry 6 }

		
		sheXdslPerfIntervalLols OBJECT-TYPE
			SYNTAX Unsigned32
			UNITS "seconds"
			MAX-ACCESS read-only
			STATUS current
			DESCRIPTION
				"Count of seconds in the interval when there was Loss of Link."
			::= { sheXdslPerfIntervalEntry 7 }

		
		sheXdslPerfIntervalESs OBJECT-TYPE
			SYNTAX Unsigned32
			UNITS "seconds"
			MAX-ACCESS read-only
			STATUS current
			DESCRIPTION
				"Count of Errored Seconds (ES) in the interval.  
				An Errored Second is a one-second interval containing one or more CRC anomalies, one or more LOS or LOF defects."
			::= { sheXdslPerfIntervalEntry 8 }

		
		sheXdslPerfIntervalSESs OBJECT-TYPE
			SYNTAX Unsigned32
			UNITS "seconds"
			MAX-ACCESS read-only
			STATUS current
			DESCRIPTION
				"Count of Severely Errored Seconds in the interval."
			::= { sheXdslPerfIntervalEntry 9 }

		
		sheXdslPerfIntervalUASs OBJECT-TYPE
			SYNTAX Unsigned32
			UNITS "seconds"
			MAX-ACCESS read-only
			STATUS current
			DESCRIPTION
				"Count of Unavailable Seconds in the interval."
			::= { sheXdslPerfIntervalEntry 10 }

		
		sheXdslPerfIntervalInits OBJECT-TYPE
			SYNTAX Unsigned32
			UNITS "occurences"
			MAX-ACCESS read-only
			STATUS current
			DESCRIPTION
				"Count of the line initialization attempts during this interval.
				This count includes both successful and failed attempts.
				
				Remark: 
				This parameter is shown for near and far end side because of table index design.
				Only the reported value for xtuc side is requested by the standard and should be used."
			::= { sheXdslPerfIntervalEntry 11 }

		
		sheXdslPerf1DayIntervalTable OBJECT-TYPE
			SYNTAX SEQUENCE OF SheXdslPerf1DayIntervalEntry
			MAX-ACCESS not-accessible
			STATUS current
			DESCRIPTION
				"This table provides one row for each XDSL performance 
				data collection interval.  This table contains live data 
				from equipment.  As such, it is NOT persistent."
			::= { sheXdslMibObjects 7 }

		
		sheXdslPerf1DayIntervalEntry OBJECT-TYPE
			SYNTAX SheXdslPerf1DayIntervalEntry
			MAX-ACCESS not-accessible
			STATUS current
			DESCRIPTION
				"An entry in the xdslPerf1DayIntervalTable."
			INDEX { ifIndex, sheXdslPhysSide, sheXdslPerf1DayIntervalNumber }
			::= { sheXdslPerf1DayIntervalTable 1 }

		
		SheXdslPerf1DayIntervalEntry ::=
			SEQUENCE { 
				sheXdslPerf1DayIntervalNumber
					Unsigned32,
				sheXdslPerf1DayIntervalMoniSecs
					HCPerfTimeElapsed,
				sheXdslPerf1DayIntervalLofs
					Unsigned32,
				sheXdslPerf1DayIntervalLoss
					Unsigned32,
				sheXdslPerf1DayIntervalLprs
					Unsigned32,
				sheXdslPerf1DayIntervalLols
					Unsigned32,
				sheXdslPerf1DayIntervalESs
					Unsigned32,
				sheXdslPerf1DayIntervalSESs
					Unsigned32,
				sheXdslPerf1DayIntervalUASs
					Unsigned32,
				sheXdslPerf1DayIntervalInits
					Unsigned32,
				sheXdslPerf1DayIntervalEndTime
					Unsigned32
			 }

		sheXdslPerf1DayIntervalNumber OBJECT-TYPE
			SYNTAX Unsigned32 (1..7)
			MAX-ACCESS read-only
			STATUS current
			DESCRIPTION
				"History Data Interval number.  Interval 1 is the most recent previous day;
				interval 7 is 7 days ago.  Intervals 2 to 7 are optional."
			::= { sheXdslPerf1DayIntervalEntry 1 }

		
		sheXdslPerf1DayIntervalMoniSecs OBJECT-TYPE
			SYNTAX HCPerfTimeElapsed
			UNITS "seconds"
			MAX-ACCESS read-only
			STATUS current
			DESCRIPTION
				"The amount of time in the 1-day interval over which the
				performance monitoring information is actually counted.
				This value will be the same as the interval duration except
				in a situation where performance monitoring data could not
				be collected for any reason."
			::= { sheXdslPerf1DayIntervalEntry 2 }

		
		sheXdslPerf1DayIntervalLofs OBJECT-TYPE
			SYNTAX Unsigned32
			UNITS "seconds"
			MAX-ACCESS read-only
			STATUS current
			DESCRIPTION
				"Count of Loss of Frame (LOF) Seconds during the 1-day interval."
			::= { sheXdslPerf1DayIntervalEntry 3 }

		
		sheXdslPerf1DayIntervalLoss OBJECT-TYPE
			SYNTAX Unsigned32
			UNITS "seconds"
			MAX-ACCESS read-only
			STATUS current
			DESCRIPTION
				"Count of Loss of Signal (LOS) Seconds during the 1-day interval."
			::= { sheXdslPerf1DayIntervalEntry 4 }

		
		sheXdslPerf1DayIntervalLprs OBJECT-TYPE
			SYNTAX Unsigned32
			UNITS "seconds"
			MAX-ACCESS read-only
			STATUS current
			DESCRIPTION
				"Count of Loss of Power (LPR) Seconds during the 1-day interval."
			::= { sheXdslPerf1DayIntervalEntry 5 }

		
		sheXdslPerf1DayIntervalLols OBJECT-TYPE
			SYNTAX Unsigned32
			UNITS "seconds"
			MAX-ACCESS read-only
			STATUS current
			DESCRIPTION
				"Count of Loss of Link (LOL) Seconds during the 1-day interval."
			::= { sheXdslPerf1DayIntervalEntry 6 }

		
		sheXdslPerf1DayIntervalESs OBJECT-TYPE
			SYNTAX Unsigned32
			UNITS "seconds"
			MAX-ACCESS read-only
			STATUS current
			DESCRIPTION
				"Count of Errored Seconds (ES) during the 1-day interval."
			::= { sheXdslPerf1DayIntervalEntry 7 }

		
		sheXdslPerf1DayIntervalSESs OBJECT-TYPE
			SYNTAX Unsigned32
			UNITS "seconds"
			MAX-ACCESS read-only
			STATUS current
			DESCRIPTION
				"Count of Severely Errored Seconds (SES) during the 1-day."
			::= { sheXdslPerf1DayIntervalEntry 8 }

		
		sheXdslPerf1DayIntervalUASs OBJECT-TYPE
			SYNTAX Unsigned32
			UNITS "seconds"
			MAX-ACCESS read-only
			STATUS current
			DESCRIPTION
				"Count of Unavailable Seconds (UAS) during the 1-day interval."
			::= { sheXdslPerf1DayIntervalEntry 9 }

		
		sheXdslPerf1DayIntervalInits OBJECT-TYPE
			SYNTAX Unsigned32
			UNITS "occurences"
			MAX-ACCESS read-only
			STATUS current
			DESCRIPTION
				"Count of the line initialization attempts during the 1-day interval.
				This count includes both successful and failed attempts.
				
				Remark: 
				This parameter is shown for near and far end side because of table index design.
				Only the reported value for xtuc side is requested by the standard and should be used."
			::= { sheXdslPerf1DayIntervalEntry 10 }

		
		sheXdslPerf1DayIntervalEndTime OBJECT-TYPE
			SYNTAX Unsigned32
			UNITS "seconds"
			MAX-ACCESS read-only
			STATUS current
			DESCRIPTION
				"This variable indicates the time of storing this interval."
			::= { sheXdslPerf1DayIntervalEntry 11 }

		
		sheXdslChanPerfDataTable OBJECT-TYPE
			SYNTAX SEQUENCE OF SheXdslChanPerfDataEntry
			MAX-ACCESS not-accessible
			STATUS current
			DESCRIPTION
				"This table provides one row for each xtu channel."
			::= { sheXdslMibObjects 8 }

		
		sheXdslChanPerfDataEntry OBJECT-TYPE
			SYNTAX SheXdslChanPerfDataEntry
			MAX-ACCESS not-accessible
			STATUS current
			DESCRIPTION
				"An entry in the xdslChanPerfDataTable.
				Indexed by ifIndex - PhysSide - ChanNum."
			INDEX { ifIndex, sheXdslPhysSide, sheXdslChanNum }
			::= { sheXdslChanPerfDataTable 1 }

		
		SheXdslChanPerfDataEntry ::=
			SEQUENCE { 
				sheXdslChanValidIntervals
					HCPerfValidIntervals,
				sheXdslChanInvalidIntervals
					HCPerfInvalidIntervals,
				sheXdslChanFecCount
					HCPerfCurrentCount,
				sheXdslChanCodingViolationCount
					HCPerfCurrentCount,
				sheXdslChanCurr15MinTimeElapsed
					HCPerfTimeElapsed,
				sheXdslChanCurr15MinFecCount
					HCPerfCurrentCount,
				sheXdslChanCurr15MinCodingViolationCount
					HCPerfCurrentCount,
				sheXdslChan1DayValidIntervals
					HCPerfValidIntervals,
				sheXdslChan1DayInvalidIntervals
					HCPerfInvalidIntervals,
				sheXdslChanCurr1DayTimeElapsed
					HCPerfTimeElapsed,
				sheXdslChanCurr1DayFecCount
					HCPerfCurrentCount,
				sheXdslChanCurr1DayCodingViolationCount
					HCPerfCurrentCount,
				sheXdslChanCrcCount
					HCPerfCurrentCount,
				sheXdslChanHecCount
					HCPerfCurrentCount,
				sheXdslChanDelineatedTotalCellCount
					HCPerfCurrentCount,
				sheXdslChanUserTotalCellCount
					HCPerfCurrentCount,
				sheXdslChanIdleCellBitErrorCount
					HCPerfCurrentCount,
				sheXdslChanCurr15MinCrcCount
					HCPerfCurrentCount,
				sheXdslChanCurr15MinHecCount
					HCPerfCurrentCount,
				sheXdslChanCurr15MinDelineatedTotalCellCount
					HCPerfCurrentCount,
				sheXdslChanCurr15MinUserTotalCellCount
					HCPerfCurrentCount,
				sheXdslChanCurr15MinIdleCellBitErrorCount
					HCPerfCurrentCount,
				sheXdslChanCurr1DayCrcCount
					HCPerfCurrentCount,
				sheXdslChanCurr1DayHecCount
					HCPerfCurrentCount,
				sheXdslChanCurr1DayDelineatedTotalCellCount
					HCPerfCurrentCount,
				sheXdslChanCurr1DayUserTotalCellCount
					HCPerfCurrentCount,
				sheXdslChanCurr1DayIdleCellBitErrorCount
					HCPerfCurrentCount
			 }

		sheXdslChanValidIntervals OBJECT-TYPE
			SYNTAX HCPerfValidIntervals
			UNITS "intervals"
			MAX-ACCESS read-only
			STATUS current
			DESCRIPTION
				"Valid Intervals per definition found in 
				HC-PerfHist-TC-MIB."
			::= { sheXdslChanPerfDataEntry 1 }

		
		sheXdslChanInvalidIntervals OBJECT-TYPE
			SYNTAX HCPerfInvalidIntervals
			UNITS "intervals"
			MAX-ACCESS read-only
			STATUS current
			DESCRIPTION
				"Invalid Intervals per definition found in 
				HC-PerfHist-TC-MIB."
			::= { sheXdslChanPerfDataEntry 2 }

		
		sheXdslChanFecCount OBJECT-TYPE
			SYNTAX HCPerfCurrentCount
			MAX-ACCESS read-only
			STATUS current
			DESCRIPTION
				"This parameter is a count of FEC anomalies (the number of corrected code words) occurring in the
				bearer channel during the accumulation period."
			REFERENCE
				"g.997.1 chapter 7.2.2.1.2/7.2.2.2.2"
			::= { sheXdslChanPerfDataEntry 3 }

		
		sheXdslChanCodingViolationCount OBJECT-TYPE
			SYNTAX HCPerfCurrentCount
			MAX-ACCESS read-only
			STATUS current
			DESCRIPTION
				"That CV-P performance parameter is a count of the number of occurrences of a cv-n anomaly in the
				PTM Data Path."
			REFERENCE
				"g.997.1 chapter 7.2.5.1.2/7.2.5.2.2"
			::= { sheXdslChanPerfDataEntry 4 }

		
		sheXdslChanCurr15MinTimeElapsed OBJECT-TYPE
			SYNTAX HCPerfTimeElapsed
			UNITS "seconds"
			MAX-ACCESS read-only
			STATUS current
			DESCRIPTION
				"Total elapsed seconds in this interval."
			::= { sheXdslChanPerfDataEntry 5 }

		
		sheXdslChanCurr15MinFecCount OBJECT-TYPE
			SYNTAX HCPerfCurrentCount
			MAX-ACCESS read-only
			STATUS current
			DESCRIPTION
				"This parameter is a count of FEC anomalies (the number of corrected code words) occurring in the
				bearer channel during the accumulation period."
			REFERENCE
				"g.997.1 chapter 7.2.2.1.2/7.2.2.2.2"
			::= { sheXdslChanPerfDataEntry 6 }

		
		sheXdslChanCurr15MinCodingViolationCount OBJECT-TYPE
			SYNTAX HCPerfCurrentCount
			MAX-ACCESS read-only
			STATUS current
			DESCRIPTION
				"That CV-P performance parameter is a count of the number of occurrences of a cv-n anomaly in the
				PTM Data Path."
			REFERENCE
				"g.997.1 chapter 7.2.5.1.2/7.2.5.2.2"
			::= { sheXdslChanPerfDataEntry 7 }

		
		sheXdslChan1DayValidIntervals OBJECT-TYPE
			SYNTAX HCPerfValidIntervals
			MAX-ACCESS read-only
			STATUS current
			DESCRIPTION
				"Valid Intervals per definition found in 
				HC-PerfHist-TC-MIB."
			::= { sheXdslChanPerfDataEntry 8 }

		
		sheXdslChan1DayInvalidIntervals OBJECT-TYPE
			SYNTAX HCPerfInvalidIntervals
			MAX-ACCESS read-only
			STATUS current
			DESCRIPTION
				"Invalid Intervals per definition found in 
				HC-PerfHist-TC-MIB."
			::= { sheXdslChanPerfDataEntry 9 }

		
		sheXdslChanCurr1DayTimeElapsed OBJECT-TYPE
			SYNTAX HCPerfTimeElapsed
			UNITS "seconds"
			MAX-ACCESS read-only
			STATUS current
			DESCRIPTION
				"Number of seconds that have elapsed since the beginning
				of the current 1-day interval."
			::= { sheXdslChanPerfDataEntry 10 }

		
		sheXdslChanCurr1DayFecCount OBJECT-TYPE
			SYNTAX HCPerfCurrentCount
			MAX-ACCESS read-only
			STATUS current
			DESCRIPTION
				"This parameter is a count of FEC anomalies (the number of corrected code words) occurring in the
				bearer channel during the accumulation period."
			REFERENCE
				"g.997.1 chapter 7.2.2.1.2/7.2.2.2.2"
			::= { sheXdslChanPerfDataEntry 11 }

		
		sheXdslChanCurr1DayCodingViolationCount OBJECT-TYPE
			SYNTAX HCPerfCurrentCount
			MAX-ACCESS read-only
			STATUS current
			DESCRIPTION
				"That CV-P performance parameter is a count of the number of occurrences of a cv-n anomaly in the
				PTM Data Path."
			REFERENCE
				"g.997.1 chapter 7.2.5.1.2/7.2.5.2.2"
			::= { sheXdslChanPerfDataEntry 12 }

		
		sheXdslChanCrcCount OBJECT-TYPE
			SYNTAX HCPerfCurrentCount
			MAX-ACCESS read-only
			STATUS current
			DESCRIPTION
				"The CRC-P performance parameter is a count of the number of occurrences of a CRC-n anomaly in
				the PTM Data Path."
			REFERENCE
				"g.997.1 chapter 7.2.5.1.1/7.2.5.2.1"
			::= { sheXdslChanPerfDataEntry 13 }

		
		sheXdslChanHecCount OBJECT-TYPE
			SYNTAX HCPerfCurrentCount
			MAX-ACCESS read-only
			STATUS current
			DESCRIPTION
				"The HEC_violation_count performance parameter is a count of the number of occurrences
				of a HEC anomaly in the ATM Data Path."
			REFERENCE
				"g.997.1 chapter 7.2.4.1.1/7.2.4.2.1"
			::= { sheXdslChanPerfDataEntry 14 }

		
		sheXdslChanDelineatedTotalCellCount OBJECT-TYPE
			SYNTAX HCPerfCurrentCount
			MAX-ACCESS read-only
			STATUS current
			DESCRIPTION
				"The delineated_total_cell_count performance parameter is a count of the total number of
				cells passed through the cell delineation process and HEC function operating on the ATM Data Path
				while in the SYNC state."
			REFERENCE
				"g.997.1 chapter 7.2.4.1.2/7.2.4.2.2"
			::= { sheXdslChanPerfDataEntry 15 }

		
		sheXdslChanUserTotalCellCount OBJECT-TYPE
			SYNTAX HCPerfCurrentCount
			MAX-ACCESS read-only
			STATUS current
			DESCRIPTION
				"The User_total_cell_count performance parameter is a count of the total number of cells in
				the ATM Data Path."
			REFERENCE
				"g.997.1 chapter 7.2.4.1.3/7.2.4.2.3"
			::= { sheXdslChanPerfDataEntry 16 }

		
		sheXdslChanIdleCellBitErrorCount OBJECT-TYPE
			SYNTAX HCPerfCurrentCount
			MAX-ACCESS read-only
			STATUS current
			DESCRIPTION
				"The idle_bit_error_count performance parameter is a count of the number of bit errors in the
				idle cell payload received in the ATM Data Path."
			REFERENCE
				"g.997.1 chapter 7.2.4.1.4/7.2.4.2.4"
			::= { sheXdslChanPerfDataEntry 17 }

		
		sheXdslChanCurr15MinCrcCount OBJECT-TYPE
			SYNTAX HCPerfCurrentCount
			MAX-ACCESS read-only
			STATUS current
			DESCRIPTION
				"The CRC-P performance parameter is a count of the number of occurrences of a CRC-n anomaly in
				the PTM Data Path."
			REFERENCE
				"g.997.1 chapter 7.2.5.1.1/7.2.5.2.1"
			::= { sheXdslChanPerfDataEntry 18 }

		
		sheXdslChanCurr15MinHecCount OBJECT-TYPE
			SYNTAX HCPerfCurrentCount
			MAX-ACCESS read-only
			STATUS current
			DESCRIPTION
				"The HEC_violation_count performance parameter is a count of the number of occurrences
				of a HEC anomaly in the ATM Data Path."
			REFERENCE
				"g.997.1 chapter 7.2.4.1.1/7.2.4.2.1"
			::= { sheXdslChanPerfDataEntry 19 }

		
		sheXdslChanCurr15MinDelineatedTotalCellCount OBJECT-TYPE
			SYNTAX HCPerfCurrentCount
			MAX-ACCESS read-only
			STATUS current
			DESCRIPTION
				"The delineated_total_cell_count performance parameter is a count of the total number of
				cells passed through the cell delineation process and HEC function operating on the ATM Data Path
				while in the SYNC state."
			REFERENCE
				"g.997.1 chapter 7.2.4.1.2/7.2.4.2.2"
			::= { sheXdslChanPerfDataEntry 20 }

		
		sheXdslChanCurr15MinUserTotalCellCount OBJECT-TYPE
			SYNTAX HCPerfCurrentCount
			MAX-ACCESS read-only
			STATUS current
			DESCRIPTION
				"The User_total_cell_count performance parameter is a count of the total number of cells in
				the ATM Data Path."
			REFERENCE
				"g.997.1 chapter 7.2.4.1.3/7.2.4.2.3"
			::= { sheXdslChanPerfDataEntry 21 }

		
		sheXdslChanCurr15MinIdleCellBitErrorCount OBJECT-TYPE
			SYNTAX HCPerfCurrentCount
			MAX-ACCESS read-only
			STATUS current
			DESCRIPTION
				"The idle_bit_error_count performance parameter is a count of the number of bit errors in the
				idle cell payload received in the ATM Data Path."
			REFERENCE
				"g.997.1 chapter 7.2.4.1.4/7.2.4.2.4"
			::= { sheXdslChanPerfDataEntry 22 }

		
		sheXdslChanCurr1DayCrcCount OBJECT-TYPE
			SYNTAX HCPerfCurrentCount
			MAX-ACCESS read-only
			STATUS current
			DESCRIPTION
				"The CRC-P performance parameter is a count of the number of occurrences of a CRC-n anomaly in
				the PTM Data Path."
			REFERENCE
				"g.997.1 chapter 7.2.5.1.1/7.2.5.2.1"
			::= { sheXdslChanPerfDataEntry 23 }

		
		sheXdslChanCurr1DayHecCount OBJECT-TYPE
			SYNTAX HCPerfCurrentCount
			MAX-ACCESS read-only
			STATUS current
			DESCRIPTION
				"The HEC_violation_count performance parameter is a count of the number of occurrences
				of a HEC anomaly in the ATM Data Path."
			REFERENCE
				"g.997.1 chapter 7.2.4.1.1/7.2.4.2.1"
			::= { sheXdslChanPerfDataEntry 24 }

		
		sheXdslChanCurr1DayDelineatedTotalCellCount OBJECT-TYPE
			SYNTAX HCPerfCurrentCount
			MAX-ACCESS read-only
			STATUS current
			DESCRIPTION
				"The delineated_total_cell_count performance parameter is a count of the total number of
				cells passed through the cell delineation process and HEC function operating on the ATM Data Path
				while in the SYNC state."
			REFERENCE
				"g.997.1 chapter 7.2.4.1.2/7.2.4.2.2"
			::= { sheXdslChanPerfDataEntry 25 }

		
		sheXdslChanCurr1DayUserTotalCellCount OBJECT-TYPE
			SYNTAX HCPerfCurrentCount
			MAX-ACCESS read-only
			STATUS current
			DESCRIPTION
				"The User_total_cell_count performance parameter is a count of the total number of cells in
				the ATM Data Path."
			REFERENCE
				"g.997.1 chapter 7.2.4.1.3/7.2.4.2.3"
			::= { sheXdslChanPerfDataEntry 26 }

		
		sheXdslChanCurr1DayIdleCellBitErrorCount OBJECT-TYPE
			SYNTAX HCPerfCurrentCount
			MAX-ACCESS read-only
			STATUS current
			DESCRIPTION
				"The idle_bit_error_count performance parameter is a count of the number of bit errors in the
				idle cell payload received in the ATM Data Path."
			REFERENCE
				"g.997.1 chapter 7.2.4.1.4/7.2.4.2.4"
			::= { sheXdslChanPerfDataEntry 27 }

		
		sheXdslChanIntervalTable OBJECT-TYPE
			SYNTAX SEQUENCE OF SheXdslChanIntervalEntry
			MAX-ACCESS not-accessible
			STATUS current
			DESCRIPTION
				"This table provides one row for each xtu channel data 
				collection interval. This table contains live data 
				from equipment.  As such, it is NOT persistent."
			::= { sheXdslMibObjects 9 }

		
		sheXdslChanIntervalEntry OBJECT-TYPE
			SYNTAX SheXdslChanIntervalEntry
			MAX-ACCESS not-accessible
			STATUS current
			DESCRIPTION
				"An entry in the xdslChanIntervalTable.
				Indexed by ifIndex - PhysSide - ChanNum - IntervalNumber."
			INDEX { ifIndex, sheXdslPhysSide, sheXdslChanNum, sheXdslChanIntervalNumber }
			::= { sheXdslChanIntervalTable 1 }

		
		SheXdslChanIntervalEntry ::=
			SEQUENCE { 
				sheXdslChanIntervalNumber
					Unsigned32,
				sheXdslChanIntervalValidData
					TruthValue,
				sheXdslChanIntervalEndTime
					Unsigned32,
				sheXdslChanIntervalFecCount
					HCPerfIntervalCount,
				sheXdslChanIntervalCodingViolationCount
					HCPerfIntervalCount,
				sheXdslChanIntervalCrcCount
					HCPerfCurrentCount,
				sheXdslChanIntervalHecCount
					HCPerfCurrentCount,
				sheXdslChanIntervalDelineatedTotalCellCount
					HCPerfCurrentCount,
				sheXdslChanIntervalUserTotalCellCount
					HCPerfCurrentCount,
				sheXdslChanIntervalIdleCellBitErrorCount
					HCPerfCurrentCount
			 }

		sheXdslChanIntervalNumber OBJECT-TYPE
			SYNTAX Unsigned32 (1..96)
			MAX-ACCESS read-only
			STATUS current
			DESCRIPTION
				"Performance Data Interval number 1 is the most recent 
				previous interval; interval 96 is 24 hours ago.  
				Intervals 2 to 96 are optional."
			::= { sheXdslChanIntervalEntry 1 }

		
		sheXdslChanIntervalValidData OBJECT-TYPE
			SYNTAX TruthValue
			MAX-ACCESS read-only
			STATUS current
			DESCRIPTION
				"This variable indicates if the data for this interval is valid."
			::= { sheXdslChanIntervalEntry 2 }

		
		sheXdslChanIntervalEndTime OBJECT-TYPE
			SYNTAX Unsigned32
			UNITS "seconds"
			MAX-ACCESS read-only
			STATUS current
			DESCRIPTION
				"This variable indicates the time of storing this interval."
			::= { sheXdslChanIntervalEntry 3 }

		
		sheXdslChanIntervalFecCount OBJECT-TYPE
			SYNTAX HCPerfIntervalCount
			MAX-ACCESS read-only
			STATUS current
			DESCRIPTION
				"This parameter is a count of FEC anomalies (the number of corrected code words) occurring in the
				bearer channel during the accumulation period."
			REFERENCE
				"g.997.1 chapter 7.2.2.1.2/7.2.2.2.2"
			::= { sheXdslChanIntervalEntry 4 }

		
		sheXdslChanIntervalCodingViolationCount OBJECT-TYPE
			SYNTAX HCPerfIntervalCount
			MAX-ACCESS read-only
			STATUS current
			DESCRIPTION
				"That CV-P performance parameter is a count of the number of occurrences of a cv-n anomaly in the
				PTM Data Path."
			REFERENCE
				"g.997.1 chapter 7.2.5.1.2/7.2.5.2.2"
			::= { sheXdslChanIntervalEntry 5 }

		
		sheXdslChanIntervalCrcCount OBJECT-TYPE
			SYNTAX HCPerfCurrentCount
			MAX-ACCESS read-only
			STATUS current
			DESCRIPTION
				"The CRC-P performance parameter is a count of the number of occurrences of a CRC-n anomaly in
				the PTM Data Path."
			REFERENCE
				"g.997.1 chapter 7.2.5.1.1/7.2.5.2.1"
			::= { sheXdslChanIntervalEntry 6 }

		
		sheXdslChanIntervalHecCount OBJECT-TYPE
			SYNTAX HCPerfCurrentCount
			MAX-ACCESS read-only
			STATUS current
			DESCRIPTION
				"The HEC_violation_count performance parameter is a count of the number of occurrences
				of a HEC anomaly in the ATM Data Path."
			REFERENCE
				"g.997.1 chapter 7.2.4.1.1/7.2.4.2.1"
			::= { sheXdslChanIntervalEntry 7 }

		
		sheXdslChanIntervalDelineatedTotalCellCount OBJECT-TYPE
			SYNTAX HCPerfCurrentCount
			MAX-ACCESS read-only
			STATUS current
			DESCRIPTION
				"The delineated_total_cell_count performance parameter is a count of the total number of
				cells passed through the cell delineation process and HEC function operating on the ATM Data Path
				while in the SYNC state."
			REFERENCE
				"g.997.1 chapter 7.2.4.1.2/7.2.4.2.2"
			::= { sheXdslChanIntervalEntry 8 }

		
		sheXdslChanIntervalUserTotalCellCount OBJECT-TYPE
			SYNTAX HCPerfCurrentCount
			MAX-ACCESS read-only
			STATUS current
			DESCRIPTION
				"The User_total_cell_count performance parameter is a count of the total number of cells in
				the ATM Data Path."
			REFERENCE
				"g.997.1 chapter 7.2.4.1.3/7.2.4.2.3"
			::= { sheXdslChanIntervalEntry 9 }

		
		sheXdslChanIntervalIdleCellBitErrorCount OBJECT-TYPE
			SYNTAX HCPerfCurrentCount
			MAX-ACCESS read-only
			STATUS current
			DESCRIPTION
				"The idle_bit_error_count performance parameter is a count of the number of bit errors in the
				idle cell payload received in the ATM Data Path."
			REFERENCE
				"g.997.1 chapter 7.2.4.1.4/7.2.4.2.4"
			::= { sheXdslChanIntervalEntry 10 }

		
		sheXdslChan1DayIntervalTable OBJECT-TYPE
			SYNTAX SEQUENCE OF SheXdslChan1DayIntervalEntry
			MAX-ACCESS not-accessible
			STATUS current
			DESCRIPTION
				"This table provides one row for each XDSL performance 
				data collection interval. This table contains live data 
				from equipment.  As such, it is NOT persistent."
			::= { sheXdslMibObjects 10 }

		
		sheXdslChan1DayIntervalEntry OBJECT-TYPE
			SYNTAX SheXdslChan1DayIntervalEntry
			MAX-ACCESS not-accessible
			STATUS current
			DESCRIPTION
				"An entry in the xdslChan1DayIntervalTable.
				Indexed by ifIndex - PhysSide - ChanNum - IntervalNumber.
				"
			INDEX { ifIndex, sheXdslPhysSide, sheXdslChanNum, sheXdslChan1DayIntervalNumber }
			::= { sheXdslChan1DayIntervalTable 1 }

		
		SheXdslChan1DayIntervalEntry ::=
			SEQUENCE { 
				sheXdslChan1DayIntervalNumber
					Unsigned32,
				sheXdslChan1DayIntervalMoniSecs
					HCPerfTimeElapsed,
				sheXdslChan1DayIntervalFecCount
					HCPerfCurrentCount,
				sheXdslChan1DayIntervalCodingViolationCount
					HCPerfCurrentCount,
				sheXdslChan1DayIntervalCrcCount
					HCPerfCurrentCount,
				sheXdslChan1DayIntervalHecCount
					HCPerfCurrentCount,
				sheXdslChan1DayIntervalDelineatedTotalCellCount
					HCPerfCurrentCount,
				sheXdslChan1DayIntervalUserTotalCellCount
					HCPerfCurrentCount,
				sheXdslChan1DayIntervalIdleCellBitErrorCount
					HCPerfCurrentCount,
				sheXdslChan1DayIntervalEndTime
					Unsigned32
			 }

		sheXdslChan1DayIntervalNumber OBJECT-TYPE
			SYNTAX Unsigned32 (1..7)
			MAX-ACCESS read-only
			STATUS current
			DESCRIPTION
				"History Data Interval number.  Interval 1 is the most
				recent previous day; interval 7 is 7 days ago.  Intervals
				4 to 7 are optional."
			::= { sheXdslChan1DayIntervalEntry 1 }

		
		sheXdslChan1DayIntervalMoniSecs OBJECT-TYPE
			SYNTAX HCPerfTimeElapsed
			UNITS "seconds"
			MAX-ACCESS read-only
			STATUS current
			DESCRIPTION
				"The amount of time in the 1-day interval over which the
				performance monitoring information is actually counted.
				This value will be the same as the interval duration except
				in a situation where performance monitoring data could not
				be collected for any reason."
			::= { sheXdslChan1DayIntervalEntry 2 }

		
		sheXdslChan1DayIntervalFecCount OBJECT-TYPE
			SYNTAX HCPerfCurrentCount
			MAX-ACCESS read-only
			STATUS current
			DESCRIPTION
				"This parameter is a count of FEC anomalies (the number of corrected code words) occurring in the
				bearer channel during the accumulation period."
			REFERENCE
				"g.997.1 chapter 7.2.2.1.2/7.2.2.2.2"
			::= { sheXdslChan1DayIntervalEntry 3 }

		
		sheXdslChan1DayIntervalCodingViolationCount OBJECT-TYPE
			SYNTAX HCPerfCurrentCount
			MAX-ACCESS read-only
			STATUS current
			DESCRIPTION
				"That CV-P performance parameter is a count of the number of occurrences of a cv-n anomaly in the
				PTM Data Path."
			REFERENCE
				"g.997.1 chapter 7.2.5.1.2/7.2.5.2.2"
			::= { sheXdslChan1DayIntervalEntry 4 }

		
		sheXdslChan1DayIntervalCrcCount OBJECT-TYPE
			SYNTAX HCPerfCurrentCount
			MAX-ACCESS read-only
			STATUS current
			DESCRIPTION
				"The CRC-P performance parameter is a count of the number of occurrences of a CRC-n anomaly in
				the PTM Data Path."
			REFERENCE
				"g.997.1 chapter 7.2.5.1.1/7.2.5.2.1"
			::= { sheXdslChan1DayIntervalEntry 5 }

		
		sheXdslChan1DayIntervalHecCount OBJECT-TYPE
			SYNTAX HCPerfCurrentCount
			MAX-ACCESS read-only
			STATUS current
			DESCRIPTION
				"The HEC_violation_count performance parameter is a count of the number of occurrences
				of a HEC anomaly in the ATM Data Path."
			REFERENCE
				"g.997.1 chapter 7.2.4.1.1/7.2.4.2.1"
			::= { sheXdslChan1DayIntervalEntry 6 }

		
		sheXdslChan1DayIntervalDelineatedTotalCellCount OBJECT-TYPE
			SYNTAX HCPerfCurrentCount
			MAX-ACCESS read-only
			STATUS current
			DESCRIPTION
				"The delineated_total_cell_count performance parameter is a count of the total number of
				cells passed through the cell delineation process and HEC function operating on the ATM Data Path
				while in the SYNC state."
			REFERENCE
				"g.997.1 chapter 7.2.4.1.2/7.2.4.2.2"
			::= { sheXdslChan1DayIntervalEntry 7 }

		
		sheXdslChan1DayIntervalUserTotalCellCount OBJECT-TYPE
			SYNTAX HCPerfCurrentCount
			MAX-ACCESS read-only
			STATUS current
			DESCRIPTION
				"The User_total_cell_count performance parameter is a count of the total number of cells in
				the ATM Data Path."
			REFERENCE
				"g.997.1 chapter 7.2.4.1.3/7.2.4.2.3"
			::= { sheXdslChan1DayIntervalEntry 8 }

		
		sheXdslChan1DayIntervalIdleCellBitErrorCount OBJECT-TYPE
			SYNTAX HCPerfCurrentCount
			MAX-ACCESS read-only
			STATUS current
			DESCRIPTION
				"The idle_bit_error_count performance parameter is a count of the number of bit errors in the
				idle cell payload received in the ATM Data Path."
			REFERENCE
				"g.997.1 chapter 7.2.4.1.4/7.2.4.2.4"
			::= { sheXdslChan1DayIntervalEntry 9 }

		
		sheXdslChan1DayIntervalEndTime OBJECT-TYPE
			SYNTAX Unsigned32
			UNITS "seconds"
			MAX-ACCESS read-only
			STATUS current
			DESCRIPTION
				"This variable indicates the time of storing this interval."
			::= { sheXdslChan1DayIntervalEntry 10 }

		
		sheXdslLineConfProfileTable OBJECT-TYPE
			SYNTAX SEQUENCE OF SheXdslLineConfProfileEntry
			MAX-ACCESS not-accessible
			STATUS current
			DESCRIPTION
				"This table contains information on the XDSL line
				configuration.  One entry in this table reflects a
				profile defined by a manager which can be used to
				configure the XDSL line.
				
				Entries in this table MUST be maintained in a 
				persistent manner."
			::= { sheXdslMibObjects 11 }

		
		sheXdslLineConfProfileEntry OBJECT-TYPE
			SYNTAX SheXdslLineConfProfileEntry
			MAX-ACCESS not-accessible
			STATUS current
			DESCRIPTION
				"Each entry consists of a list of parameters that represents the configuration of a xDSL line.
				Default profiles will always exist and its parameters will be set to
				vendor-specific values, unless otherwise specified in this document.
				
				Dynamic' profiles are implemented.
				There are five different default profiles in the NE, which could not be modified!
				'DEFVAL'  - default profile for interfaces with iftype 'vdsl' (97) for VDSL2 over isdn
				'DEFVAL_VDSL2_P'  - default profile for interfaces with iftype 'vdsl' (97) for VDSL2 over pots
				'DEFVAL_ADSL_A' - default profile for interfaces with iftype 'adsl2' (230) for ADSL2+ over pots (annexA)
				'DEFVAL_ADSL_B' - default profile for interfaces with iftype 'adsl2' (230) for ADSL2+ over isdn (annexB)
				'DEFVAL_ADSL_J' - default profile for interfaces with iftype 'adsl2' (230) for ADSL2+ ADL (annexJ)"
			INDEX { sheXdslLineConfProfileIndex }
			::= { sheXdslLineConfProfileTable 1 }

		
		SheXdslLineConfProfileEntry ::=
			SEQUENCE { 
				sheXdslLineConfProfileIndex
					Unsigned32,
				sheXdslLineConfProfileName
					SnmpAdminString,
				sheXdslLineConfDownRateMode
					SheXdslProfileRateModeType,
				sheXdslLineConfUpRateMode
					SheXdslProfileRateModeType,
				sheXdslLineConfDownMaxPwr
					Unsigned32,
				sheXdslLineConfUpMaxPwr
					Unsigned32,
				sheXdslLineConfMaxUpRxPower
					Integer32,
				sheXdslLineConfDownMaxSnrMgn
					Unsigned32,
				sheXdslLineConfDownMinSnrMgn
					Unsigned32,
				sheXdslLineConfDownTargetSnrMgn
					Unsigned32,
				sheXdslLineConfUpMaxSnrMgn
					Unsigned32,
				sheXdslLineConfUpMinSnrMgn
					Unsigned32,
				sheXdslLineConfUpTargetSnrMgn
					Unsigned32,
				sheXdslLineConfVtucDownshiftSnrMgn
					INTEGER,
				sheXdslLineConfVtucUpshiftSnrMgn
					INTEGER,
				sheXdslLineConfVtucMinDownshiftTime
					INTEGER,
				sheXdslLineConfVtucMinUpshiftTime
					INTEGER,
				sheXdslLineConfVturDownshiftSnrMgn
					INTEGER,
				sheXdslLineConfVturUpshiftSnrMgn
					INTEGER,
				sheXdslLineConfVturMinDownshiftTime
					INTEGER,
				sheXdslLineConfVturMinUpshiftTime
					INTEGER,
				sheXdslLineConfUseVdsl2BandPlanNumber
					SheVdsl2BandPlanType,
				sheXdslLineConfUseVdsl2ProfileNumber
					SheVdsl2ProfileType,
				sheXdslLineConfGsStandard
					SheXdslLineStandardType,
				sheXdslLineConfForceINPDs
					TruthValue,
				sheXdslLineConfForceINPUs
					TruthValue,
				sheXdslLineConfChan1ConfProfile
					SnmpAdminString,
				sheXdslLineConfChan1RaRatioDs
					Unsigned32,
				sheXdslLineConfChan1RaRatioUs
					Unsigned32,
				sheXdslLineConfChan2ConfProfile
					SnmpAdminString
			 }

		sheXdslLineConfProfileIndex OBJECT-TYPE
			SYNTAX Unsigned32 (1..300)
			MAX-ACCESS read-only
			STATUS current
			DESCRIPTION
				"Index of this table."
			::= { sheXdslLineConfProfileEntry 1 }

		
		sheXdslLineConfProfileName OBJECT-TYPE
			SYNTAX SnmpAdminString (SIZE (1..32))
			MAX-ACCESS read-only
			STATUS current
			DESCRIPTION
				"This object identifies a row in this table.  
				
				Dynamic' profiles are implemented.The profile name is user specified.
				There are five different default profiles in the NE, which could not be modified!
				'DEFVAL'  - default profile for interfaces with iftype 'vdsl' (97) for VDSL2 over isdn
				'DEFVAL_VDSL2_P'  - default profile for interfaces with iftype 'vdsl' (97) for VDSL2 over pots
				'DEFVAL_ADSL_A' - default profile for interfaces with iftype 'adsl2' (230) for ADSL2+ over pots (annexA)
				'DEFVAL_ADSL_B' - default profile for interfaces with iftype 'adsl2' (230) for ADSL2+ over isdn (annexB)
				'DEFVAL_ADSL_J' - default profile for interfaces with iftype 'adsl2' (230) for ADSL2+ ADL (annexJ)
				
				This characters are not allowed:  space : ?"
			::= { sheXdslLineConfProfileEntry 2 }

		
		sheXdslLineConfDownRateMode OBJECT-TYPE
			SYNTAX SheXdslProfileRateModeType
			MAX-ACCESS read-only
			STATUS current
			DESCRIPTION
				"Specifies the rate selection behavior for the line
				in the downstream direction.
				
				fixed(1)          forces the rate to the configured minimum rate
				adaptAtInit(2)    adapts the line based upon line quality.
				adaptAtRuntime(3) seamless rateadapts during runtime based upon line quality
				
				Please note the following rule for margin configuration in case of usage mode (3):
				
				sheXdslLineConfDownMinSnrMgn < sheXdslLineConfVturDownshiftSnrMgn < 
				sheXdslLineConfDownTargetSnrMgn < sheXdslLineConfVturUpshiftSnrMgn < 
				sheXdslLineConfDownMaxSnrMgn
				
				
				"
			REFERENCE
				"g.997.1 chapter 7.3.1.4.1"
			DEFVAL { 2 }
			::= { sheXdslLineConfProfileEntry 3 }

		
		sheXdslLineConfUpRateMode OBJECT-TYPE
			SYNTAX SheXdslProfileRateModeType
			MAX-ACCESS read-only
			STATUS current
			DESCRIPTION
				"Specifies the rate selection behavior for the line
				in the upstream direction.
				
				fixed(1)          forces the rate to the configured minimum rate
				adaptAtInit(2)    adapts the line based upon line quality.
				adaptAtRuntime(3) seamless rateadapts during runtime based upon line quality
				
				Please note the following rule for margin configuration in case of usage mode (3):
				
				sheXdslLineConfUpMinSnrMgn < sheXdslLineConfVtucDownshiftSnrMgn < 
				sheXdslLineConfUpTargetSnrMgn < sheXdslLineConfVtucUpshiftSnrMgn < 
				sheXdslLineConfUpMaxSnrMgn"
			REFERENCE
				"g.997.1 chapter 7.3.1.4.2"
			DEFVAL { 2 }
			::= { sheXdslLineConfProfileEntry 4 }

		
		sheXdslLineConfDownMaxPwr OBJECT-TYPE
			SYNTAX Unsigned32 (0..255)
			UNITS "0.1dBm"
			MAX-ACCESS read-only
			STATUS current
			DESCRIPTION
				"Specifies the maximum aggregate downstream power
				level in the range 0 to 25.5 dBm."
			REFERENCE
				"g.997.1 chapter 7.3.1.2.3"
			DEFVAL { 0 }
			::= { sheXdslLineConfProfileEntry 5 }

		
		sheXdslLineConfUpMaxPwr OBJECT-TYPE
			SYNTAX Unsigned32 (0..255)
			UNITS "0.1dBm"
			MAX-ACCESS read-only
			STATUS current
			DESCRIPTION
				"Specifies the maximum aggregate upstream power
				level in the range 0 to 25.5 dBm."
			REFERENCE
				"g.997.1 chapter 7.3.1.2.4"
			DEFVAL { 0 }
			::= { sheXdslLineConfProfileEntry 6 }

		
		sheXdslLineConfMaxUpRxPower OBJECT-TYPE
			SYNTAX Integer32 (-255..255)
			UNITS "0.1dBm"
			MAX-ACCESS read-only
			STATUS current
			DESCRIPTION
				"Maximum received upstream power. The XTU-C will force the XTU-R to reduce transmitted power,
				if this value will be exceed."
			REFERENCE
				"g.997.1 chapter 7.3.1.2.5"
			DEFVAL { 255 }
			::= { sheXdslLineConfProfileEntry 7 }

		
		sheXdslLineConfDownMaxSnrMgn OBJECT-TYPE
			SYNTAX Unsigned32 (0..310 | 65535)
			UNITS "0.1dB"
			MAX-ACCESS read-only
			STATUS current
			DESCRIPTION
				"Specifies the maximum downstream Signal/Noise Margin
				in units of 0.1 dB, for a range of 0 to 31 dB.
				Rule: 
				MaxSnr > TargetSnr > MinSnr
				
				A special value of 0xFFFF is used to indicate that no
				Maximum Noise Margin limit is to be applied (i.e., the maximum value is infinite)."
			REFERENCE
				"g.997.1 chapter 7.3.1.3.3"
			DEFVAL { 310 }
			::= { sheXdslLineConfProfileEntry 8 }

		
		sheXdslLineConfDownMinSnrMgn OBJECT-TYPE
			SYNTAX Unsigned32 (0..310)
			UNITS "0.1dB"
			MAX-ACCESS read-only
			STATUS current
			DESCRIPTION
				"Specifies the minimum downstream Signal/Noise Margin
				in units of 0.1dB, for a range of 0 to 31 dB.
				Rule: 
				MaxSnr > TargetSnr > MinSnr
				"
			REFERENCE
				"g.997.1 chapter 7.3.1.3.5"
			DEFVAL { 0 }
			::= { sheXdslLineConfProfileEntry 9 }

		
		sheXdslLineConfDownTargetSnrMgn OBJECT-TYPE
			SYNTAX Unsigned32 (0..310)
			UNITS "0.1dB"
			MAX-ACCESS read-only
			STATUS current
			DESCRIPTION
				"Specifies the target downstream Signal/Noise Margin
				in units of 0.1 dB, for a range of 0 to 31 dB.
				This is the Noise Margin the transceivers must achieve 
				with a BER of sheXdslChannelProfileMaxBerDs or better to successfully complete 
				initialization.
				Rule: 
				MaxSnr > TargetSnr > MinSnr
				"
			REFERENCE
				"g.997.1 chapter 7.3.1.3.1"
			DEFVAL { 65 }
			::= { sheXdslLineConfProfileEntry 10 }

		
		sheXdslLineConfUpMaxSnrMgn OBJECT-TYPE
			SYNTAX Unsigned32 (0..310 | 65535)
			UNITS "0.1dB"
			MAX-ACCESS read-only
			STATUS current
			DESCRIPTION
				"Specifies the maximum upstream Signal/Noise Margin
				in units of 0.1 dB, for a range of 0 to 31 dB.
				Rule: 
				MaxSnr > TargetSnr > MinSnr
				
				A special value of 0xFFFF is used to indicate that no
				Maximum Noise Margin limit is to be applied (i.e., the maximum value is infinite)."
			REFERENCE
				"g.997.1 chapter 7.3.1.3.4"
			DEFVAL { 310 }
			::= { sheXdslLineConfProfileEntry 11 }

		
		sheXdslLineConfUpMinSnrMgn OBJECT-TYPE
			SYNTAX Unsigned32 (0..310)
			UNITS "0.1dB"
			MAX-ACCESS read-only
			STATUS current
			DESCRIPTION
				"Specifies the minimum upstream Signal/Noise Margin
				in units of 0.1 dB, for a range of 0 to 31 dB.
				Rule: 
				MaxSnr > TargetSnr > MinSnr
				"
			REFERENCE
				"g.997.1 chapter 7.3.1.3.6"
			DEFVAL { 0 }
			::= { sheXdslLineConfProfileEntry 12 }

		
		sheXdslLineConfUpTargetSnrMgn OBJECT-TYPE
			SYNTAX Unsigned32 (0..310)
			UNITS "0.1dB"
			MAX-ACCESS read-only
			STATUS current
			DESCRIPTION
				"Specifies the target upstream Signal/Noise Margin in 
				units of 0.1 dB, for a range of 0 to 31 dB.  This 
				is the Noise Margin the transceivers must achieve with 
				a BER of sheXdslChannelProfileMaxBerUs or better to successfully complete 
				initialization.
				Rule: 
				MaxSnr > TargetSnr > MinSnr
				"
			REFERENCE
				"g.997.1 chapter 7.3.1.3.2"
			DEFVAL { 65 }
			::= { sheXdslLineConfProfileEntry 13 }

		
		sheXdslLineConfVtucDownshiftSnrMgn OBJECT-TYPE
			SYNTAX INTEGER (0..310)
			UNITS "0.1dB"
			MAX-ACCESS read-only
			STATUS current
			DESCRIPTION
				"Configured Signal/Noise Margin for rate downshift.
				If the  upstream noise margin falls below this level, the modem
				should attempt to decrease its transmit rate."
			REFERENCE
				"g.997.1 chapter 7.3.1.4.8"
			DEFVAL { 0 }
			::= { sheXdslLineConfProfileEntry 26 }

		
		sheXdslLineConfVtucUpshiftSnrMgn OBJECT-TYPE
			SYNTAX INTEGER (0..310)
			UNITS "0.1dB"
			MAX-ACCESS read-only
			STATUS current
			DESCRIPTION
				"Configured Signal/Noise Margin for rate upshift.
				If the upstream noise margin rises above this level, the modem
				should attempt to increase its transmit rate."
			REFERENCE
				"g.997.1 chapter 7.3.1.4.4"
			DEFVAL { 0 }
			::= { sheXdslLineConfProfileEntry 27 }

		
		sheXdslLineConfVtucMinDownshiftTime OBJECT-TYPE
			SYNTAX INTEGER (0..16383)
			UNITS "seconds"
			MAX-ACCESS read-only
			STATUS current
			DESCRIPTION
				"Minimum time that the current upstream margin is below DownshiftSnrMgn before a downshift occurs.
				"
			REFERENCE
				"g.997.1 chapter 7.3.1.4.10"
			DEFVAL { 0 }
			::= { sheXdslLineConfProfileEntry 28 }

		
		sheXdslLineConfVtucMinUpshiftTime OBJECT-TYPE
			SYNTAX INTEGER (0..16383)
			UNITS "seconds"
			MAX-ACCESS read-only
			STATUS current
			DESCRIPTION
				"Minimum time that the current upstream margin is above UpshiftSnrMgn before an upshift occurs.
				"
			REFERENCE
				"g.997.1 chapter 7.3.1.4.6"
			DEFVAL { 0 }
			::= { sheXdslLineConfProfileEntry 29 }

		
		sheXdslLineConfVturDownshiftSnrMgn OBJECT-TYPE
			SYNTAX INTEGER (0..310)
			UNITS "0.1dB"
			MAX-ACCESS read-only
			STATUS current
			DESCRIPTION
				"Configured Signal/Noise Margin for rate downshift.
				If the downstream noise margin falls below this level, the modem
				should attempt to decrease its transmit rate."
			REFERENCE
				"g.997.1 chapter 7.3.1.4.7"
			DEFVAL { 0 }
			::= { sheXdslLineConfProfileEntry 30 }

		
		sheXdslLineConfVturUpshiftSnrMgn OBJECT-TYPE
			SYNTAX INTEGER (0..310)
			UNITS "0.1dB"
			MAX-ACCESS read-only
			STATUS current
			DESCRIPTION
				"Configured Signal/Noise Margin for rate upshift.
				If the downstream noise margin rises above this level, the modem
				should attempt to increase its transmit rate."
			REFERENCE
				"g.997.1 chapter 7.3.1.4.3"
			DEFVAL { 0 }
			::= { sheXdslLineConfProfileEntry 31 }

		
		sheXdslLineConfVturMinDownshiftTime OBJECT-TYPE
			SYNTAX INTEGER (0..16383)
			UNITS "seconds"
			MAX-ACCESS read-only
			STATUS current
			DESCRIPTION
				"Minimum time that the current downstream margin is below DownshiftSnrMgn before a downshift occurs.
				"
			REFERENCE
				"g.997.1 chapter 7.3.1.4.9"
			DEFVAL { 0 }
			::= { sheXdslLineConfProfileEntry 32 }

		
		sheXdslLineConfVturMinUpshiftTime OBJECT-TYPE
			SYNTAX INTEGER (0..16383)
			UNITS "seconds"
			MAX-ACCESS read-only
			STATUS current
			DESCRIPTION
				"Minimum time that the current downstream margin is above UpshiftSnrMgn before an upshift occurs.
				"
			REFERENCE
				"g.997.1 chapter 7.3.1.4.5"
			DEFVAL { 0 }
			::= { sheXdslLineConfProfileEntry 33 }

		
		sheXdslLineConfUseVdsl2BandPlanNumber OBJECT-TYPE
			SYNTAX SheVdsl2BandPlanType
			MAX-ACCESS read-only
			STATUS current
			DESCRIPTION
				"Band plan notation according to G993.2.
				valid values:
				 bandPlanItuAnnexAM1EU32(0),
				 bandPlanItuAnnexAM9EU64(1),
				 bandPlanItuAnnexAM1ADLU32(2),
				 bandPlanItuAnnexAM9ADLU64(3),
				 bandPlan997M1cA7(4),
				 bandPlan997M1xM8(5),
				 bandPlan997M1xM(6),
				 bandPlan997M2xM8(7),
				 bandPlan997M2xA(8),
				 bandPlan997M2xM(9),
				 bandPlan998M1xA(10),
				 bandPlan998M1xB(11),
				 bandPlan998M1xNUS0(12),
				 bandPlan998M2xA(13),
				 bandPlan998M2xM(14),
				 bandPlan998M2xM17(15),
				 bandPlan998M2xB(16),
				 bandPlan998M2xB17(17),
				 bandPlan998M2xNUS0(18),
				 bandPlan998M2xNUS017(19),
				 bandPlan997E30M2xNUS0(22),
				 bandPlan998E17M2xA(25),
				 bandPlan998E17M2xNUS0(26),
				 bandPlanAnfpCal0Long(27),
				 bandPlanAnfpCal0Medium(28),
				 bandPlanAnfpCal0Short(29),
				 bandPlanAnfpCal0EShort(30),
				 bandPlanItuAnnexAM10EU128(40),
				 bandPlanAnnexAM1Eu32(50),
				 bandPlanAnnexAM2Eu36(51),
				 bandPlanAnnexAM3Eu40(52),
				 bandPlanAnnexAM4Eu44(53),
				 bandPlanAnnexAM5Eu48(54),
				 bandPlanAnnexAM6Eu52(55),
				 bandPlanAnnexAM7Eu56(56),
				 bandPlanAnnexAM8Eu60(57),
				 bandPlanAnnexAM9Eu64(58),
				 bandPlanAnnexAEu128(59),
				 bandPlanAnnexAM1Adlu32(70),
				 bandPlanAnnexAM2Adlu36(71),
				 bandPlanAnnexAM3Adlu40(72),
				 bandPlanAnnexAM4Adlu44(73),
				 bandPlanAnnexAM5Adlu48(74),
				 bandPlanAnnexAM6Adlu52(75),
				 bandPlanAnnexAM7Adlu56(76),
				 bandPlanAnnexAM8Adlu60(77),
				 bandPlanAnnexAM9Adlu64(78),
				 bandPlanAnnexAAdlu128(79),
				 bandPlanAnnexB997M1CA7(100),
				 bandPlanAnnexB997M1XM8(101),
				 bandPlanAnnexB997M1XM(102),
				 bandPlanAnnexB997M2XM8(103),
				 bandPlanAnnexB997M2XA(104),
				 bandPlanAnnexB997M2XM(105),
				 bandPlanAnnexB997HPE17M1NUS0(106),
				 bandPlanAnnexB997HPE30M1NUS0(107),
				 bandPlanAnnexB997E17M2XA(108)        -> replace bandPlanAnnexB997E17M2XNUS0 with R2.8 MIB 327
				                                         because of G993.2 standard update
				 bandPlanAnnexB997E30M2XNUS0(109),
				 bandPlanAnnexB998M1XA(120),
				 bandPlanAnnexB998M1XB(121),
				 bandPlanAnnexB998M1XNUS0(122),
				 bandPlanAnnexB998M2XA(123),
				 bandPlanAnnexB998M2XM(124),
				 bandPlanAnnexB998M2XB(125),
				 bandPlanAnnexB998M2XNUS0(126),
				 bandPlanAnnexB998E17M2XNUS0(127),
				 bandPlanAnnexB998E17M2XNUS0M(128),
				 bandPlanAnnexB998ADE17M2XNUS0M(129),
				 bandPlanAnnexB998ADE17M2XA(130),
				 bandPlanAnnexB998ADE17M2XB(131),
				 bandPlanAnnexB998E30M2XNUS0(132),
				 bandPlanAnnexB998E30M2XNUS0M(133),
				 bandPlanAnnexB998ADE30M2XNUS0M(134),
				 bandPlanAnnexB998ADE30M2XNUS0A(135),
				 bandPlanAnnexB998ADE17M2XM(140),
				 bandPlanAnnexB998E17M2XA(141)
				
				Relevant only for Vdsl2 mode.
				REMARK:
				Check MSC documentation for valid band plan and profile combinations!!
				The bandplan numbers below 50 should not longer be used!"
			DEFVAL { bandPlan998M2xB }
			::= { sheXdslLineConfProfileEntry 35 }

		
		sheXdslLineConfUseVdsl2ProfileNumber OBJECT-TYPE
			SYNTAX SheVdsl2ProfileType
			MAX-ACCESS read-only
			STATUS current
			DESCRIPTION
				"This attribute selects the Vdsl2 profile which should be used for configuration of basic parameters.
				Profile settings are defined in g993.2.
				
				Values to use:
						dslProfile8A(0),
						dslProfile8B(1),
						dslProfile8C(2),
						dslProfile8D(3),
						dslProfile12A(4),
						dslProfile12B(5),
						dslProfile17A(6),
						dslProfile30A(7),
						dslProfile17B(8),
				
				Relevant only for Vdsl2 mode. 
				Be aware, that dslProfile30A use a different subcarrier spacing of 8.625 kHz!
				REMARK:
				Check MSC documentation for valid band plan and profile combinations!!"
			REFERENCE
				"g993.2 chapter 6"
			DEFVAL { dslProfile17A }
			::= { sheXdslLineConfProfileEntry 36 }

		
		sheXdslLineConfGsStandard OBJECT-TYPE
			SYNTAX SheXdslLineStandardType
			MAX-ACCESS read-only
			STATUS current
			DESCRIPTION
				"preferred used standard compliance. see g.997.1 clause 7.3.1.1.1 (ATSE).
				The following bits could be set:
					ansiT1413(0),
					g9921AdslPotsNonOverlapped(2),
					g9921AdslIsdnNonOverlapped(4),
					g9923Adsl2PotsNonOverlapped(18),
					g9923Adsl2IsdnNonOverlapped(20),
					g9923ADMAdsl2NonOverlappedAnnexJ(30),
					g9923ReachExtAdsl2PotsNonOverlappedM1(34),
					g9923ReachExtAdsl2PotsNonOverlappedM2(35),
					g9923ExtUpAdsl2PotsNonOverlapped(38),
					g9925Adsl2PlusPotsNonOverlapped(40),
					g9925Adsl2PlusIsdnNonOverlapped(42),
					g9925ADMAdsl2PlusNonOverlappedAnnexJ(48),
					g9925ExtUpAdsl2PlusPotsNonOverlapped(50),
					g9932Vdsl2NonOverlappedRegionA(56)
					g9932Vdsl2NonOverlappedRegionB(57),
					
				Customer can select a single mode or enable all possible standards and the system 
				will select the mode depending on the detected remote side.
				At minimum, one bit has always to be set! Currently a mix of enabled VDSL and ADSL
				standards will be rejected by the NE. Same will be occure for a mix of ADSL pots and
				isdn standards.
				
				A configuration of this parameter, which causes a Standard change (ADSL->VDSL or back)
				could only made for NOT USED profiles!"
			DEFVAL { { g9932Vdsl2NonOverlappedRegionB } }
			::= { sheXdslLineConfProfileEntry 38 }

		
		sheXdslLineConfForceINPDs OBJECT-TYPE
			SYNTAX TruthValue
			MAX-ACCESS read-only
			STATUS obsolete
			DESCRIPTION
				"This parameter indicates that the framer settings of the bearer shall be selected such that the impulse
				noise protection computed according to the formula specified in the relevant Recommendation is
				greater than or equal to the minimal impulse noise protection requirement.
				
				This flag shall have the same value for all the bearers of one line in the same direction.
				This parameter specifies the value for downstream direction.
				
				Remark: Moved to sheXdslLineTable with SHE R2.6 and not longer supported via line profile!!"
			REFERENCE
				"ITU-T G.997.1, chapter 7.3.2.5"
			DEFVAL { false }
			::= { sheXdslLineConfProfileEntry 41 }

		
		sheXdslLineConfForceINPUs OBJECT-TYPE
			SYNTAX TruthValue
			MAX-ACCESS read-only
			STATUS obsolete
			DESCRIPTION
				"This parameter indicates that the framer settings of the bearer shall be selected such that the impulse
				noise protection computed according to the formula specified in the relevant Recommendation is
				greater than or equal to the minimal impulse noise protection requirement.
				
				This flag shall have the same value for all the bearers of one line in the same direction.
				This parameter specifies the value for upstream direction.
				
				Remark: Moved to sheXdslLineTable with SHE R2.6 and not longer supported via line profile!!"
			REFERENCE
				"ITU-T G.997.1, chapter 7.3.2.5"
			DEFVAL { false }
			::= { sheXdslLineConfProfileEntry 42 }

		
		sheXdslLineConfChan1ConfProfile OBJECT-TYPE
			SYNTAX SnmpAdminString (SIZE (1..32))
			MAX-ACCESS read-only
			STATUS obsolete
			DESCRIPTION
				"The value of this object identifies the row in the XDSL channel configuration
				Profile Table,(sheXdslChannelProfileTable) that applies to DSL bearer
				channel #1. The channel profile name specified here must
				match the name of an existing row in the
				sheXdslChannelProfileTable table.
				
				Remark: Moved to sheXdslLineTable with SHE R2.6 and not longer supported via line profile!!"
			DEFVAL { "DEFVAL" }
			::= { sheXdslLineConfProfileEntry 43 }

		
		sheXdslLineConfChan1RaRatioDs OBJECT-TYPE
			SYNTAX Unsigned32 (0..100)
			UNITS "percents"
			MAX-ACCESS read-only
			STATUS obsolete
			DESCRIPTION
				"Rate Adaptation Ratio. The ratio (in %) that should be taken
				into account for the bearer channel #1 when performing rate
				adaptation on Downstream. The ratio refers to the available
				data rate in excess of the Minimum Data Rate, summed over all
				bearer channels. Also, the 100 - sheXdslLineConfChan1RaRatioDs
				is the ratio of excess data rate to be assigned to all other bearer
				channels on Downstream direction. The sum of rate adaptation ratios
				over all bearers on the same direction shall be equal to 100%.
				
				Remark: Moved to sheXdslLineTable with SHE R2.6 and not longer supported via line profile!!"
			REFERENCE
				"ITU-T G.997.1, paragraph 7.3.2.1"
			DEFVAL { 100 }
			::= { sheXdslLineConfProfileEntry 44 }

		
		sheXdslLineConfChan1RaRatioUs OBJECT-TYPE
			SYNTAX Unsigned32 (0..100)
			UNITS "percents"
			MAX-ACCESS read-only
			STATUS obsolete
			DESCRIPTION
				"Rate Adaptation Ratio. The ratio (in %) that should be taken
				into account for the bearer channel #1 when performing rate
				adaptation on Upstream. The ratio refers to the available
				data rate in excess of the Minimum Data Rate, summed over all
				bearer channels. Also, the 100 - sheXdslLineConfChan1RaRatioUs
				is the ratio of excess data rate to be assigned to all other
				bearer channels on Upstream direction. The sum of rate adaptation
				ratios over all bearers on the same direction shall be equal to 100 %.
				
				Remark: Moved to sheXdslLineTable with SHE R2.6 and not longer supported via line profile!!"
			REFERENCE
				"ITU-T G.997.1, paragraph 7.3.2.1"
			DEFVAL { 100 }
			::= { sheXdslLineConfProfileEntry 45 }

		
		sheXdslLineConfChan2ConfProfile OBJECT-TYPE
			SYNTAX SnmpAdminString (SIZE (0..32))
			MAX-ACCESS read-only
			STATUS obsolete
			DESCRIPTION
				"The value of this object identifies the row in the XDSL channel configuration
				Profile Table, (sheXdslChannelProfileTable) that applies to DSL bearer
				channel #2. If the channel is unused, then the object is set
				to a zero length string.
				
				The modification of this parameter which causes a switchover between
				single and dualLatency is only possible for lineProfiles which are 
				not in use!!
				
				Remark: Moved to sheXdslLineTable with SHE R2.6 and not longer supported via line profile!!"
			DEFVAL { "" }
			::= { sheXdslLineConfProfileEntry 46 }

		
		sheXdslLineConfProfileControl OBJECT IDENTIFIER ::= { sheXdslMibObjects 12 }

		
		sheXdslLineConfProfileControlRequest OBJECT-TYPE
			SYNTAX SheXdslControlRequestType
			MAX-ACCESS read-write
			STATUS current
			DESCRIPTION
				"createXdslLineConfProfile            
				sheXdslLineConfProfileControlName
				...
				
				modifyXdslLineConfProfile
				(A modification of sheXdslLineConfProfileControlUseVdsl2ProfileNumber, in a way that
				it causes a new subcarrier spacing is not allowed for profiles, which are assigned
				to a xdsl line!)
				sheXdslLineConfProfileControlIndex
				sheXdslLineConfProfileControlName
				...
				
				deleteXdslLineConfProfile
				sheXdslLineConfProfileControlIndex
				sheXdslLineConfProfileControlName
				
				"
			::= { sheXdslLineConfProfileControl 1 }

		
		sheXdslLineConfProfileControlIndex OBJECT-TYPE
			SYNTAX Unsigned32 (1..300)
			MAX-ACCESS read-write
			STATUS current
			DESCRIPTION
				"Index of the configured xdsl line profile."
			::= { sheXdslLineConfProfileControl 2 }

		
		sheXdslLineConfProfileControlStatus OBJECT-TYPE
			SYNTAX SheControlStatusType
			MAX-ACCESS read-only
			STATUS current
			DESCRIPTION
				"The status of a user command. 
				"
			::= { sheXdslLineConfProfileControl 3 }

		
		sheXdslLineConfProfileControlTimer OBJECT-TYPE
			SYNTAX Gauge32
			MAX-ACCESS read-only
			STATUS current
			DESCRIPTION
				"The maximum wait time for the manager for a long running user command. 
				"
			::= { sheXdslLineConfProfileControl 4 }

		
		sheXdslLineConfProfileControlReqResult OBJECT-TYPE
			SYNTAX SheXdslControlRequestResultType
			MAX-ACCESS read-only
			STATUS current
			DESCRIPTION
				"The result of the last user command."
			::= { sheXdslLineConfProfileControl 5 }

		
		sheXdslLineConfProfileControlTimeStamp OBJECT-TYPE
			SYNTAX Unsigned32
			UNITS "sec"
			MAX-ACCESS read-only
			STATUS current
			DESCRIPTION
				"The time stamp of the last command (end of command)."
			::= { sheXdslLineConfProfileControl 6 }

		
		sheXdslLineConfProfileControlName OBJECT-TYPE
			SYNTAX SnmpAdminString (SIZE (1..32))
			MAX-ACCESS read-write
			STATUS current
			DESCRIPTION
				"look at table"
			::= { sheXdslLineConfProfileControl 7 }

		
		sheXdslLineConfProfileControlDownRateMode OBJECT-TYPE
			SYNTAX SheXdslProfileRateModeType
			MAX-ACCESS read-write
			STATUS current
			DESCRIPTION
				"Look at table."
			::= { sheXdslLineConfProfileControl 8 }

		
		sheXdslLineConfProfileControlUpRateMode OBJECT-TYPE
			SYNTAX SheXdslProfileRateModeType
			MAX-ACCESS read-write
			STATUS current
			DESCRIPTION
				"Look at table."
			::= { sheXdslLineConfProfileControl 9 }

		
		sheXdslLineConfProfileControlDownMaxPwr OBJECT-TYPE
			SYNTAX Unsigned32 (0..255)
			UNITS "0.1dBm"
			MAX-ACCESS read-write
			STATUS current
			DESCRIPTION
				"Look at table."
			::= { sheXdslLineConfProfileControl 10 }

		
		sheXdslLineConfProfileControlUpMaxPwr OBJECT-TYPE
			SYNTAX Unsigned32 (0..255)
			UNITS "0.1dBm"
			MAX-ACCESS read-write
			STATUS current
			DESCRIPTION
				"Look at table."
			::= { sheXdslLineConfProfileControl 11 }

		
		sheXdslLineConfProfileControlMaxUpRxPower OBJECT-TYPE
			SYNTAX Integer32 (-255..255)
			UNITS "0.1dBm"
			MAX-ACCESS read-write
			STATUS current
			DESCRIPTION
				"look at table."
			::= { sheXdslLineConfProfileControl 12 }

		
		sheXdslLineConfProfileControlDownMaxSnrMgn OBJECT-TYPE
			SYNTAX Unsigned32 (0..310 | 65535)
			UNITS "0.1dB"
			MAX-ACCESS read-write
			STATUS current
			DESCRIPTION
				"Look at table.
				Max > Target > Min value!"
			::= { sheXdslLineConfProfileControl 13 }

		
		sheXdslLineConfProfileControlDownMinSnrMgn OBJECT-TYPE
			SYNTAX Unsigned32 (0..310)
			UNITS "0.1dB"
			MAX-ACCESS read-write
			STATUS current
			DESCRIPTION
				"Look at table.
				Max > Target > Min value!"
			::= { sheXdslLineConfProfileControl 14 }

		
		sheXdslLineConfProfileControlDownTargetSnrMgn OBJECT-TYPE
			SYNTAX Unsigned32 (0..310)
			UNITS "0.1dB"
			MAX-ACCESS read-write
			STATUS current
			DESCRIPTION
				"Look at table.
				Max > Target > Min value!"
			::= { sheXdslLineConfProfileControl 15 }

		
		sheXdslLineConfProfileControlUpMaxSnrMgn OBJECT-TYPE
			SYNTAX Unsigned32 (0..310 | 65535)
			UNITS "0.1dB"
			MAX-ACCESS read-write
			STATUS current
			DESCRIPTION
				"Look at table.
				Max > Target > Min value!"
			::= { sheXdslLineConfProfileControl 16 }

		
		sheXdslLineConfProfileControlUpMinSnrMgn OBJECT-TYPE
			SYNTAX Unsigned32 (0..310)
			UNITS "0.dB"
			MAX-ACCESS read-write
			STATUS current
			DESCRIPTION
				"Look at table.
				Max > Target > Min value!"
			::= { sheXdslLineConfProfileControl 17 }

		
		sheXdslLineConfProfileControlUpTargetSnrMgn OBJECT-TYPE
			SYNTAX Unsigned32 (0..310)
			UNITS "0.1dB"
			MAX-ACCESS read-write
			STATUS current
			DESCRIPTION
				"Look at table.
				Max > Target > Min value!"
			::= { sheXdslLineConfProfileControl 18 }

		
		sheXdslLineConfProfileControlVtucDownshiftSnrMgn OBJECT-TYPE
			SYNTAX INTEGER (0..310)
			UNITS "0.1dB"
			MAX-ACCESS read-write
			STATUS current
			DESCRIPTION
				"Configured Signal/Noise Margin for rate downshift.
				If the noise margin falls below this level, the modem
				should attempt to decrease its transmit rate."
			::= { sheXdslLineConfProfileControl 31 }

		
		sheXdslLineConfProfileControlVtucUpshiftSnrMgn OBJECT-TYPE
			SYNTAX INTEGER (0..310)
			UNITS "0.1dB"
			MAX-ACCESS read-write
			STATUS current
			DESCRIPTION
				"Configured Signal/Noise Margin for rate upshift.
				If the noise margin rises above this level, the modem
				should attempt to increase its transmit rate."
			::= { sheXdslLineConfProfileControl 32 }

		
		sheXdslLineConfProfileControlVtucMinDownshiftTime OBJECT-TYPE
			SYNTAX INTEGER (0..16383)
			UNITS "seconds"
			MAX-ACCESS read-write
			STATUS current
			DESCRIPTION
				"Minimum time that the current margin is below DownshiftSnrMgn before a downshift occurs."
			::= { sheXdslLineConfProfileControl 33 }

		
		sheXdslLineConfProfileControlVtucMinUpshiftTime OBJECT-TYPE
			SYNTAX INTEGER (0..16383)
			UNITS "seconds"
			MAX-ACCESS read-write
			STATUS current
			DESCRIPTION
				"Minimum time that the current margin is above UpshiftSnrMgn before an upshift occurs."
			::= { sheXdslLineConfProfileControl 34 }

		
		sheXdslLineConfProfileControlVturDownshiftSnrMgn OBJECT-TYPE
			SYNTAX INTEGER (0..310)
			UNITS "0.1dB"
			MAX-ACCESS read-write
			STATUS current
			DESCRIPTION
				"Configured Signal/Noise Margin for rate downshift.
				If the noise margin falls below this level, the modem
				should attempt to decrease its transmit rate."
			::= { sheXdslLineConfProfileControl 35 }

		
		sheXdslLineConfProfileControlVturUpshiftSnrMgn OBJECT-TYPE
			SYNTAX INTEGER (0..310)
			UNITS "0.1dB"
			MAX-ACCESS read-write
			STATUS current
			DESCRIPTION
				"Configured Signal/Noise Margin for rate upshift.
				If the noise margin rises above this level, the modem
				should attempt to increase its transmit rate."
			::= { sheXdslLineConfProfileControl 36 }

		
		sheXdslLineConfProfileControlVturMinDownshiftTime OBJECT-TYPE
			SYNTAX INTEGER (0..16383)
			UNITS "seconds"
			MAX-ACCESS read-write
			STATUS current
			DESCRIPTION
				"Minimum time that the current margin is below DownshiftSnrMgn before a downshift occurs."
			::= { sheXdslLineConfProfileControl 37 }

		
		sheXdslLineConfProfileControlVturMinUpshiftTime OBJECT-TYPE
			SYNTAX INTEGER (0..16383)
			UNITS "seconds"
			MAX-ACCESS read-write
			STATUS current
			DESCRIPTION
				"Minimum time that the current margin is above UpshiftSnrMgn before an upshift occurs."
			::= { sheXdslLineConfProfileControl 38 }

		
		sheXdslLineConfProfileControlUseVdsl2BandPlanNumber OBJECT-TYPE
			SYNTAX SheVdsl2BandPlanType
			MAX-ACCESS read-write
			STATUS current
			DESCRIPTION
				"look at table
				Note:
				The bandplan numbers below 50 should not longer be used!"
			::= { sheXdslLineConfProfileControl 40 }

		
		sheXdslLineConfProfileControlUseVdsl2ProfileNumber OBJECT-TYPE
			SYNTAX SheVdsl2ProfileType
			MAX-ACCESS read-write
			STATUS current
			DESCRIPTION
				"A modification of sheXdslLineConfProfileControlUseVdsl2ProfileNumber, in a way that
				it causes a new subcarrier spacing is not allowed for profiles, which are assigned
				to a xdsl line!
				
				Be aware, that dslProfile30A use a different subcarrier spacing of 8.625 kHz!"
			::= { sheXdslLineConfProfileControl 41 }

		
		sheXdslLineConfProfileControlGsStandard OBJECT-TYPE
			SYNTAX SheXdslLineStandardType
			MAX-ACCESS read-write
			STATUS current
			DESCRIPTION
				"look at table."
			::= { sheXdslLineConfProfileControl 43 }

		
		sheXdslLineConfProfileControlForceINPDs OBJECT-TYPE
			SYNTAX TruthValue
			MAX-ACCESS read-write
			STATUS obsolete
			DESCRIPTION
				"look at table
				
				Remark: Moved to sheXdslLineTableControl with SHE R2.6 and not longer 
				supported via line profile!!"
			::= { sheXdslLineConfProfileControl 46 }

		
		sheXdslLineConfProfileControlForceINPUs OBJECT-TYPE
			SYNTAX TruthValue
			MAX-ACCESS read-write
			STATUS obsolete
			DESCRIPTION
				"look at table
				
				Remark: Moved to sheXdslLineTableControl with SHE R2.6 and not longer 
				supported via line profile!!"
			::= { sheXdslLineConfProfileControl 47 }

		
		sheXdslLineConfControlChan1ConfProfile OBJECT-TYPE
			SYNTAX SnmpAdminString (SIZE (1..32))
			MAX-ACCESS read-write
			STATUS obsolete
			DESCRIPTION
				"The channel profile name specified here must match the name of an existing
				row in the sheXdslChannelProfileTable table.
				
				Remark: Moved to sheXdslLineTableControl with SHE R2.6 and not longer 
				supported via line profile!!"
			::= { sheXdslLineConfProfileControl 48 }

		
		sheXdslLineConfControlChan1RaRatioDs OBJECT-TYPE
			SYNTAX Unsigned32 (0..100)
			UNITS "percents"
			MAX-ACCESS read-write
			STATUS obsolete
			DESCRIPTION
				"Look at table.
				
				Remark: Moved to sheXdslLineTableControl with SHE R2.6 and not longer 
				supported via line profile!!"
			::= { sheXdslLineConfProfileControl 49 }

		
		sheXdslLineConfControlChan1RaRatioUs OBJECT-TYPE
			SYNTAX Unsigned32 (0..100)
			UNITS "percents"
			MAX-ACCESS read-write
			STATUS obsolete
			DESCRIPTION
				"Look at table
				
				Remark: Moved to sheXdslLineTableControl with SHE R2.6 and not longer 
				supported via line profile!!"
			::= { sheXdslLineConfProfileControl 50 }

		
		sheXdslLineConfControlChan2ConfProfile OBJECT-TYPE
			SYNTAX SnmpAdminString (SIZE (0..32))
			MAX-ACCESS read-write
			STATUS obsolete
			DESCRIPTION
				"The channel profile name specified here must match the name of an existing
				row in the sheXdslChannelProfileTable table.
				
				Remark: Moved to sheXdslLineTableControl with SHE R2.6 and not longer 
				supported via line profile!!"
			::= { sheXdslLineConfProfileControl 51 }

		
		sheXdslLineAlarmConfProfileTable OBJECT-TYPE
			SYNTAX SEQUENCE OF SheXdslLineAlarmConfProfileEntry
			MAX-ACCESS not-accessible
			STATUS current
			DESCRIPTION
				"This table contains information on the XDSL line alarm
				configuration.  One entry in this table reflects a profile
				defined by a manager which can be used to configure the 
				XDSL line alarm thresholds.
				
				Entries in this table MUST be maintained in a 
				persistent manner."
			::= { sheXdslMibObjects 13 }

		
		sheXdslLineAlarmConfProfileEntry OBJECT-TYPE
			SYNTAX SheXdslLineAlarmConfProfileEntry
			MAX-ACCESS not-accessible
			STATUS current
			DESCRIPTION
				"Each entry consists of a list of parameters that
				represents the configuration of a XDSL line alarm
				profile.  
				
				A default profile with an index of 'DEFVAL', will 
				always exist and its parameters will be set to vendor 
				specific values, unless otherwise specified in this 
				document. The default profile could not be modified!"
			INDEX { sheXdslLineAlarmConfProfileIndex }
			::= { sheXdslLineAlarmConfProfileTable 1 }

		
		SheXdslLineAlarmConfProfileEntry ::=
			SEQUENCE { 
				sheXdslLineAlarmConfProfileIndex
					Unsigned32,
				sheXdslLineAlarmConfProfileName
					SnmpAdminString,
				sheXdslThresh15MinLofs
					HCPerfIntervalThreshold,
				sheXdslThresh15MinLoss
					HCPerfIntervalThreshold,
				sheXdslThresh15MinLprs
					HCPerfIntervalThreshold,
				sheXdslThresh15MinLols
					HCPerfIntervalThreshold,
				sheXdslThresh15MinESs
					HCPerfIntervalThreshold,
				sheXdslThresh15MinSESs
					HCPerfIntervalThreshold,
				sheXdslThresh15MinUASs
					HCPerfIntervalThreshold,
				sheXdslInitFailureNotifyEnable
					TruthValue,
				sheXdslLineAlarmOperationalStateNotifyEnable
					TruthValue,
				sheXdslLineAlarmConfigViolationCheck
					SheXdslConfigViolationCheckType
			 }

		sheXdslLineAlarmConfProfileIndex OBJECT-TYPE
			SYNTAX Unsigned32 (1..300)
			MAX-ACCESS read-only
			STATUS current
			DESCRIPTION
				"Description."
			::= { sheXdslLineAlarmConfProfileEntry 1 }

		
		sheXdslLineAlarmConfProfileName OBJECT-TYPE
			SYNTAX SnmpAdminString (SIZE (1..32))
			MAX-ACCESS read-only
			STATUS current
			DESCRIPTION
				"
				Dynamic' profiles are implemented.The profile
				name is user specified. A default profile with 
				an name of 'DEFVAL', will always exist and its
				parameters will be set to vendor specific values,
				unless otherwise specified in this 
				document.
				
				
				This characters are not allowed:  space : ?"
			::= { sheXdslLineAlarmConfProfileEntry 2 }

		
		sheXdslThresh15MinLofs OBJECT-TYPE
			SYNTAX HCPerfIntervalThreshold
			UNITS "seconds"
			MAX-ACCESS read-only
			STATUS current
			DESCRIPTION
				"This object configures the threshold for the number of
				loss of frame seconds (lofs) within any given 15-minute
				performance data collection interval.  If the value of 
				loss of frame seconds in a particular 15-minute collection
				interval reaches/exceeds this value, a 
				xdslPerfLofsThreshNotification notification will be 
				generated.
				This configuration is set for xtuc and xtur side.
				Value 0 should be interpreted as disabled."
			DEFVAL { 0 }
			::= { sheXdslLineAlarmConfProfileEntry 3 }

		
		sheXdslThresh15MinLoss OBJECT-TYPE
			SYNTAX HCPerfIntervalThreshold
			UNITS "seconds"
			MAX-ACCESS read-only
			STATUS current
			DESCRIPTION
				"This object configures the threshold for the number of
				loss of signal seconds (loss) within any given 15-minute
				performance data collection interval.  If the value of 
				loss of signal seconds in a particular 15-minute 
				collection interval reaches/exceeds this value, a 
				xdslPerfLossThreshNotification notification will be 
				generated.
				This configuration is set for xtuc and xtur side.
				Value 0 should be interpreted as disabled."
			REFERENCE
				"g.997.1 chapter 7.3.1.8"
			DEFVAL { 0 }
			::= { sheXdslLineAlarmConfProfileEntry 4 }

		
		sheXdslThresh15MinLprs OBJECT-TYPE
			SYNTAX HCPerfIntervalThreshold
			UNITS "seconds"
			MAX-ACCESS read-only
			STATUS current
			DESCRIPTION
				"This object configures the threshold for the number of
				loss of power seconds (lprs) within any given 15-minute
				performance data collection interval.  If the value of 
				loss of power seconds in a particular 15-minute collection
				interval reaches/exceeds this value, a 
				xdslPerfLprsThreshNotification notification will be 
				generated.
				This configuration is set for xtuc and xtur side.
				Value 0 should be interpreted as disabled."
			DEFVAL { 0 }
			::= { sheXdslLineAlarmConfProfileEntry 5 }

		
		sheXdslThresh15MinLols OBJECT-TYPE
			SYNTAX HCPerfIntervalThreshold
			UNITS "seconds"
			MAX-ACCESS read-only
			STATUS current
			DESCRIPTION
				"This object configures the threshold for the number of
				loss of link seconds (lols) within any given 15-minute
				performance data collection interval.  If the value of 
				loss of power seconds in a particular 15-minute collection
				interval reaches/exceeds this value, a 
				xdslPerfLolsThreshNotification notification will be 
				generated.
				This configuration is set for xtuc and xtur side.
				Value 0 should be interpreted as disabled."
			DEFVAL { 0 }
			::= { sheXdslLineAlarmConfProfileEntry 6 }

		
		sheXdslThresh15MinESs OBJECT-TYPE
			SYNTAX HCPerfIntervalThreshold
			UNITS "seconds"
			MAX-ACCESS read-only
			STATUS current
			DESCRIPTION
				"This object configures the threshold for the number of
				errored seconds (ESs) within any given 15-minute
				performance data collection interval.  If the value of 
				errored seconds in a particular 15-minute collection 
				interval reaches/exceeds this value, a 
				xdslPerfESsThreshNotification notification will be 
				generated.
				This configuration is set for xtuc and xtur side.
				Value 0 should be interpreted as disabled."
			REFERENCE
				"g.997.1 chapter 7.3.1.8"
			DEFVAL { 0 }
			::= { sheXdslLineAlarmConfProfileEntry 7 }

		
		sheXdslThresh15MinSESs OBJECT-TYPE
			SYNTAX HCPerfIntervalThreshold
			UNITS "seconds"
			MAX-ACCESS read-only
			STATUS current
			DESCRIPTION
				"This object configures the threshold for the number of
				severely errored seconds (SESs) within any given 15-minute
				performance data collection interval.  If the value of 
				severely errored seconds in a particular 15-minute 
				collection interval reaches/exceeds this value, a 
				xdslPerfSESsThreshNotification notification will be 
				generated.
				This configuration is set for xtuc and xtur side.
				Value 0 should be interpreted as disabled."
			REFERENCE
				"g.997.1 chapter 7.3.1.8"
			DEFVAL { 0 }
			::= { sheXdslLineAlarmConfProfileEntry 8 }

		
		sheXdslThresh15MinUASs OBJECT-TYPE
			SYNTAX HCPerfIntervalThreshold
			UNITS "seconds"
			MAX-ACCESS read-only
			STATUS current
			DESCRIPTION
				"This object configures the threshold for the number of
				unavailable seconds (UASs) within any given 15-minute
				performance data collection interval.  If the value of 
				unavailable seconds in a particular 15-minute collection 
				interval reaches/exceeds this value, a 
				xdslPerfUASsThreshNotification notification will be 
				generated.
				This configuration is set for xtuc and xtur side.
				Value 0 should be interpreted as disabled."
			REFERENCE
				"g.997.1 chapter 7.3.1.8"
			DEFVAL { 0 }
			::= { sheXdslLineAlarmConfProfileEntry 9 }

		
		sheXdslInitFailureNotifyEnable OBJECT-TYPE
			SYNTAX TruthValue
			MAX-ACCESS read-only
			STATUS current
			DESCRIPTION
				"This object specifies if a xdslInitFailureNotification will be 
				generated if an initialization failure occurs."
			DEFVAL { false }
			::= { sheXdslLineAlarmConfProfileEntry 10 }

		
		sheXdslLineAlarmOperationalStateNotifyEnable OBJECT-TYPE
			SYNTAX TruthValue
			MAX-ACCESS read-only
			STATUS current
			DESCRIPTION
				"This object specifies if a xdslOperationalStateNotification 
				will be generated if an operartional state change occurs."
			DEFVAL { true }
			::= { sheXdslLineAlarmConfProfileEntry 13 }

		
		sheXdslLineAlarmConfigViolationCheck OBJECT-TYPE
			SYNTAX SheXdslConfigViolationCheckType
			MAX-ACCESS read-only
			STATUS current
			DESCRIPTION
				"This parameter control the downstream line monitoring for CPE's which do not support the nearest
				supported impulse noise protection (INP) value. This is  related to MIB-parameter checks for 
				ADSL2x links between CO side and CPE side. In particular it can be checked whether a configured
				(i.e. desired) parameter setting is supported by the attached CPE as well.
				This capability information is exchange during handshake phase.
				
				When activated, the consequence of parameter violation can be to generate just a alarm and
				go to showtime anyway or the CPE shall not synchronize at all, i.e. the link will not be established.
				
				Valid settings:
				checkMinINP(1)          -> set BIT to 1 will enable the MinINP check
				abortOnINPViolation(2)  -> set BIT to 1 will abort the trainings sequence and the line will not reach 
				                            showtime state if a INP config violation was detectedcted
				
				Note:
				New parameter with R2.8 maintenance. 
				It is DSL firmware depended if a line support this feature and if a separate abort-handling
				is possible. If no support is available, the configuration will be ignored."
			::= { sheXdslLineAlarmConfProfileEntry 15 }

		
		sheXdslLineAlarmConfProfileControl OBJECT IDENTIFIER ::= { sheXdslMibObjects 14 }

		
		sheXdslLineAlarmConfProfileControlRequest OBJECT-TYPE
			SYNTAX SheXdslControlRequestType
			MAX-ACCESS read-write
			STATUS current
			DESCRIPTION
				"createXdslLineAlarmConfProfile            
				sheXdslLineAlarmConfProfileControlName
				...
				
				modifyXdslLineAlarmConfProfile
				sheXdslLineAlarmConfProfileControlIndex
				sheXdslLineAlarmConfProfileControlName
				...
				
				deleteXdslLineAlarmConfProfile
				sheXdslLineAlarmConfProfileControlIndex
				sheXdslLineAlarmConfProfileControlName
				
				"
			::= { sheXdslLineAlarmConfProfileControl 1 }

		
		sheXdslLineAlarmConfProfileControlIndex OBJECT-TYPE
			SYNTAX Unsigned32 (1..300)
			MAX-ACCESS read-write
			STATUS current
			DESCRIPTION
				"Index of the configured xdsl line alarm profile.."
			::= { sheXdslLineAlarmConfProfileControl 2 }

		
		sheXdslLineAlarmConfProfileControlStatus OBJECT-TYPE
			SYNTAX SheControlStatusType
			MAX-ACCESS read-only
			STATUS current
			DESCRIPTION
				"The status of a user command. 
				"
			::= { sheXdslLineAlarmConfProfileControl 3 }

		
		sheXdslLineAlarmConfProfileControlTimer OBJECT-TYPE
			SYNTAX Gauge32
			MAX-ACCESS read-only
			STATUS current
			DESCRIPTION
				"The maximum wait time for the manager for a long running user command. 
				"
			::= { sheXdslLineAlarmConfProfileControl 4 }

		
		sheXdslLineAlarmConfProfileControlReqResult OBJECT-TYPE
			SYNTAX SheXdslControlRequestResultType
			MAX-ACCESS read-only
			STATUS current
			DESCRIPTION
				"The result of the last user command."
			::= { sheXdslLineAlarmConfProfileControl 5 }

		
		sheXdslLineAlarmConfProfileControlTimeStamp OBJECT-TYPE
			SYNTAX Unsigned32
			UNITS "sec"
			MAX-ACCESS read-only
			STATUS current
			DESCRIPTION
				"The time stamp of the last command (end of command)."
			::= { sheXdslLineAlarmConfProfileControl 6 }

		
		sheXdslLineAlarmConfProfileControlName OBJECT-TYPE
			SYNTAX SnmpAdminString (SIZE (1..32))
			MAX-ACCESS read-write
			STATUS current
			DESCRIPTION
				"look at table"
			::= { sheXdslLineAlarmConfProfileControl 7 }

		
		sheXdslLineAlarmConfProfileControlThresh15MinLofs OBJECT-TYPE
			SYNTAX HCPerfIntervalThreshold
			UNITS "seconds"
			MAX-ACCESS read-write
			STATUS current
			DESCRIPTION
				"Look at table."
			::= { sheXdslLineAlarmConfProfileControl 8 }

		
		sheXdslLineAlarmConfProfileControlThresh15MinLoss OBJECT-TYPE
			SYNTAX HCPerfIntervalThreshold
			UNITS "seconds"
			MAX-ACCESS read-write
			STATUS current
			DESCRIPTION
				"Look at table."
			::= { sheXdslLineAlarmConfProfileControl 9 }

		
		sheXdslLineAlarmConfProfileControlThresh15MinLprs OBJECT-TYPE
			SYNTAX HCPerfIntervalThreshold
			UNITS "seconds"
			MAX-ACCESS read-write
			STATUS current
			DESCRIPTION
				"Look at table."
			::= { sheXdslLineAlarmConfProfileControl 10 }

		
		sheXdslLineAlarmConfProfileControlThresh15MinLols OBJECT-TYPE
			SYNTAX HCPerfIntervalThreshold
			UNITS "seconds"
			MAX-ACCESS read-write
			STATUS current
			DESCRIPTION
				"Look at table."
			::= { sheXdslLineAlarmConfProfileControl 11 }

		
		sheXdslLineAlarmConfProfileControlThresh15MinESs OBJECT-TYPE
			SYNTAX HCPerfIntervalThreshold
			UNITS "seconds"
			MAX-ACCESS read-write
			STATUS current
			DESCRIPTION
				"Look at table."
			::= { sheXdslLineAlarmConfProfileControl 12 }

		
		sheXdslLineAlarmConfProfileControlThresh15MinSESs OBJECT-TYPE
			SYNTAX HCPerfIntervalThreshold
			UNITS "seconds"
			MAX-ACCESS read-write
			STATUS current
			DESCRIPTION
				"Look at table."
			::= { sheXdslLineAlarmConfProfileControl 13 }

		
		sheXdslLineAlarmConfProfileControlThresh15MinUASs OBJECT-TYPE
			SYNTAX HCPerfIntervalThreshold
			UNITS "seconds"
			MAX-ACCESS read-write
			STATUS current
			DESCRIPTION
				"Look at table."
			::= { sheXdslLineAlarmConfProfileControl 14 }

		
		sheXdslLineAlarmConfProfileControlInitFailureNotifyEnable OBJECT-TYPE
			SYNTAX TruthValue
			MAX-ACCESS read-write
			STATUS current
			DESCRIPTION
				"Look at table."
			::= { sheXdslLineAlarmConfProfileControl 15 }

		
		sheXdslLineAlarmConfProfileOperationalStateNotifyEnable OBJECT-TYPE
			SYNTAX TruthValue
			MAX-ACCESS read-write
			STATUS current
			DESCRIPTION
				"look at table."
			::= { sheXdslLineAlarmConfProfileControl 18 }

		
		sheXdslLineAlarmConfProfileViolationCheck OBJECT-TYPE
			SYNTAX SheXdslConfigViolationCheckType
			MAX-ACCESS read-write
			STATUS current
			DESCRIPTION
				"look at table.
				
				Note:
				New parameter with R2.8 maintenance. "
			::= { sheXdslLineAlarmConfProfileControl 20 }

		
		sheXdslLineConfExtnProfileTable OBJECT-TYPE
			SYNTAX SEQUENCE OF SheXdslLineConfExtnProfileEntry
			MAX-ACCESS not-accessible
			STATUS current
			DESCRIPTION
				"This table contains information on the XDSL line
				configuration.  One entry in this table reflects a
				profile defined by a manager which can be used to
				configure the XDSL line.
				
				Entries in this table MUST be maintained in a 
				persistent manner."
			::= { sheXdslMibObjects 15 }

		
		sheXdslLineConfExtnProfileEntry OBJECT-TYPE
			SYNTAX SheXdslLineConfExtnProfileEntry
			MAX-ACCESS not-accessible
			STATUS current
			DESCRIPTION
				"Each entry consists of a list of parameters that
				represents the configuration of a xDSL line.   
				
				Dynamic' profiles are implemented.The profile name is user specified.
				There are five different default profiles in the NE, which could not be modified!
				Check corresponding LineProfile-Entry for detailes."
			INDEX { sheXdslLineConfProfileIndex }
			::= { sheXdslLineConfExtnProfileTable 1 }

		
		SheXdslLineConfExtnProfileEntry ::=
			SEQUENCE { 
				sheXdslLineConfExtnDownBitSwap
					SheXdslEnableType,
				sheXdslLineConfExtnUpBitSwap
					SheXdslEnableType,
				sheXdslLineConfExtnDownPboEsel
					Unsigned32,
				sheXdslLineConfExtnDownPboMus
					Unsigned32,
				sheXdslLineConfExtnDownPboFMin
					Unsigned32,
				sheXdslLineConfExtnDownPboFMax
					Unsigned32,
				sheXdslLineConfExtnXtucPwrMgmtL0Time
					INTEGER,
				sheXdslLineConfExtnXtucPwrMgmtL2Time
					INTEGER,
				sheXdslLineConfExtnXtucPwrMgmtL2ATPR
					INTEGER,
				sheXdslLineConfExtnXtucPwrMgmtMode
					SheXdslXtucPwrMgmtModeType,
				sheXdslLineConfExtnUseCustomSubcarrierMask
					SheXdslEnableType,
				sheXdslLineConfExtnCustomSubcarrierMask
					OCTET STRING,
				sheXdslLineConfExtnXtucPwrMgmtL2ATPRT
					INTEGER,
				sheXdslLineConfExtnDownPboEpsd
					OCTET STRING,
				sheXdslLineConfExtnDownPboEScmA
					Unsigned32,
				sheXdslLineConfExtnDownPboEScmB
					Unsigned32,
				sheXdslLineConfExtnDownPboEScmC
					Unsigned32,
				sheXdslLineConfExtnUpPboA
					OCTET STRING,
				sheXdslLineConfExtnUpPboB
					OCTET STRING,
				sheXdslLineConfExtnMaxDownNomPsd
					Integer32,
				sheXdslLineConfExtnMaxUpNomPsd
					Integer32,
				sheXdslLineConfExtnDownPboEselMin
					Unsigned32,
				sheXdslLineConfExtnDownPboMof
					Unsigned32,
				sheXdslLineConfExtnProfileUpPboKL
					Unsigned32,
				sheXdslLineConfExtnProfileUpPboKO
					SheXdslEnableType,
				sheXdslLineConfExtnProfileUpPboBoostMode
					SheXdslEnableType,
				sheXdslLineConfExtnMsgMinUp
					Unsigned32,
				sheXdslLineConfExtnMsgMinDown
					Unsigned32,
				sheXdslLineConfExtnUsPsdMaskSelection
					SheXdslLineConfUsPSDMaskSelectionType,
				sheXdslLineConfExtnCustomUsSubcarrierMask
					OCTET STRING,
				sheXdslLineConfExtnSnrModeDown
					SheXdslSnrModeType,
				sheXdslLineConfExtnSnrModeUp
					SheXdslSnrModeType,
				sheXdslLineConfExtnTxRefVnDown
					OCTET STRING,
				sheXdslLineConfExtnTxRefVnUp
					OCTET STRING
			 }

		sheXdslLineConfExtnDownBitSwap OBJECT-TYPE
			SYNTAX SheXdslEnableType
			MAX-ACCESS read-only
			STATUS current
			DESCRIPTION
				"downstream bit swapping"
			DEFVAL { 1 }
			::= { sheXdslLineConfExtnProfileEntry 1 }

		
		sheXdslLineConfExtnUpBitSwap OBJECT-TYPE
			SYNTAX SheXdslEnableType
			MAX-ACCESS read-only
			STATUS current
			DESCRIPTION
				"upstream bit swapping"
			DEFVAL { 1 }
			::= { sheXdslLineConfExtnProfileEntry 2 }

		
		sheXdslLineConfExtnDownPboEsel OBJECT-TYPE
			SYNTAX Unsigned32 (0..511)
			UNITS "0.5dB"
			MAX-ACCESS read-only
			STATUS current
			DESCRIPTION
				"This configuration parameter defines the assumed electrical length of cables
				(E-side cables) connecting exchange based DSL services to a remote flexibility
				point (cabinet), that may also host remotely located DSL that is subject
				to spectrally shaped downstream power backoff depending on this length.
				For this parameter the electrical length is defined as the loss (in dB)
				of an equivalent length of hypothetical cable at a reference frequency
				defined by the network operator or in spectrum management regulations.
				All values which can be represented by the format are valid values.
				
				If this value is zero, the DPBO in this section shall be disabled.
				If this value is not zero and sheXdslLineConfExtnDownPboEselMin is not
				512 (disabled EselMin), sheXdslLineConfExtnDownPboEsel >= sheXdslLineConfExtnDownPboEselMin 
				is required!
				"
			REFERENCE
				"g.997 chapter 7.3.1.2.13"
			DEFVAL { 0 }
			::= { sheXdslLineConfExtnProfileEntry 3 }

		
		sheXdslLineConfExtnDownPboMus OBJECT-TYPE
			SYNTAX Unsigned32 (0..255)
			UNITS "0.5 dBm/Hz"
			MAX-ACCESS read-only
			STATUS current
			DESCRIPTION
				"DPBOMUS defines the assumed Minimum Usable receive Signal PSD (in dBm/Hz) for
				exchange based services, used to modify parameter DPBOFMAX defined below. 
				All values which can be represented by the format are valid values:
				0 = 0 dBm/Hz .. -127.5 dBm/Hz (coded as 255)."
			REFERENCE
				"g.997 chapter 7.3.1.2.13"
			DEFVAL { 216 }
			::= { sheXdslLineConfExtnProfileEntry 4 }

		
		sheXdslLineConfExtnDownPboFMin OBJECT-TYPE
			SYNTAX Unsigned32 (0..2048)
			MAX-ACCESS read-only
			STATUS current
			DESCRIPTION
				"DPBO shall be applied in the range starting at DPBOFMIN and should
				be configured as an subcarrier index. 
				The resulting range of valid values is from 0 to 8832 kHz in steps of 4.3125 kHz.."
			REFERENCE
				"g.997 chapter 7.3.1.2.13 a5)"
			DEFVAL { 64 }
			::= { sheXdslLineConfExtnProfileEntry 5 }

		
		sheXdslLineConfExtnDownPboFMax OBJECT-TYPE
			SYNTAX Unsigned32 (32..4095)
			MAX-ACCESS read-only
			STATUS current
			DESCRIPTION
				"The maximum subcarrier at which DPBO may be applied is DPBOFMAX. 
				The resulting range of valid values is from 138 kHz to 29997.75 kHz in steps of 4.3125 kHz."
			REFERENCE
				"g.997 chapter 7.3.1.2.13 a6)"
			DEFVAL { 512 }
			::= { sheXdslLineConfExtnProfileEntry 6 }

		
		sheXdslLineConfExtnXtucPwrMgmtL0Time OBJECT-TYPE
			SYNTAX INTEGER (0..255)
			MAX-ACCESS read-only
			STATUS current
			DESCRIPTION
				"This parameter represents the minimum time (in seconds)
				between an exit from the L2 state and the next entry into
				the L2 state. It ranges from 0 to 255 seconds.
				"
			REFERENCE
				"g.997.1 chapter 7.3.1.1.5"
			DEFVAL { 10 }
			::= { sheXdslLineConfExtnProfileEntry 7 }

		
		sheXdslLineConfExtnXtucPwrMgmtL2Time OBJECT-TYPE
			SYNTAX INTEGER (0..255)
			MAX-ACCESS read-only
			STATUS current
			DESCRIPTION
				"This parameter represents the minimum time (in seconds)
				between an Entry into the L2 state and the first
				Power Trim in the L2 state and between two consecutive
				Power Trims in the L2 State. It ranges from 0 to 255 seconds.
				"
			REFERENCE
				"g.997.1 chapter 7.3.1.1.6"
			DEFVAL { 10 }
			::= { sheXdslLineConfExtnProfileEntry 8 }

		
		sheXdslLineConfExtnXtucPwrMgmtL2ATPR OBJECT-TYPE
			SYNTAX INTEGER (0..31)
			UNITS "1dB"
			MAX-ACCESS read-only
			STATUS current
			DESCRIPTION
				"This parameter represents the maximum aggregate transmit power reduction (in dB)
				that can be performed through a single Power Trim in the L2 state.
				It ranges from 0 dB to 31 dB in steps of 1 dB.
				"
			REFERENCE
				"g.997.1 chapter 7.3.1.1.7"
			DEFVAL { 0 }
			::= { sheXdslLineConfExtnProfileEntry 9 }

		
		sheXdslLineConfExtnXtucPwrMgmtMode OBJECT-TYPE
			SYNTAX SheXdslXtucPwrMgmtModeType
			MAX-ACCESS read-only
			STATUS current
			DESCRIPTION
				"Which Xdsl Power Management state is enabled and 
				where the line may autonomously transition to.
				disable(0)       -> none
				l3Enabled(1)     -> idle state
				l1l2Enabled(2)   -> low power state
				l1l2l3Enabled(3) -> all
				"
			REFERENCE
				"g.997.1 chapter 7.3.1.1.4"
			DEFVAL { 0 }
			::= { sheXdslLineConfExtnProfileEntry 11 }

		
		sheXdslLineConfExtnUseCustomSubcarrierMask OBJECT-TYPE
			SYNTAX SheXdslEnableType
			MAX-ACCESS read-only
			STATUS current
			DESCRIPTION
				"Enable/Disable usage of subcarrier masking defined in 
				sheXdslLineConfExtnCustomSubcarrierMask for DS direction and 
				sheXdslLineConfExtnCustomUsSubcarrierMask for US direction.
				
				Only valid for ADSL, ADSL2 and ADSL2+ mode.
				
				Note: 
				The parameter sheXdslLineConfExtnCustomUsSubcarrierMask is only valid for
				SHE R2.6 RP2 and following."
			DEFVAL { disable }
			::= { sheXdslLineConfExtnProfileEntry 16 }

		
		sheXdslLineConfExtnCustomSubcarrierMask OBJECT-TYPE
			SYNTAX OCTET STRING (SIZE (0..64))
			MAX-ACCESS read-only
			STATUS current
			DESCRIPTION
				"Each one of the 512 bits in this OCTET STRING array represents the corresponding bin.
				A value of one indicates that the corresponding subcarrier is enabled.
				
				Coding example: '8001FFFF....' enables first subcarrier (subcarrier 0), sixteenth subcarrier
				and all followings.
				
				Default value will be one (enable) for all subcarriers which means that the NE uses the subcarriers
				according the selected standard.
				
				Only valid for ADSL, ADSL2 and ADSL2+ mode. Depending on the used standard,
				only a subset of bin's will be evaluated by the NE. Example:
				G992.1 (ADSL) AnnexA bin 6-32 related to US and bin 33-255 related to DS direction.
				G992.1 (ADSL) AnnexB bin 32-63 related to US and bin 64-255 related to DS direction.
				For G.992.4, and G.992.5, it is defined in the corresponding recommendations.
				
				Note:
				With SHE R2.6 RP2, this parameter defines only the DS SubcarrierMask!
				The US SubcarrierMask was moved to sheXdslLineConfExtnCustomUsSubcarrierMask parameter."
			REFERENCE
				"g.997.1 chapter 7.3.1.2.6"
			::= { sheXdslLineConfExtnProfileEntry 17 }

		
		sheXdslLineConfExtnXtucPwrMgmtL2ATPRT OBJECT-TYPE
			SYNTAX INTEGER (0..31)
			UNITS "1dB"
			MAX-ACCESS read-only
			STATUS current
			DESCRIPTION
				"This parameter represents the total maximum aggregate transmit power reduction (in dB)
				that can be performed in an L2 state. This is the sum of all reductions of L2 request
				and power trims.
				It ranges from 0 dB to 31 dB in steps of 1 dB."
			REFERENCE
				"g.997.1 chapter 7.3.1.1.9"
			DEFVAL { 0 }
			::= { sheXdslLineConfExtnProfileEntry 18 }

		
		sheXdslLineConfExtnDownPboEpsd OBJECT-TYPE
			SYNTAX OCTET STRING (SIZE (64))
			MAX-ACCESS read-only
			STATUS current
			DESCRIPTION
				"Used PSD mask that is assumed to be permitted at the exchange.
				The set of breakpoints can be represented as [(t1, PSD1),(t2, PSD2),
				.. , (tN, PSDN)]. The subcarrier index (tN) shall be coded as an unsigned
				integer (16 bit, range 1..4095). The MIB PSD mask level (PSDN) shall be
				coded as an unsigned integer (16 bit) representing the MIB PSD mask levels
				0 dBm/Hz (coded as 0) to -127.5 dBm/Hz (coded as 255), in steps of 0.5 dBm/Hz.
				
				The maximum number of breakpoints for DPBOEPSD is 16. If less then maximum
				breakpoints will be defined, all used breakpoints should be configured in a
				consecutive way without spaces (t1 - t2 - t3.. and not t1 - t5 - t7..). The
				default value should be set according PSD settings for ADSL2+.
				
				Subcarrier     PSD
				59             -36.5 
				256            -36.5
				314            -42
				376            -46.5
				499            -47.5
				"
			REFERENCE
				"g.997 chapter 7.3.1.2.13"
			DEFVAL { '003B004901000049013A00540178005D01F3005F'h }
			::= { sheXdslLineConfExtnProfileEntry 19 }

		
		sheXdslLineConfExtnDownPboEScmA OBJECT-TYPE
			SYNTAX Unsigned32 (0..640)
			UNITS "2^-8"
			MAX-ACCESS read-only
			STATUS current
			DESCRIPTION
				"This configuration parameter defines a cable model in terms of three
				scalars DPBOESCMA, DPBOESCMB and DPBOESCMC that are used to estimate
				the frequency dependent loss of E-side cables calculated from the
				
				DPBOESEL parameter using the formula:
				  ESCM(f) = (DPBOESCMA + DPBOESCMB*sqrt(f) + DPBOESCMC*f )*DPBOESCL
				
				Where ESCM is expressed in dB and f is expressed in MHz.
				DPBOESCMA, DPBOESCMB, DPBOESCMC shall be coded as unsigned integers
				representing a scalar value from -1 (coded as 0) to 1.5 (coded as 640)
				in step of 2^-8. All values are valid."
			REFERENCE
				"g.997 chapter 7.3.1.2.13"
			DEFVAL { 270 }
			::= { sheXdslLineConfExtnProfileEntry 20 }

		
		sheXdslLineConfExtnDownPboEScmB OBJECT-TYPE
			SYNTAX Unsigned32 (0..640)
			UNITS "2^-8"
			MAX-ACCESS read-only
			STATUS current
			DESCRIPTION
				"This configuration parameter defines a cable model in terms of three
				scalars DPBOESCMA, DPBOESCMB and DPBOESCMC that are used to estimate
				the frequency dependent loss of E-side cables calculated from the
				
				DPBOESEL parameter using the formula:
				  ESCM(f) = (DPBOESCMA + DPBOESCMB*sqrt(f) + DPBOESCMC*f )*DPBOESCL
				
				Where ESCM is expressed in dB and f is expressed in MHz.
				DPBOESCMA, DPBOESCMB, DPBOESCMC shall be coded as unsigned integers
				representing a scalar value from -1 (coded as 0) to 1.5 (coded as 640)
				in step of 2^-8. All values are valid."
			REFERENCE
				"g.997 chapter 7.3.1.2.13"
			DEFVAL { 490 }
			::= { sheXdslLineConfExtnProfileEntry 21 }

		
		sheXdslLineConfExtnDownPboEScmC OBJECT-TYPE
			SYNTAX Unsigned32 (0..640)
			UNITS "2^-8"
			MAX-ACCESS read-only
			STATUS current
			DESCRIPTION
				"This configuration parameter defines a cable model in terms of three
				scalars DPBOESCMA, DPBOESCMB and DPBOESCMC that are used to estimate
				the frequency dependent loss of E-side cables calculated from the
				
				DPBOESEL parameter using the formula:
				  ESCM(f) = (DPBOESCMA + DPBOESCMB*sqrt(f) + DPBOESCMC*f )*DPBOESCL
				
				Where ESCM is expressed in dB and f is expressed in MHz.
				DPBOESCMA, DPBOESCMB, DPBOESCMC shall be coded as unsigned integers
				representing a scalar value from -1 (coded as 0) to 1.5 (coded as 640)
				in step of 2^-8. All values are valid."
			REFERENCE
				"g.997 chapter 7.3.1.2.13"
			DEFVAL { 264 }
			::= { sheXdslLineConfExtnProfileEntry 22 }

		
		sheXdslLineConfExtnUpPboA OBJECT-TYPE
			SYNTAX OCTET STRING (SIZE (10))
			UNITS "0.01 dBm/Hz"
			MAX-ACCESS read-only
			STATUS current
			DESCRIPTION
				"Is the value of A in the reference PSD, PSDREF(f)= -A - B * sqrt(f).
				The value is given for each US band except US0. Each single value consists
				of 2 octets. First couple of octets representing the value for band US1.
				Second for band US2, third for US3, fourth for US4 and the last
				couple represent the value for US5. All values can be set, but only if the
				respective band is realy in use the values will be taken, otherwise
				NE will ignore the settings. 
				The simultaneous setting of values of UPBOA = 40 dBm/Hz and 
				UPBOB = 0 dBm/Hz for a band shall cause UPBO to be disabled.
				This are the default setting for all band's.
				
				The valid range for a single index: 4000 .. 8095"
			REFERENCE
				"g.997 chapter 7.3.1.2.14 point a1)."
			DEFVAL { '0FA00FA00FA00FA00FA0'h }
			::= { sheXdslLineConfExtnProfileEntry 23 }

		
		sheXdslLineConfExtnUpPboB OBJECT-TYPE
			SYNTAX OCTET STRING (SIZE (10))
			UNITS "0.01 dBm/Hz"
			MAX-ACCESS read-only
			STATUS current
			DESCRIPTION
				"Is the value of B in the reference PSD, PSDREF(f)= -A - B * sqrt(f).
				The value is given for each US band except US0. Each single value consists
				of 2 octets. First couple of octets representing the value band US1.
				Second for band US2, third for US3, fourth for US4 and the last
				couple represent the value for US5. All values can be set, but only if the
				respective band is realy in use the values will be taken, otherwise
				NE will ignore the settings. 
				The simultaneous setting of values of UPBOA = 40 dBm/Hz and 
				UPBOB = 0 dBm/Hz for a band shall cause UPBO to be disabled.
				This are the default setting for all band's.
				
				The valid range for a single index: 0 .. 4095"
			REFERENCE
				"g.997 chapter 7.3.1.2.14 point a1)."
			DEFVAL { '00000000000000000000'h }
			::= { sheXdslLineConfExtnProfileEntry 24 }

		
		sheXdslLineConfExtnMaxDownNomPsd OBJECT-TYPE
			SYNTAX Integer32 (-600..-300)
			UNITS "0.1 dBm/Hz"
			MAX-ACCESS read-only
			STATUS current
			DESCRIPTION
				"This parameter represents the maximum nominal transmit PSD in 
				downstream direction during initialization and showtime."
			REFERENCE
				"g.997 chapter 7.3.1.2.1"
			DEFVAL { -535 }
			::= { sheXdslLineConfExtnProfileEntry 25 }

		
		sheXdslLineConfExtnMaxUpNomPsd OBJECT-TYPE
			SYNTAX Integer32 (-600..-300)
			UNITS "0.1 dBm/Hz"
			MAX-ACCESS read-only
			STATUS current
			DESCRIPTION
				"This parameter represents the maximum nominal transmit PSD in 
				upstream direction during initialization and showtime."
			REFERENCE
				"g.997 chapter 7.3.1.2.2"
			DEFVAL { -543 }
			::= { sheXdslLineConfExtnProfileEntry 26 }

		
		sheXdslLineConfExtnDownPboEselMin OBJECT-TYPE
			SYNTAX Unsigned32 (0..512)
			UNITS "0.5dB"
			MAX-ACCESS read-only
			STATUS current
			DESCRIPTION
				"This configuration parameter defines the minimum assumed electrical length 
				of cables (E-side cables) connecting exchange based DSL services to a 
				remote flexibility point (cabinet), that may also host remotely located DSL
				that is subject to spectrally shaped downstream power backoff depending on this
				length. For this parameter the electrical length is defined as the loss (in dB)
				of an equivalent length of hypothetical cable at a reference frequency
				defined by the network operator or in spectrum management regulations.
				All values which can be represented by the format are valid values.
				
				Default: sheXdslLineConfExtnDownPboEselMin = 512
				
				If this value is not 512 (disabled) and sheXdslLineConfExtnDownPboEsel is not
				zero (DPBO disabled), sheXdslLineConfExtnDownPboEsel >= sheXdslLineConfExtnDownPboEselMin 
				is required!
				
				"
			REFERENCE
				"g.997 chapter 7.3.1.2.13"
			DEFVAL { 512 }
			::= { sheXdslLineConfExtnProfileEntry 27 }

		
		sheXdslLineConfExtnDownPboMof OBJECT-TYPE
			SYNTAX Unsigned32 (0..255)
			UNITS "0.5 dBm/Hz"
			MAX-ACCESS read-only
			STATUS current
			DESCRIPTION
				"DPBOMOF (mask overall floor) defines the absolut minimum of the used PSD mask
				(in dBm/Hz) for exchange based services.
				All values which can be represented by the format are valid values:
				0 = 0 dBm/Hz .. -127.5 dBm/Hz (coded as 255).
				
				NOTE:
				This parameter is not longer supported with R2.6 RP2."
			REFERENCE
				"g.997 chapter 7.3.1.2.13"
			DEFVAL { 190 }
			::= { sheXdslLineConfExtnProfileEntry 28 }

		
		sheXdslLineConfExtnProfileUpPboKL OBJECT-TYPE
			SYNTAX Unsigned32 (0..1280)
			UNITS "0.1 dB"
			MAX-ACCESS read-only
			STATUS current
			DESCRIPTION
				"This parameter defines the electrical loop length expressed in dB at 1 MHz.
				The value could be coded in the range from 0 to 128 dB in steps of 0.1 dB."
			REFERENCE
				"g.997 chapter 7.3.1.2.14 point a2)."
			::= { sheXdslLineConfExtnProfileEntry 30 }

		
		sheXdslLineConfExtnProfileUpPboKO OBJECT-TYPE
			SYNTAX SheXdslEnableType
			MAX-ACCESS read-only
			STATUS current
			DESCRIPTION
				"This parameter is a flag that forces the xTU-R to use the electrical loop length
				of the MIB (defined in sheXdslLineConfExtnProfileUpPboKL) to compute UPBO. If 
				not enabled, the electrical loop length shall be autonomously derived be the xTU's.
				Default value is disabled."
			REFERENCE
				"g.997 chapter 7.3.1.2.14 point a3)."
			DEFVAL { 2 }
			::= { sheXdslLineConfExtnProfileEntry 31 }

		
		sheXdslLineConfExtnProfileUpPboBoostMode OBJECT-TYPE
			SYNTAX SheXdslEnableType
			MAX-ACCESS read-only
			STATUS current
			DESCRIPTION
				"Enable Boost Mode.
				If disabled, the UPBO standard mode is used with the LOSS function calculated according to §7.3.1.2.13 of G.997.1."
			REFERENCE
				"g.997 chapter 7.3.1.2.13 "
			DEFVAL { 1 }
			::= { sheXdslLineConfExtnProfileEntry 32 }

		
		sheXdslLineConfExtnMsgMinUp OBJECT-TYPE
			SYNTAX Unsigned32 (4..248)
			UNITS "kbps"
			MAX-ACCESS read-only
			STATUS current
			DESCRIPTION
				"This parameter defines the minimum rate of the message based overhead that shall be maintained
				by the xTU in the upstream direction. MSGMINus is expressed in bits per second and ranges from
				4000 to 248 000 bit/s with 1000 bit/s steps."
			REFERENCE
				"g.997 chapter 7.3.1.5.1"
			DEFVAL { 16 }
			::= { sheXdslLineConfExtnProfileEntry 33 }

		
		sheXdslLineConfExtnMsgMinDown OBJECT-TYPE
			SYNTAX Unsigned32 (4..248)
			UNITS "kbps"
			MAX-ACCESS read-only
			STATUS current
			DESCRIPTION
				"This parameter defines the minimum rate of the message based overhead that shall be maintained
				by the xTU in the downstream direction. MSGMINds is expressed in bits per second and ranges from
				4000 to 248 000 bit/s with 1000 bit/s steps."
			REFERENCE
				"g.997 chapter 7.3.1.5.2"
			DEFVAL { 16 }
			::= { sheXdslLineConfExtnProfileEntry 34 }

		
		sheXdslLineConfExtnUsPsdMaskSelection OBJECT-TYPE
			SYNTAX SheXdslLineConfUsPSDMaskSelectionType
			MAX-ACCESS read-only
			STATUS current
			DESCRIPTION
				"Selects the PSD mask option to be used.
				This parameter is used only for annexes J and M of ITU-T Recs. G.992-3 and G.992.5.
				Other DSL standards will ignore the configured value!"
			REFERENCE
				"G997.1 chapter 7.3.1.2.11"
			DEFVAL { adlu64eu64 }
			::= { sheXdslLineConfExtnProfileEntry 35 }

		
		sheXdslLineConfExtnCustomUsSubcarrierMask OBJECT-TYPE
			SYNTAX OCTET STRING (SIZE (0..64))
			MAX-ACCESS read-only
			STATUS current
			DESCRIPTION
				"Each one of the 512 bits in this OCTET STRING array represents the corresponding bin.
				A value of one indicates that the corresponding subcarrier is enabled.
				
				Coding example: '03FFFFFE00...' enables subcarrier's 6-32 and disable all followings.
				
				Default value will be one (enable) for all subcarriers which means that the NE uses the subcarriers
				according the selected standard.
				
				Only valid for ADSL, ADSL2 and ADSL2+ mode. Depending on the used standard,
				only a subset of bin's will be evaluated by the NE. Example:
				G992.1 (ADSL) AnnexA bin 6-32 related to US and bin 33-256 related to DS direction.
				G992.1 (ADSL) AnnexB bin 32-63 related to US and bin 64-256 related to DS direction.
				For G.992.4, and G.992.5, it is defined in the corresponding recommendations.
				
				Note:
				New parameter with SHE R2.6 RP2 and defines only the US SubcarrierMask!
				The DS SubcarrierMask is defined in sheXdslLineConfExtnCustomSubcarrierMask parameter."
			REFERENCE
				"g.997.1 chapter 7.3.1.2.7"
			::= { sheXdslLineConfExtnProfileEntry 36 }

		
		sheXdslLineConfExtnSnrModeDown OBJECT-TYPE
			SYNTAX SheXdslSnrModeType
			MAX-ACCESS read-only
			STATUS current
			DESCRIPTION
				"This parameter enables the transmitter referred virtual noise in the downstream direction,
				defined in sheXdslLineConfExtnTxRefVnDown.
				If set to 1, the virtual noise is disabled. If set to 2, the virtual noise is enabled.
				
				Note: Configuration is only valid for VDSL2 mode."
			REFERENCE
				"g.997.1 chapter 7.3.1.7.1"
			DEFVAL { virtualNoiseDisabled }
			::= { sheXdslLineConfExtnProfileEntry 37 }

		
		sheXdslLineConfExtnSnrModeUp OBJECT-TYPE
			SYNTAX SheXdslSnrModeType
			MAX-ACCESS read-only
			STATUS current
			DESCRIPTION
				"This parameter enables the transmitter referred virtual noise in the upstream direction,
				defined in sheXdslLineConfExtnTxRefVnUp.
				If set to 1, the virtual noise is disabled. If set to 2, the virtual noise is enabled.
				
				Note: Configuration is only valid for VDSL2 mode."
			REFERENCE
				"g.997.1 chapter 7.3.1.7.2"
			DEFVAL { virtualNoiseDisabled }
			::= { sheXdslLineConfExtnProfileEntry 38 }

		
		sheXdslLineConfExtnTxRefVnDown OBJECT-TYPE
			SYNTAX OCTET STRING (SIZE (0..128))
			MAX-ACCESS read-only
			STATUS current
			DESCRIPTION
				"This configuration parameter defines the downstream transmitter referred virtual noise
				(TXREFVNds). The TXREFVNds shall be specified through a set of breakpoints. Each breakpoint
				shall consist of a subcarrier index t, with a subcarrier spacing of 4.3125 kHz, and a noise PSD level
				(expressed in dBm/Hz) at that subcarrier. The set of breakpoints can then be represented as [(t1,
				PSD1), (t2, PSD2), . , (tN, PSDN)]. The subcarrier index shall be coded as an unsigned integer 
				(16 bit, value range 1..4096, 0 means breakpoint not used). The noise level (16 bit) ranges 
				from -40 dBm/Hz (coded as 0) to -140 dBm/Hz (coded as 200) in steps of 0.5 dBm/Hz. 
				A special value (coded as 255) indicates a noise level of 0 W/Hz.
				The maximum number of breakpoints is 32. If less then maximum breakpoints will be defined,
				all used breakpoints should be configured in a consecutive way without spaces.
				
				Note: Configuration is only valid for VDSL2 mode.
				"
			REFERENCE
				"g.997.1 chapter 7.3.1.7.3"
			DEFVAL { ''h }
			::= { sheXdslLineConfExtnProfileEntry 39 }

		
		sheXdslLineConfExtnTxRefVnUp OBJECT-TYPE
			SYNTAX OCTET STRING (SIZE (0..64))
			MAX-ACCESS read-only
			STATUS current
			DESCRIPTION
				"This configuration parameter defines the upstream transmitter referred virtual noise
				(TXREFVNus). The TXREFVNus shall be specified through a set of breakpoints. Each breakpoint
				shall consist of a subcarrier index t, with a subcarrier spacing of 4.3125 kHz, and a noise PSD level
				(expressed in dBm/Hz) at that subcarrier. The set of breakpoints can then be represented as [(t1,
				PSD1), (t2, PSD2), . , (tN, PSDN)]. The subcarrier index shall be coded as an unsigned integer 
				(16 bit, value range 1..4096, 0 means breakpoint not used). The noise level (16 bit) ranges 
				from -40 dBm/Hz (coded as 0) to -140 dBm/Hz (coded as 200) in steps of 0.5 dBm/Hz. 
				A special value (coded as 255) indicates a noise level of 0 W/Hz.
				The maximum number of breakpoints is 16. If less then maximum breakpoints will be defined,
				all used breakpoints should be configured in a consecutive way without spaces.
				
				Note: Configuration is only valid for VDSL2 mode.
				"
			REFERENCE
				"g.997.1 chapter 7.3.1.7.4"
			DEFVAL { ''h }
			::= { sheXdslLineConfExtnProfileEntry 40 }

		
		sheXdslLineConfExtnProfileControl OBJECT IDENTIFIER ::= { sheXdslMibObjects 16 }

		
		sheXdslLineConfExtnProfileControlRequest OBJECT-TYPE
			SYNTAX SheXdslControlRequestType
			MAX-ACCESS read-write
			STATUS current
			DESCRIPTION
				"modifyXdslLineConfExtnProfile
				sheXdslLineConfExtnProfileControlIndex
				...
				
				
				"
			::= { sheXdslLineConfExtnProfileControl 1 }

		
		sheXdslLineConfExtnProfileControlIndex OBJECT-TYPE
			SYNTAX Unsigned32 (1..300)
			MAX-ACCESS read-write
			STATUS current
			DESCRIPTION
				"Index of the configured xdsl line profile."
			::= { sheXdslLineConfExtnProfileControl 2 }

		
		sheXdslLineConfExtnProfileControlStatus OBJECT-TYPE
			SYNTAX SheControlStatusType
			MAX-ACCESS read-only
			STATUS current
			DESCRIPTION
				"The status of a user command. 
				"
			::= { sheXdslLineConfExtnProfileControl 3 }

		
		sheXdslLineConfExtnProfileControlTimer OBJECT-TYPE
			SYNTAX Gauge32
			MAX-ACCESS read-only
			STATUS current
			DESCRIPTION
				"The maximum wait time for the manager for a long running user command. 
				"
			::= { sheXdslLineConfExtnProfileControl 4 }

		
		sheXdslLineConfExtnProfileControlReqResult OBJECT-TYPE
			SYNTAX SheXdslControlRequestResultType
			MAX-ACCESS read-only
			STATUS current
			DESCRIPTION
				"The result of the last user command."
			::= { sheXdslLineConfExtnProfileControl 5 }

		
		sheXdslLineConfExtnProfileControlTimeStamp OBJECT-TYPE
			SYNTAX Unsigned32
			UNITS "sec"
			MAX-ACCESS read-only
			STATUS current
			DESCRIPTION
				"The time stamp of the last command (end of command)."
			::= { sheXdslLineConfExtnProfileControl 6 }

		
		sheXdslLineConfExtnProfileControlDownBitSwap OBJECT-TYPE
			SYNTAX SheXdslEnableType
			MAX-ACCESS read-write
			STATUS current
			DESCRIPTION
				"look at table"
			::= { sheXdslLineConfExtnProfileControl 7 }

		
		sheXdslLineConfExtnProfileControlUpBitSwap OBJECT-TYPE
			SYNTAX SheXdslEnableType
			MAX-ACCESS read-write
			STATUS current
			DESCRIPTION
				"look at table"
			::= { sheXdslLineConfExtnProfileControl 8 }

		
		sheXdslLineConfExtnProfileControlDownPboEsel OBJECT-TYPE
			SYNTAX Unsigned32 (0..511)
			UNITS "0.5dB"
			MAX-ACCESS read-write
			STATUS current
			DESCRIPTION
				"look at table"
			::= { sheXdslLineConfExtnProfileControl 9 }

		
		sheXdslLineConfExtnProfileControlDownPboMus OBJECT-TYPE
			SYNTAX Unsigned32 (0..255)
			UNITS "0.5 dBm/Hz"
			MAX-ACCESS read-write
			STATUS current
			DESCRIPTION
				"look at table"
			::= { sheXdslLineConfExtnProfileControl 10 }

		
		sheXdslLineConfExtnProfileControlDownPboFMin OBJECT-TYPE
			SYNTAX Unsigned32 (0..2048)
			MAX-ACCESS read-write
			STATUS current
			DESCRIPTION
				"look at table"
			::= { sheXdslLineConfExtnProfileControl 11 }

		
		sheXdslLineConfExtnProfileControlDownPboFMax OBJECT-TYPE
			SYNTAX Unsigned32 (32..4095)
			MAX-ACCESS read-write
			STATUS current
			DESCRIPTION
				"look at table"
			::= { sheXdslLineConfExtnProfileControl 12 }

		
		sheXdslLineConfExtnProfileControlXtucPwrMgmtL0Time OBJECT-TYPE
			SYNTAX INTEGER (0..255)
			MAX-ACCESS read-write
			STATUS current
			DESCRIPTION
				"This parameter represents the minimum time (in seconds)
				between an exit from the L2 state and the next entry into
				the L2 state. It ranges from 0 to 255 seconds."
			::= { sheXdslLineConfExtnProfileControl 13 }

		
		sheXdslLineConfExtnProfileControlXtucPwrMgmtL2Time OBJECT-TYPE
			SYNTAX INTEGER (0..255)
			MAX-ACCESS read-write
			STATUS current
			DESCRIPTION
				"This parameter represents the minimum time (in seconds)
				between an Entry into the L2 state and the first
				Power Trim in the L2 state and between two consecutive
				Power Trims in the L2 State. It ranges from 0 to 255 seconds."
			::= { sheXdslLineConfExtnProfileControl 14 }

		
		sheXdslLineConfExtnProfileControlXtucPwrMgmtL2ATPR OBJECT-TYPE
			SYNTAX INTEGER (0..31)
			UNITS "1dB"
			MAX-ACCESS read-write
			STATUS current
			DESCRIPTION
				"This parameter represents the maximum aggregate transmit power reduction (in dB)
				that can be performed through a single Power Trim in the L2 state."
			::= { sheXdslLineConfExtnProfileControl 15 }

		
		sheXdslLineConfExtnProfileControlXtucPwrMgmtMode OBJECT-TYPE
			SYNTAX SheXdslXtucPwrMgmtModeType
			MAX-ACCESS read-write
			STATUS current
			DESCRIPTION
				"Which DSL Power Management state is enabled.
				Currently powermanagment will not be supported by xdsl-lines."
			::= { sheXdslLineConfExtnProfileControl 17 }

		
		sheXdslLineConfExtnProfileControlUseCustomSubcarrierMask OBJECT-TYPE
			SYNTAX SheXdslEnableType
			MAX-ACCESS read-write
			STATUS current
			DESCRIPTION
				"look at table."
			::= { sheXdslLineConfExtnProfileControl 22 }

		
		sheXdslLineConfExtnProfileControlCustomSubcarrierMask OBJECT-TYPE
			SYNTAX OCTET STRING (SIZE (0..64))
			MAX-ACCESS read-write
			STATUS current
			DESCRIPTION
				"look at table."
			::= { sheXdslLineConfExtnProfileControl 23 }

		
		sheXdslLineConfExtnProfileControlXtucPwrMgmtL2ATPRT OBJECT-TYPE
			SYNTAX INTEGER (0..31)
			UNITS "1dB"
			MAX-ACCESS read-write
			STATUS current
			DESCRIPTION
				"look at table"
			::= { sheXdslLineConfExtnProfileControl 24 }

		
		sheXdslLineConfExtnProfileControlDownPboEpsd OBJECT-TYPE
			SYNTAX OCTET STRING (SIZE (64))
			MAX-ACCESS read-write
			STATUS current
			DESCRIPTION
				"look at table."
			::= { sheXdslLineConfExtnProfileControl 25 }

		
		sheXdslLineConfExtnProfileControlDownPboEScmA OBJECT-TYPE
			SYNTAX Unsigned32 (0..640)
			UNITS "2^-8"
			MAX-ACCESS read-write
			STATUS current
			DESCRIPTION
				"look at table."
			::= { sheXdslLineConfExtnProfileControl 26 }

		
		sheXdslLineConfExtnProfileControlDownPboEScmB OBJECT-TYPE
			SYNTAX Unsigned32 (0..640)
			UNITS "2^-8"
			MAX-ACCESS read-write
			STATUS current
			DESCRIPTION
				"look at table."
			::= { sheXdslLineConfExtnProfileControl 27 }

		
		sheXdslLineConfExtnProfileControlDownPboEScmC OBJECT-TYPE
			SYNTAX Unsigned32 (0..640)
			UNITS "2^-8"
			MAX-ACCESS read-write
			STATUS current
			DESCRIPTION
				"look at table."
			::= { sheXdslLineConfExtnProfileControl 28 }

		
		sheXdslLineConfExtnProfileControlUpPboA OBJECT-TYPE
			SYNTAX OCTET STRING (SIZE (10))
			UNITS "0.01 dBm/Hz"
			MAX-ACCESS read-write
			STATUS current
			DESCRIPTION
				"look at table."
			::= { sheXdslLineConfExtnProfileControl 29 }

		
		sheXdslLineConfExtnProfileControlUpPboB OBJECT-TYPE
			SYNTAX OCTET STRING (SIZE (10))
			UNITS "0.01 dBm/Hz"
			MAX-ACCESS read-write
			STATUS current
			DESCRIPTION
				"look at table."
			::= { sheXdslLineConfExtnProfileControl 30 }

		
		sheXdslLineConfExtnProfileControlMaxDownNomPsd OBJECT-TYPE
			SYNTAX Integer32 (-600..-300)
			UNITS "0.1 dBm/Hz"
			MAX-ACCESS read-write
			STATUS current
			DESCRIPTION
				"look at table."
			::= { sheXdslLineConfExtnProfileControl 31 }

		
		sheXdslLineConfExtnProfileControlMaxUpNomPsd OBJECT-TYPE
			SYNTAX Integer32 (-600..-300)
			UNITS "0.1 dBm/Hz"
			MAX-ACCESS read-write
			STATUS current
			DESCRIPTION
				"look at table."
			::= { sheXdslLineConfExtnProfileControl 32 }

		
		sheXdslLineConfExtnProfileControlDownPboEselMin OBJECT-TYPE
			SYNTAX Unsigned32 (0..512)
			UNITS "0.5dB"
			MAX-ACCESS read-write
			STATUS current
			DESCRIPTION
				"look at table"
			::= { sheXdslLineConfExtnProfileControl 33 }

		
		sheXdslLineConfExtnProfileControlDownPboMof OBJECT-TYPE
			SYNTAX Unsigned32 (0..255)
			UNITS "0.5 dBm/Hz"
			MAX-ACCESS read-write
			STATUS current
			DESCRIPTION
				"look at table
				
				
				NOTE:
				This parameter is not longer supported with R2.6 RP2."
			::= { sheXdslLineConfExtnProfileControl 34 }

		
		sheXdslLineConfExtnProfileControlUpPboKL OBJECT-TYPE
			SYNTAX Unsigned32 (0..1280)
			UNITS "0.1 dB"
			MAX-ACCESS read-write
			STATUS current
			DESCRIPTION
				"look at table."
			::= { sheXdslLineConfExtnProfileControl 36 }

		
		sheXdslLineConfExtnProfileControlUpPboKO OBJECT-TYPE
			SYNTAX SheXdslEnableType
			MAX-ACCESS read-write
			STATUS current
			DESCRIPTION
				"Look at table."
			::= { sheXdslLineConfExtnProfileControl 37 }

		
		sheXdslLineConfExtnProfileControlUpPboBoostMode OBJECT-TYPE
			SYNTAX SheXdslEnableType
			MAX-ACCESS read-write
			STATUS current
			DESCRIPTION
				"Look at table."
			::= { sheXdslLineConfExtnProfileControl 38 }

		
		sheXdslLineConfExtnProfileControlMsgMinUp OBJECT-TYPE
			SYNTAX Unsigned32 (4..248)
			UNITS "kbps"
			MAX-ACCESS read-write
			STATUS current
			DESCRIPTION
				"Look at table."
			::= { sheXdslLineConfExtnProfileControl 39 }

		
		sheXdslLineConfExtnProfileControlMsgMinDown OBJECT-TYPE
			SYNTAX Unsigned32 (4..248)
			UNITS "kbps"
			MAX-ACCESS read-write
			STATUS current
			DESCRIPTION
				"Look at table."
			::= { sheXdslLineConfExtnProfileControl 40 }

		
--  1.3.6.1.4.1.231.7.1.2.2.1.14.1.1.16.41
		sheXdslLineConfExtnProfileControlUsPsdMaskSelection OBJECT-TYPE
			SYNTAX SheXdslLineConfUsPSDMaskSelectionType
			MAX-ACCESS read-write
			STATUS current
			DESCRIPTION
				"This parameter is used only for annexes J and M of ITU-T Recs. G.992-3 and G.992.5.
				This configuration parameter defines which upstream PSD mask is enabled.
				"
			::= { sheXdslLineConfExtnProfileControl 41 }

		
		sheXdslLineConfExtnProfileControlCustomUsSubcarrierMask OBJECT-TYPE
			SYNTAX OCTET STRING (SIZE (0..64))
			MAX-ACCESS read-write
			STATUS current
			DESCRIPTION
				"look at table."
			::= { sheXdslLineConfExtnProfileControl 42 }

		
		sheXdslLineConfExtnProfileControlSnrModeDown OBJECT-TYPE
			SYNTAX SheXdslSnrModeType
			MAX-ACCESS read-write
			STATUS current
			DESCRIPTION
				"Look at table."
			::= { sheXdslLineConfExtnProfileControl 43 }

		
		sheXdslLineConfExtnProfileControlSnrModeUp OBJECT-TYPE
			SYNTAX SheXdslSnrModeType
			MAX-ACCESS read-write
			STATUS current
			DESCRIPTION
				"Look at table."
			::= { sheXdslLineConfExtnProfileControl 44 }

		
		sheXdslLineConfExtnProfileControlTxRefVnDown OBJECT-TYPE
			SYNTAX OCTET STRING (SIZE (0..128))
			MAX-ACCESS read-write
			STATUS current
			DESCRIPTION
				"Look at table."
			::= { sheXdslLineConfExtnProfileControl 45 }

		
		sheXdslLineConfExtnProfileControlTxRefVnUp OBJECT-TYPE
			SYNTAX OCTET STRING (SIZE (0..64))
			MAX-ACCESS read-write
			STATUS current
			DESCRIPTION
				"Look at table."
			::= { sheXdslLineConfExtnProfileControl 46 }

		
		sheXdslPsdMaskProfileTable OBJECT-TYPE
			SYNTAX SEQUENCE OF SheXdslPsdMaskProfileEntry
			MAX-ACCESS not-accessible
			STATUS current
			DESCRIPTION
				"Description."
			::= { sheXdslMibObjects 17 }

		
		sheXdslPsdMaskProfileEntry OBJECT-TYPE
			SYNTAX SheXdslPsdMaskProfileEntry
			MAX-ACCESS not-accessible
			STATUS current
			DESCRIPTION
				"Each entry describes a MIB based PSD mask.
				A downstream (usage) profile could support 32 breakpoints.
				A upstream profile could support 16 breakpoints."
			INDEX { sheXdslPsdMaskProfileIndex }
			::= { sheXdslPsdMaskProfileTable 1 }

		
		SheXdslPsdMaskProfileEntry ::=
			SEQUENCE { 
				sheXdslPsdMaskProfileIndex
					Unsigned32,
				sheXdslPsdMaskProfileName
					OCTET STRING,
				sheXdslPsdMaskProfileUsedBreakpoints
					Unsigned32,
				sheXdslPsdMaskProfileSubcarrierIndex01
					Unsigned32,
				sheXdslPsdMaskProfilePsdLevel01
					Unsigned32,
				sheXdslPsdMaskProfileSubcarrierIndex02
					Unsigned32,
				sheXdslPsdMaskProfilePsdLevel02
					Unsigned32,
				sheXdslPsdMaskProfileSubcarrierIndex03
					Unsigned32,
				sheXdslPsdMaskProfilePsdLevel03
					Unsigned32,
				sheXdslPsdMaskProfileSubcarrierIndex04
					Unsigned32,
				sheXdslPsdMaskProfilePsdLevel04
					Unsigned32,
				sheXdslPsdMaskProfileSubcarrierIndex05
					Unsigned32,
				sheXdslPsdMaskProfilePsdLevel05
					Unsigned32,
				sheXdslPsdMaskProfileSubcarrierIndex06
					Unsigned32,
				sheXdslPsdMaskProfilePsdLevel06
					Unsigned32,
				sheXdslPsdMaskProfileSubcarrierIndex07
					Unsigned32,
				sheXdslPsdMaskProfilePsdLevel07
					Unsigned32,
				sheXdslPsdMaskProfileSubcarrierIndex08
					Unsigned32,
				sheXdslPsdMaskProfilePsdLevel08
					Unsigned32,
				sheXdslPsdMaskProfileSubcarrierIndex09
					Unsigned32,
				sheXdslPsdMaskProfilePsdLevel09
					Unsigned32,
				sheXdslPsdMaskProfileSubcarrierIndex10
					Unsigned32,
				sheXdslPsdMaskProfilePsdLevel10
					Unsigned32,
				sheXdslPsdMaskProfileSubcarrierIndex11
					Unsigned32,
				sheXdslPsdMaskProfilePsdLevel11
					Unsigned32,
				sheXdslPsdMaskProfileSubcarrierIndex12
					Unsigned32,
				sheXdslPsdMaskProfilePsdLevel12
					Unsigned32,
				sheXdslPsdMaskProfileSubcarrierIndex13
					Unsigned32,
				sheXdslPsdMaskProfilePsdLevel13
					Unsigned32,
				sheXdslPsdMaskProfileSubcarrierIndex14
					Unsigned32,
				sheXdslPsdMaskProfilePsdLevel14
					Unsigned32,
				sheXdslPsdMaskProfileSubcarrierIndex15
					Unsigned32,
				sheXdslPsdMaskProfilePsdLevel15
					Unsigned32,
				sheXdslPsdMaskProfileSubcarrierIndex16
					Unsigned32,
				sheXdslPsdMaskProfilePsdLevel16
					Unsigned32,
				sheXdslPsdMaskProfileSubcarrierIndex17
					Unsigned32,
				sheXdslPsdMaskProfilePsdLevel17
					Unsigned32,
				sheXdslPsdMaskProfileSubcarrierIndex18
					Unsigned32,
				sheXdslPsdMaskProfilePsdLevel18
					Unsigned32,
				sheXdslPsdMaskProfileSubcarrierIndex19
					Unsigned32,
				sheXdslPsdMaskProfilePsdLevel19
					Unsigned32,
				sheXdslPsdMaskProfileSubcarrierIndex20
					Unsigned32,
				sheXdslPsdMaskProfilePsdLevel20
					Unsigned32,
				sheXdslPsdMaskProfileSubcarrierIndex21
					Unsigned32,
				sheXdslPsdMaskProfilePsdLevel21
					Unsigned32,
				sheXdslPsdMaskProfileSubcarrierIndex22
					Unsigned32,
				sheXdslPsdMaskProfilePsdLevel22
					Unsigned32,
				sheXdslPsdMaskProfileSubcarrierIndex23
					Unsigned32,
				sheXdslPsdMaskProfilePsdLevel23
					Unsigned32,
				sheXdslPsdMaskProfileSubcarrierIndex24
					Unsigned32,
				sheXdslPsdMaskProfilePsdLevel24
					Unsigned32,
				sheXdslPsdMaskProfileSubcarrierIndex25
					Unsigned32,
				sheXdslPsdMaskProfilePsdLevel25
					Unsigned32,
				sheXdslPsdMaskProfileSubcarrierIndex26
					Unsigned32,
				sheXdslPsdMaskProfilePsdLevel26
					Unsigned32,
				sheXdslPsdMaskProfileSubcarrierIndex27
					Unsigned32,
				sheXdslPsdMaskProfilePsdLevel27
					Unsigned32,
				sheXdslPsdMaskProfileSubcarrierIndex28
					Unsigned32,
				sheXdslPsdMaskProfilePsdLevel28
					Unsigned32,
				sheXdslPsdMaskProfileSubcarrierIndex29
					Unsigned32,
				sheXdslPsdMaskProfilePsdLevel29
					Unsigned32,
				sheXdslPsdMaskProfileSubcarrierIndex30
					Unsigned32,
				sheXdslPsdMaskProfilePsdLevel30
					Unsigned32,
				sheXdslPsdMaskProfileSubcarrierIndex31
					Unsigned32,
				sheXdslPsdMaskProfilePsdLevel31
					Unsigned32,
				sheXdslPsdMaskProfileSubcarrierIndex32
					Unsigned32,
				sheXdslPsdMaskProfilePsdLevel32
					Unsigned32,
				sheXdslPsdMaskProfileUsage
					SheXdslCustomePsdMaskProfileUsageType
			 }

		sheXdslPsdMaskProfileIndex OBJECT-TYPE
			SYNTAX Unsigned32 (1..100)
			MAX-ACCESS read-only
			STATUS current
			DESCRIPTION
				"Index for that PSDMaskProfile."
			::= { sheXdslPsdMaskProfileEntry 1 }

		
		sheXdslPsdMaskProfileName OBJECT-TYPE
			SYNTAX OCTET STRING (SIZE (1..32))
			MAX-ACCESS read-only
			STATUS current
			DESCRIPTION
				"A name for that profile. This name will be used for referencing the used profile in the lineextnprofile.
				This characters are not allowed:  space : ? and empty string."
			::= { sheXdslPsdMaskProfileEntry 2 }

		
		sheXdslPsdMaskProfileUsedBreakpoints OBJECT-TYPE
			SYNTAX Unsigned32 (0..32)
			MAX-ACCESS read-only
			STATUS current
			DESCRIPTION
				"Defines the number of used breakpoints by this profile. As described in g.997.1,
				a maximum set of 16 or 32 breakpoints could be defined for MIB based PDS mask's in
				downstream direction. In upstream direction a maximum set of 16 breakpoints will be supported.
				If less then maximum breakpoints will be defined, all used breakpoints should be configured
				in a continuous way, that means: use Index01-Index04 if 4 breakpoints will be set and not 
				Index01-Index03-Index11-Index32.  "
			::= { sheXdslPsdMaskProfileEntry 3 }

		
		sheXdslPsdMaskProfileSubcarrierIndex01 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 4 }

		
		sheXdslPsdMaskProfilePsdLevel01 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 5 }

		
		sheXdslPsdMaskProfileSubcarrierIndex02 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 6 }

		
		sheXdslPsdMaskProfilePsdLevel02 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 7 }

		
		sheXdslPsdMaskProfileSubcarrierIndex03 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 8 }

		
		sheXdslPsdMaskProfilePsdLevel03 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 9 }

		
		sheXdslPsdMaskProfileSubcarrierIndex04 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 10 }

		
		sheXdslPsdMaskProfilePsdLevel04 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 11 }

		
		sheXdslPsdMaskProfileSubcarrierIndex05 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 12 }

		
		sheXdslPsdMaskProfilePsdLevel05 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 13 }

		
		sheXdslPsdMaskProfileSubcarrierIndex06 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 14 }

		
		sheXdslPsdMaskProfilePsdLevel06 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 15 }

		
		sheXdslPsdMaskProfileSubcarrierIndex07 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 16 }

		
		sheXdslPsdMaskProfilePsdLevel07 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 17 }

		
		sheXdslPsdMaskProfileSubcarrierIndex08 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 18 }

		
		sheXdslPsdMaskProfilePsdLevel08 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 19 }

		
		sheXdslPsdMaskProfileSubcarrierIndex09 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 20 }

		
		sheXdslPsdMaskProfilePsdLevel09 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 21 }

		
		sheXdslPsdMaskProfileSubcarrierIndex10 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 22 }

		
		sheXdslPsdMaskProfilePsdLevel10 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 23 }

		
		sheXdslPsdMaskProfileSubcarrierIndex11 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 24 }

		
		sheXdslPsdMaskProfilePsdLevel11 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 25 }

		
		sheXdslPsdMaskProfileSubcarrierIndex12 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 26 }

		
		sheXdslPsdMaskProfilePsdLevel12 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 27 }

		
		sheXdslPsdMaskProfileSubcarrierIndex13 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 28 }

		
		sheXdslPsdMaskProfilePsdLevel13 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 29 }

		
		sheXdslPsdMaskProfileSubcarrierIndex14 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 30 }

		
		sheXdslPsdMaskProfilePsdLevel14 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 31 }

		
		sheXdslPsdMaskProfileSubcarrierIndex15 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 32 }

		
		sheXdslPsdMaskProfilePsdLevel15 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 33 }

		
		sheXdslPsdMaskProfileSubcarrierIndex16 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 34 }

		
		sheXdslPsdMaskProfilePsdLevel16 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 35 }

		
		sheXdslPsdMaskProfileSubcarrierIndex17 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 36 }

		
		sheXdslPsdMaskProfilePsdLevel17 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 37 }

		
		sheXdslPsdMaskProfileSubcarrierIndex18 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 38 }

		
		sheXdslPsdMaskProfilePsdLevel18 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 39 }

		
		sheXdslPsdMaskProfileSubcarrierIndex19 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 40 }

		
		sheXdslPsdMaskProfilePsdLevel19 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 41 }

		
		sheXdslPsdMaskProfileSubcarrierIndex20 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 42 }

		
		sheXdslPsdMaskProfilePsdLevel20 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 43 }

		
		sheXdslPsdMaskProfileSubcarrierIndex21 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 44 }

		
		sheXdslPsdMaskProfilePsdLevel21 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 45 }

		
		sheXdslPsdMaskProfileSubcarrierIndex22 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 46 }

		
		sheXdslPsdMaskProfilePsdLevel22 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 47 }

		
		sheXdslPsdMaskProfileSubcarrierIndex23 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 48 }

		
		sheXdslPsdMaskProfilePsdLevel23 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 49 }

		
		sheXdslPsdMaskProfileSubcarrierIndex24 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 50 }

		
		sheXdslPsdMaskProfilePsdLevel24 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 51 }

		
		sheXdslPsdMaskProfileSubcarrierIndex25 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 52 }

		
		sheXdslPsdMaskProfilePsdLevel25 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 53 }

		
		sheXdslPsdMaskProfileSubcarrierIndex26 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 54 }

		
		sheXdslPsdMaskProfilePsdLevel26 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 55 }

		
		sheXdslPsdMaskProfileSubcarrierIndex27 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 56 }

		
		sheXdslPsdMaskProfilePsdLevel27 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 57 }

		
		sheXdslPsdMaskProfileSubcarrierIndex28 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 58 }

		
		sheXdslPsdMaskProfilePsdLevel28 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 59 }

		
		sheXdslPsdMaskProfileSubcarrierIndex29 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 60 }

		
		sheXdslPsdMaskProfilePsdLevel29 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 61 }

		
		sheXdslPsdMaskProfileSubcarrierIndex30 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 62 }

		
		sheXdslPsdMaskProfilePsdLevel30 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 63 }

		
		sheXdslPsdMaskProfileSubcarrierIndex31 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 64 }

		
		sheXdslPsdMaskProfilePsdLevel31 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 65 }

		
		sheXdslPsdMaskProfileSubcarrierIndex32 OBJECT-TYPE
			SYNTAX Unsigned32 (0..4095 | 65535)
			MAX-ACCESS read-only
			STATUS current
			DESCRIPTION
				"Index of the subcarrier, where this breakpoint will be placed.
				If 0xffff, the index and the corresponding PsdLevel are not valid."
			DEFVAL { 65535 }
			::= { sheXdslPsdMaskProfileEntry 66 }

		
		sheXdslPsdMaskProfilePsdLevel32 OBJECT-TYPE
			SYNTAX Unsigned32 (0..195)
			UNITS "0.5 dBm/Hz"
			MAX-ACCESS read-only
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileEntry 67 }

		
		sheXdslPsdMaskProfileUsage OBJECT-TYPE
			SYNTAX SheXdslCustomePsdMaskProfileUsageType
			MAX-ACCESS read-only
			STATUS current
			DESCRIPTION
				"Type of usage custom psd mask profile for downstream or upstream direction.
				This parameter can only be set during profile creation!"
			DEFVAL { downstream }
			::= { sheXdslPsdMaskProfileEntry 68 }

		
		sheXdslPsdMaskProfileControl OBJECT IDENTIFIER ::= { sheXdslMibObjects 18 }

		
		sheXdslPsdMaskProfileControlRequest OBJECT-TYPE
			SYNTAX SheXdslControlRequestType
			MAX-ACCESS read-write
			STATUS current
			DESCRIPTION
				"createXdslPsdMaskProfile
				sheXdslPsdMaskProfileControlName
				sheXdslPsdMaskProfileControlUsage
				
				
				modifyXdslPsdMaskProfile
				sheXdslPsdMaskProfileControlIndex
				...
				
				deleteXdslPsdMaskProfile
				sheXdslPsdMaskProfileControlIndex
				
				
				"
			::= { sheXdslPsdMaskProfileControl 1 }

		
		sheXdslPsdMaskProfileControlIndex OBJECT-TYPE
			SYNTAX Unsigned32 (1..100)
			MAX-ACCESS read-write
			STATUS current
			DESCRIPTION
				"Index of the configured xdsl psdmask profile entry."
			::= { sheXdslPsdMaskProfileControl 2 }

		
		sheXdslPsdMaskProfileControlStatus OBJECT-TYPE
			SYNTAX SheControlStatusType
			MAX-ACCESS read-only
			STATUS current
			DESCRIPTION
				"The status of a user command. 
				"
			::= { sheXdslPsdMaskProfileControl 3 }

		
		sheXdslPsdMaskProfileControlTimer OBJECT-TYPE
			SYNTAX Gauge32
			MAX-ACCESS read-only
			STATUS current
			DESCRIPTION
				"The maximum wait time for the manager for a long running user command. 
				"
			::= { sheXdslPsdMaskProfileControl 4 }

		
		sheXdslPsdMaskProfileControlReqResult OBJECT-TYPE
			SYNTAX SheXdslControlRequestResultType
			MAX-ACCESS read-only
			STATUS current
			DESCRIPTION
				"The result of the last user command."
			::= { sheXdslPsdMaskProfileControl 5 }

		
		sheXdslPsdMaskProfileControlTimeStamp OBJECT-TYPE
			SYNTAX Unsigned32
			UNITS "sec"
			MAX-ACCESS read-only
			STATUS current
			DESCRIPTION
				"The time stamp of the last command (end of command)."
			::= { sheXdslPsdMaskProfileControl 6 }

		
		sheXdslPsdMaskProfileControlName OBJECT-TYPE
			SYNTAX OCTET STRING (SIZE (1..32))
			MAX-ACCESS read-write
			STATUS current
			DESCRIPTION
				"look at table"
			::= { sheXdslPsdMaskProfileControl 7 }

		
		sheXdslPsdMaskProfileControlUsedBreakpoints OBJECT-TYPE
			SYNTAX Unsigned32 (0..32)
			MAX-ACCESS read-write
			STATUS current
			DESCRIPTION
				"Defines the number of used breakpoints by this profile. As described in g.997.1,
				a maximum set of 16 or 32 breakpoints could be defined for MIB based PDS mask's.
				If less then maximum breakpoints will be defined, all used breakpoints should be configured
				in a consecutive way, that means: use Index01-Index04 if 4 breakpoints will be set and not 
				Index01-Index03-Index11-Index32."
			::= { sheXdslPsdMaskProfileControl 8 }

		
		sheXdslPsdMaskProfileControlSubcarrierIndex01 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 9 }

		
		sheXdslPsdMaskProfileControlPsdLevel01 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 10 }

		
		sheXdslPsdMaskProfileControlSubcarrierIndex02 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 11 }

		
		sheXdslPsdMaskProfileControlPsdLevel02 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 12 }

		
		sheXdslPsdMaskProfileControlSubcarrierIndex03 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 13 }

		
		sheXdslPsdMaskProfileControlPsdLevel03 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 14 }

		
		sheXdslPsdMaskProfileControlSubcarrierIndex04 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 15 }

		
		sheXdslPsdMaskProfileControlPsdLevel04 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 16 }

		
		sheXdslPsdMaskProfileControlSubcarrierIndex05 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 17 }

		
		sheXdslPsdMaskProfileControlPsdLevel05 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 18 }

		
		sheXdslPsdMaskProfileControlSubcarrierIndex06 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 19 }

		
		sheXdslPsdMaskProfileControlPsdLevel06 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 20 }

		
		sheXdslPsdMaskProfileControlSubcarrierIndex07 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 21 }

		
		sheXdslPsdMaskProfileControlPsdLevel07 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 22 }

		
		sheXdslPsdMaskProfileControlSubcarrierIndex08 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 23 }

		
		sheXdslPsdMaskProfileControlPsdLevel08 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 24 }

		
		sheXdslPsdMaskProfileControlSubcarrierIndex09 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 25 }

		
		sheXdslPsdMaskProfileControlPsdLevel09 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 26 }

		
		sheXdslPsdMaskProfileControlSubcarrierIndex10 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 27 }

		
		sheXdslPsdMaskProfileControlPsdLevel10 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 28 }

		
		sheXdslPsdMaskProfileControlSubcarrierIndex11 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 29 }

		
		sheXdslPsdMaskProfileControlPsdLevel11 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 30 }

		
		sheXdslPsdMaskProfileControlSubcarrierIndex12 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 31 }

		
		sheXdslPsdMaskProfileControlPsdLevel12 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 32 }

		
		sheXdslPsdMaskProfileControlSubcarrierIndex13 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 33 }

		
		sheXdslPsdMaskProfileControlPsdLevel13 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 34 }

		
		sheXdslPsdMaskProfileControlSubcarrierIndex14 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 35 }

		
		sheXdslPsdMaskProfileControlPsdLevel14 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 36 }

		
		sheXdslPsdMaskProfileControlSubcarrierIndex15 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 37 }

		
		sheXdslPsdMaskProfileControlPsdLevel15 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 38 }

		
		sheXdslPsdMaskProfileControlSubcarrierIndex16 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 39 }

		
		sheXdslPsdMaskProfileControlPsdLevel16 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 40 }

		
		sheXdslPsdMaskProfileControlSubcarrierIndex17 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 41 }

		
		sheXdslPsdMaskProfileControlPsdLevel17 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 42 }

		
		sheXdslPsdMaskProfileControlSubcarrierIndex18 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 43 }

		
		sheXdslPsdMaskProfileControlPsdLevel18 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 44 }

		
		sheXdslPsdMaskProfileControlSubcarrierIndex19 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 45 }

		
		sheXdslPsdMaskProfileControlPsdLevel19 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 46 }

		
		sheXdslPsdMaskProfileControlSubcarrierIndex20 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 47 }

		
		sheXdslPsdMaskProfileControlPsdLevel20 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 48 }

		
		sheXdslPsdMaskProfileControlSubcarrierIndex21 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 49 }

		
		sheXdslPsdMaskProfileControlPsdLevel21 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 50 }

		
		sheXdslPsdMaskProfileControlSubcarrierIndex22 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 51 }

		
		sheXdslPsdMaskProfileControlPsdLevel22 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 52 }

		
		sheXdslPsdMaskProfileControlSubcarrierIndex23 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 53 }

		
		sheXdslPsdMaskProfileControlPsdLevel23 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 54 }

		
		sheXdslPsdMaskProfileControlSubcarrierIndex24 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 55 }

		
		sheXdslPsdMaskProfileControlPsdLevel24 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 56 }

		
		sheXdslPsdMaskProfileControlSubcarrierIndex25 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 57 }

		
		sheXdslPsdMaskProfileControlPsdLevel25 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 58 }

		
		sheXdslPsdMaskProfileControlSubcarrierIndex26 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 59 }

		
		sheXdslPsdMaskProfileControlPsdLevel26 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 60 }

		
		sheXdslPsdMaskProfileControlSubcarrierIndex27 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 61 }

		
		sheXdslPsdMaskProfileControlPsdLevel27 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 62 }

		
		sheXdslPsdMaskProfileControlSubcarrierIndex28 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 63 }

		
		sheXdslPsdMaskProfileControlPsdLevel28 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 64 }

		
		sheXdslPsdMaskProfileControlSubcarrierIndex29 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 65 }

		
		sheXdslPsdMaskProfileControlPsdLevel29 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 66 }

		
		sheXdslPsdMaskProfileControlSubcarrierIndex30 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 67 }

		
		sheXdslPsdMaskProfileControlPsdLevel30 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 68 }

		
		sheXdslPsdMaskProfileControlSubcarrierIndex31 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 69 }

		
		sheXdslPsdMaskProfileControlPsdLevel31 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 70 }

		
		sheXdslPsdMaskProfileControlSubcarrierIndex32 OBJECT-TYPE
			SYNTAX Unsigned32 (0..4095 | 65535)
			MAX-ACCESS read-write
			STATUS current
			DESCRIPTION
				"Index of the subcarrier, where this breakpoint will be placed.
				If 0xffff, the index and the corresponding PsdLevel are not valid."
			::= { sheXdslPsdMaskProfileControl 71 }

		
		sheXdslPsdMaskProfileControlPsdLevel32 OBJECT-TYPE
			SYNTAX Unsigned32 (0..195)
			UNITS "0.5 dBm/Hz"
			MAX-ACCESS read-write
			STATUS current
			DESCRIPTION
				"The MIB PSD mask level shall be coded as an unsigned integer representing the 
				MIB PSD mask levels 0 dBm/Hz (coded as 0) to -97.5 dBm/Hz (coded as 195), 
				in steps of 0.5 dBm/Hz."
			::= { sheXdslPsdMaskProfileControl 72 }

		
		sheXdslPsdMaskProfileControlUsage OBJECT-TYPE
			SYNTAX SheXdslCustomePsdMaskProfileUsageType
			MAX-ACCESS read-write
			STATUS current
			DESCRIPTION
				"look at table."
			::= { sheXdslPsdMaskProfileControl 73 }

		
		sheXdslCustomNotchProfileTable OBJECT-TYPE
			SYNTAX SEQUENCE OF SheXdslCustomNotchProfileEntry
			MAX-ACCESS not-accessible
			STATUS current
			DESCRIPTION
				"Description."
			::= { sheXdslMibObjects 19 }

		
		sheXdslCustomNotchProfileEntry OBJECT-TYPE
			SYNTAX SheXdslCustomNotchProfileEntry
			MAX-ACCESS not-accessible
			STATUS current
			DESCRIPTION
				"Each entry describes a MIB based CustomNotch profile.
				
				NOTE:
				For G.992.5, this configuration parameter defines the subset of downstream PSD mask breakpoints,
				as specified in PSDMASKds, that shall be used to notch an RFI band. This subset consists of
				couples of consecutive subcarrier indices belonging to breakpoints: [ti; ti + 1], corresponding to the
				low level of the notch. The specific interpolation around these points is defined in the relevant
				Recommendations (e.g., G.992.5).
				The configured breakpoint’s in such a notch profile define only the low level subcarriers of the notch.
				The additional needed carriers and the psd level on these points will be evaluated from the NE
				according to the G992.5 recommendation. 
				
				For G.993.2, this configuration parameter defines the bands where the PSD shall be reduced as
				specified in § 7.2.1.2/G.993.2. Each band shall be represented by a start and stop subcarrier indices
				with a subcarrier spacing of 4.3125kHz. Up to 16 bands may be specified. This parameter defines
				the RFI bands for both upstream and downstream directions.
				
				"
			REFERENCE
				"g.997.1 chapter 7.3.1.2.10
				g.992.5 chapter 8.5.1 / figure 8-1"
			INDEX { sheXdslCustomNotchProfileIndex }
			::= { sheXdslCustomNotchProfileTable 1 }

		
		SheXdslCustomNotchProfileEntry ::=
			SEQUENCE { 
				sheXdslCustomNotchProfileIndex
					Unsigned32,
				sheXdslCustomNotchProfileName
					OCTET STRING,
				sheXdslCustomNotchProfileUsedNotches
					Unsigned32,
				sheXdslCustomNotchProfileStartIndex01
					Unsigned32,
				sheXdslCustomNotchProfileStopIndex01
					Unsigned32,
				sheXdslCustomNotchProfileStartIndex02
					Unsigned32,
				sheXdslCustomNotchProfileStopIndex02
					Unsigned32,
				sheXdslCustomNotchProfileStartIndex03
					Unsigned32,
				sheXdslCustomNotchProfileStopIndex03
					Unsigned32,
				sheXdslCustomNotchProfileStartIndex04
					Unsigned32,
				sheXdslCustomNotchProfileStopIndex04
					Unsigned32,
				sheXdslCustomNotchProfileStartIndex05
					Unsigned32,
				sheXdslCustomNotchProfileStopIndex05
					Unsigned32,
				sheXdslCustomNotchProfileStartIndex06
					Unsigned32,
				sheXdslCustomNotchProfileStopIndex06
					Unsigned32,
				sheXdslCustomNotchProfileStartIndex07
					Unsigned32,
				sheXdslCustomNotchProfileStopIndex07
					Unsigned32,
				sheXdslCustomNotchProfileStartIndex08
					Unsigned32,
				sheXdslCustomNotchProfileStopIndex08
					Unsigned32,
				sheXdslCustomNotchProfileStartIndex09
					Unsigned32,
				sheXdslCustomNotchProfileStopIndex09
					Unsigned32,
				sheXdslCustomNotchProfileStartIndex10
					Unsigned32,
				sheXdslCustomNotchProfileStopIndex10
					Unsigned32,
				sheXdslCustomNotchProfileStartIndex11
					Unsigned32,
				sheXdslCustomNotchProfileStopIndex11
					Unsigned32,
				sheXdslCustomNotchProfileStartIndex12
					Unsigned32,
				sheXdslCustomNotchProfileStopIndex12
					Unsigned32,
				sheXdslCustomNotchProfileStartIndex13
					Unsigned32,
				sheXdslCustomNotchProfileStopIndex13
					Unsigned32,
				sheXdslCustomNotchProfileStartIndex14
					Unsigned32,
				sheXdslCustomNotchProfileStopIndex14
					Unsigned32,
				sheXdslCustomNotchProfileStartIndex15
					Unsigned32,
				sheXdslCustomNotchProfileStopIndex15
					Unsigned32,
				sheXdslCustomNotchProfileStartIndex16
					Unsigned32,
				sheXdslCustomNotchProfileStopIndex16
					Unsigned32
			 }

		sheXdslCustomNotchProfileIndex OBJECT-TYPE
			SYNTAX Unsigned32 (1..100)
			MAX-ACCESS read-only
			STATUS current
			DESCRIPTION
				"Index for that sheXdslCustomNotchProfile."
			::= { sheXdslCustomNotchProfileEntry 1 }

		
		sheXdslCustomNotchProfileName OBJECT-TYPE
			SYNTAX OCTET STRING (SIZE (1..32))
			MAX-ACCESS read-only
			STATUS current
			DESCRIPTION
				"A name for that profile. This name will be used for referencing the used profile in the linetable.
				This characters are not allowed:  space : ? and empty string."
			::= { sheXdslCustomNotchProfileEntry 2 }

		
		sheXdslCustomNotchProfileUsedNotches OBJECT-TYPE
			SYNTAX Unsigned32 (0..16)
			MAX-ACCESS read-only
			STATUS current
			DESCRIPTION
				"Defines the number of used notches by this profile. A maximum set of 16 custom notches could be defined.
				If less then 16 will be defined, all used notches should be configured
				in a consecutive way, that means: use Index01-Index04 if 4 notches will be set and not 
				Index01-Index03-Index07-Index08.  
				
				Be aware, that the NE can handle only 16 notches per line at time. 
				If all free defined notches in this profile should be used, it is not allowed 
				to enable additional predefined notches from the RFIBandMask !! If such notches
				are already activ, it is not possible to assign a notchprofile to such a line 
				if the total amount of notches (RFIBand's + UsedNotches) is greater then 16. 
				"
			::= { sheXdslCustomNotchProfileEntry 3 }

		
		sheXdslCustomNotchProfileStartIndex01 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 4 }

		
		sheXdslCustomNotchProfileStopIndex01 OBJECT-TYPE
			SYNTAX Unsigned32 (0 | 1..4095)
			MAX-ACCESS read-only
			STATUS current
			DESCRIPTION
				"Index of the subcarrier, where this notch will stop. If 0, the notch is not valid."
			::= { sheXdslCustomNotchProfileEntry 5 }

		
		sheXdslCustomNotchProfileStartIndex02 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 6 }

		
		sheXdslCustomNotchProfileStopIndex02 OBJECT-TYPE
			SYNTAX Unsigned32 (0 | 1..4095)
			MAX-ACCESS read-only
			STATUS current
			DESCRIPTION
				"Index of the subcarrier, where this notch will stop. If 0, the notch is not valid."
			DEFVAL { 0 }
			::= { sheXdslCustomNotchProfileEntry 7 }

		
		sheXdslCustomNotchProfileStartIndex03 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 8 }

		
		sheXdslCustomNotchProfileStopIndex03 OBJECT-TYPE
			SYNTAX Unsigned32 (0 | 1..4095)
			MAX-ACCESS read-only
			STATUS current
			DESCRIPTION
				"Index of the subcarrier, where this notch will stop. If 0, the notch is not valid."
			DEFVAL { 0 }
			::= { sheXdslCustomNotchProfileEntry 9 }

		
		sheXdslCustomNotchProfileStartIndex04 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 10 }

		
		sheXdslCustomNotchProfileStopIndex04 OBJECT-TYPE
			SYNTAX Unsigned32 (0 | 1..4095)
			MAX-ACCESS read-only
			STATUS current
			DESCRIPTION
				"Index of the subcarrier, where this notch will stop. If 0, the notch is not valid."
			DEFVAL { 0 }
			::= { sheXdslCustomNotchProfileEntry 11 }

		
		sheXdslCustomNotchProfileStartIndex05 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 12 }

		
		sheXdslCustomNotchProfileStopIndex05 OBJECT-TYPE
			SYNTAX Unsigned32 (0 | 1..4095)
			MAX-ACCESS read-only
			STATUS current
			DESCRIPTION
				"Index of the subcarrier, where this notch will stop. If 0, the notch is not valid."
			DEFVAL { 0 }
			::= { sheXdslCustomNotchProfileEntry 13 }

		
		sheXdslCustomNotchProfileStartIndex06 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 14 }

		
		sheXdslCustomNotchProfileStopIndex06 OBJECT-TYPE
			SYNTAX Unsigned32 (0 | 1..4095)
			MAX-ACCESS read-only
			STATUS current
			DESCRIPTION
				"Index of the subcarrier, where this notch will stop. If 0, the notch is not valid."
			DEFVAL { 0 }
			::= { sheXdslCustomNotchProfileEntry 15 }

		
		sheXdslCustomNotchProfileStartIndex07 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 16 }

		
		sheXdslCustomNotchProfileStopIndex07 OBJECT-TYPE
			SYNTAX Unsigned32 (0 | 1..4095)
			MAX-ACCESS read-only
			STATUS current
			DESCRIPTION
				"Index of the subcarrier, where this notch will stop. If 0, the notch is not valid."
			DEFVAL { 0 }
			::= { sheXdslCustomNotchProfileEntry 17 }

		
		sheXdslCustomNotchProfileStartIndex08 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 18 }

		
		sheXdslCustomNotchProfileStopIndex08 OBJECT-TYPE
			SYNTAX Unsigned32 (0 | 1..4095)
			MAX-ACCESS read-only
			STATUS current
			DESCRIPTION
				"Index of the subcarrier, where this notch will stop. If 0, the notch is not valid."
			DEFVAL { 0 }
			::= { sheXdslCustomNotchProfileEntry 19 }

		
		sheXdslCustomNotchProfileStartIndex09 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 20 }

		
		sheXdslCustomNotchProfileStopIndex09 OBJECT-TYPE
			SYNTAX Unsigned32 (0 | 1..4095)
			MAX-ACCESS read-only
			STATUS current
			DESCRIPTION
				"Index of the subcarrier, where this notch will stop. If 0, the notch is not valid."
			::= { sheXdslCustomNotchProfileEntry 21 }

		
		sheXdslCustomNotchProfileStartIndex10 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 22 }

		
		sheXdslCustomNotchProfileStopIndex10 OBJECT-TYPE
			SYNTAX Unsigned32 (0 | 1..4095)
			MAX-ACCESS read-only
			STATUS current
			DESCRIPTION
				"Index of the subcarrier, where this notch will stop. If 0, the notch is not valid."
			::= { sheXdslCustomNotchProfileEntry 23 }

		
		sheXdslCustomNotchProfileStartIndex11 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 24 }

		
		sheXdslCustomNotchProfileStopIndex11 OBJECT-TYPE
			SYNTAX Unsigned32 (0 | 1..4095)
			MAX-ACCESS read-only
			STATUS current
			DESCRIPTION
				"Index of the subcarrier, where this notch will stop. If 0, the notch is not valid."
			::= { sheXdslCustomNotchProfileEntry 25 }

		
		sheXdslCustomNotchProfileStartIndex12 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 26 }

		
		sheXdslCustomNotchProfileStopIndex12 OBJECT-TYPE
			SYNTAX Unsigned32 (0 | 1..4095)
			MAX-ACCESS read-only
			STATUS current
			DESCRIPTION
				"Index of the subcarrier, where this notch will stop. If 0, the notch is not valid."
			::= { sheXdslCustomNotchProfileEntry 27 }

		
		sheXdslCustomNotchProfileStartIndex13 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 28 }

		
		sheXdslCustomNotchProfileStopIndex13 OBJECT-TYPE
			SYNTAX Unsigned32 (0 | 1..4095)
			MAX-ACCESS read-only
			STATUS current
			DESCRIPTION
				"Index of the subcarrier, where this notch will stop. If 0, the notch is not valid."
			::= { sheXdslCustomNotchProfileEntry 29 }

		
		sheXdslCustomNotchProfileStartIndex14 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 30 }

		
		sheXdslCustomNotchProfileStopIndex14 OBJECT-TYPE
			SYNTAX Unsigned32 (0 | 1..4095)
			MAX-ACCESS read-only
			STATUS current
			DESCRIPTION
				"Index of the subcarrier, where this notch will stop. If 0, the notch is not valid."
			::= { sheXdslCustomNotchProfileEntry 31 }

		
		sheXdslCustomNotchProfileStartIndex15 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 32 }

		
		sheXdslCustomNotchProfileStopIndex15 OBJECT-TYPE
			SYNTAX Unsigned32 (0 | 1..4095)
			MAX-ACCESS read-only
			STATUS current
			DESCRIPTION
				"Index of the subcarrier, where this notch will stop. If 0, the notch is not valid."
			::= { sheXdslCustomNotchProfileEntry 33 }

		
		sheXdslCustomNotchProfileStartIndex16 OBJECT-TYPE
			SYNTAX Unsigned32 (0 | 1..4095)
			MAX-ACCESS read-only
			STATUS current
			DESCRIPTION
				"Index of the subcarrier, where this notch will start. If 0, the notch is not valid."
			DEFVAL { 0 }
			::= { sheXdslCustomNotchProfileEntry 34 }

		
		sheXdslCustomNotchProfileStopIndex16 OBJECT-TYPE
			SYNTAX Unsigned32 (0 | 1..4095)
			MAX-ACCESS read-only
			STATUS current
			DESCRIPTION
				"Index of the subcarrier, where this notch will stop. If 0, the notch is not valid."
			::= { sheXdslCustomNotchProfileEntry 35 }

		
		sheXdslCustomNotchProfileControl OBJECT IDENTIFIER ::= { sheXdslMibObjects 20 }

		
		sheXdslCustomNotchProfileControlRequest OBJECT-TYPE
			SYNTAX SheXdslControlRequestType
			MAX-ACCESS read-write
			STATUS current
			DESCRIPTION
				"createXdslCustomNotchProfile
				sheXdslCustomNotchProfileControlName
				...
				
				modifyXdslCustomNotchProfile (not allowed if profile is assigned!)
				sheXdslCustomNotchProfileControlIndex
				...
				
				deleteXdslCustomNotchProfile
				sheXdslCustomNotchProfileControlIndex
				
				
				"
			::= { sheXdslCustomNotchProfileControl 1 }

		
		sheXdslCustomNotchProfileControlIndex OBJECT-TYPE
			SYNTAX Unsigned32 (1..100)
			MAX-ACCESS read-write
			STATUS current
			DESCRIPTION
				"Index of the configured xdsl psdmask profile entry."
			::= { sheXdslCustomNotchProfileControl 2 }

		
		sheXdslCustomNotchProfileControlStatus OBJECT-TYPE
			SYNTAX SheControlStatusType
			MAX-ACCESS read-only
			STATUS current
			DESCRIPTION
				"The status of a user command. 
				"
			::= { sheXdslCustomNotchProfileControl 3 }

		
		sheXdslCustomNotchProfileControlTimer OBJECT-TYPE
			SYNTAX Gauge32
			MAX-ACCESS read-only
			STATUS current
			DESCRIPTION
				"The maximum wait time for the manager for a long running user command. 
				"
			::= { sheXdslCustomNotchProfileControl 4 }

		
		sheXdslCustomNotchProfileControlReqResult OBJECT-TYPE
			SYNTAX SheXdslControlRequestResultType
			MAX-ACCESS read-only
			STATUS current
			DESCRIPTION
				"The result of the last user command."
			::= { sheXdslCustomNotchProfileControl 5 }

		
		sheXdslCustomNotchProfileControlTimeStamp OBJECT-TYPE
			SYNTAX Unsigned32
			UNITS "sec"
			MAX-ACCESS read-only
			STATUS current
			DESCRIPTION
				"The time stamp of the last command (end of command)."
			::= { sheXdslCustomNotchProfileControl 6 }

		
		sheXdslCustomNotchProfileControlName OBJECT-TYPE
			SYNTAX OCTET STRING (SIZE (1..32))
			MAX-ACCESS read-write
			STATUS current
			DESCRIPTION
				"look at table"
			::= { sheXdslCustomNotchProfileControl 7 }

		
		sheXdslCustomNotchProfileControlUsedNotches OBJECT-TYPE
			SYNTAX Unsigned32 (0..16)
			MAX-ACCESS read-write
			STATUS current
			DESCRIPTION
				"look at table."
			::= { sheXdslCustomNotchProfileControl 8 }

		
		sheXdslCustomNotchProfileControlStartIndex01 OBJECT-TYPE
			SYNTAX Unsigned32 (0 | 1..4095)
			MAX-ACCESS read-write
			STATUS current
			DESCRIPTION
				"look at table"
			::= { sheXdslCustomNotchProfileControl 9 }

		
		sheXdslCustomNotchProfileControlStopIndex01 OBJECT-TYPE
			SYNTAX Unsigned32 (0 | 1..4095)
			MAX-ACCESS read-write
			STATUS current
			DESCRIPTION
				"look at table"
			::= { sheXdslCustomNotchProfileControl 10 }

		
		sheXdslCustomNotchProfileControlStartIndex02 OBJECT-TYPE
			SYNTAX Unsigned32 (0 | 1..4095)
			MAX-ACCESS read-write
			STATUS current
			DESCRIPTION
				"look at table"
			::= { sheXdslCustomNotchProfileControl 11 }

		
		sheXdslCustomNotchProfileControlStopIndex02 OBJECT-TYPE
			SYNTAX Unsigned32 (0 | 1..4095)
			MAX-ACCESS read-write
			STATUS current
			DESCRIPTION
				"look at table"
			::= { sheXdslCustomNotchProfileControl 12 }

		
		sheXdslCustomNotchProfileControlStartIndex03 OBJECT-TYPE
			SYNTAX Unsigned32 (0 | 1..4095)
			MAX-ACCESS read-write
			STATUS current
			DESCRIPTION
				"look at table"
			::= { sheXdslCustomNotchProfileControl 13 }

		
		sheXdslCustomNotchProfileControlStopIndex03 OBJECT-TYPE
			SYNTAX Unsigned32 (0 | 1..4095)
			MAX-ACCESS read-write
			STATUS current
			DESCRIPTION
				"look at table"
			::= { sheXdslCustomNotchProfileControl 14 }

		
		sheXdslCustomNotchProfileControlStartIndex04 OBJECT-TYPE
			SYNTAX Unsigned32 (0 | 1..4095)
			MAX-ACCESS read-write
			STATUS current
			DESCRIPTION
				"look at table"
			::= { sheXdslCustomNotchProfileControl 15 }

		
		sheXdslCustomNotchProfileControlStopIndex04 OBJECT-TYPE
			SYNTAX Unsigned32 (0 | 1..4095)
			MAX-ACCESS read-write
			STATUS current
			DESCRIPTION
				"look at table"
			::= { sheXdslCustomNotchProfileControl 16 }

		
		sheXdslCustomNotchProfileControlStartIndex05 OBJECT-TYPE
			SYNTAX Unsigned32 (0 | 1..4095)
			MAX-ACCESS read-write
			STATUS current
			DESCRIPTION
				"look at table"
			::= { sheXdslCustomNotchProfileControl 17 }

		
		sheXdslCustomNotchProfileControlStopIndex05 OBJECT-TYPE
			SYNTAX Unsigned32 (0 | 1..4095)
			MAX-ACCESS read-write
			STATUS current
			DESCRIPTION
				"look at table"
			::= { sheXdslCustomNotchProfileControl 18 }

		
		sheXdslCustomNotchProfileControlStartIndex06 OBJECT-TYPE
			SYNTAX Unsigned32 (0 | 1..4095)
			MAX-ACCESS read-write
			STATUS current
			DESCRIPTION
				"look at table"
			::= { sheXdslCustomNotchProfileControl 19 }

		
		sheXdslCustomNotchProfileControlStopIndex06 OBJECT-TYPE
			SYNTAX Unsigned32 (0 | 1..4095)
			MAX-ACCESS read-write
			STATUS current
			DESCRIPTION
				"look at table"
			::= { sheXdslCustomNotchProfileControl 20 }

		
		sheXdslCustomNotchProfileControlStartIndex07 OBJECT-TYPE
			SYNTAX Unsigned32 (0 | 1..4095)
			MAX-ACCESS read-write
			STATUS current
			DESCRIPTION
				"look at table"
			::= { sheXdslCustomNotchProfileControl 21 }

		
		sheXdslCustomNotchProfileControlStopIndex07 OBJECT-TYPE
			SYNTAX Unsigned32 (0 | 1..4095)
			MAX-ACCESS read-write
			STATUS current
			DESCRIPTION
				"look at table"
			::= { sheXdslCustomNotchProfileControl 22 }

		
		sheXdslCustomNotchProfileControlStartIndex08 OBJECT-TYPE
			SYNTAX Unsigned32 (0 | 1..4095)
			MAX-ACCESS read-write
			STATUS current
			DESCRIPTION
				"look at table"
			::= { sheXdslCustomNotchProfileControl 23 }

		
		sheXdslCustomNotchProfileControlStopIndex08 OBJECT-TYPE
			SYNTAX Unsigned32 (0 | 1..4095)
			MAX-ACCESS read-write
			STATUS current
			DESCRIPTION
				"look at table"
			::= { sheXdslCustomNotchProfileControl 24 }

		
		sheXdslCustomNotchProfileControlStartIndex09 OBJECT-TYPE
			SYNTAX Unsigned32 (0 | 1..4095)
			MAX-ACCESS read-write
			STATUS current
			DESCRIPTION
				"look at table"
			::= { sheXdslCustomNotchProfileControl 25 }

		
		sheXdslCustomNotchProfileControlStopIndex09 OBJECT-TYPE
			SYNTAX Unsigned32 (0 | 1..4095)
			MAX-ACCESS read-write
			STATUS current
			DESCRIPTION
				"look at table"
			::= { sheXdslCustomNotchProfileControl 26 }

		
		sheXdslCustomNotchProfileControlStartIndex10 OBJECT-TYPE
			SYNTAX Unsigned32 (0 | 1..4095)
			MAX-ACCESS read-write
			STATUS current
			DESCRIPTION
				"look at table"
			::= { sheXdslCustomNotchProfileControl 27 }

		
		sheXdslCustomNotchProfileControlStopIndex10 OBJECT-TYPE
			SYNTAX Unsigned32 (0 | 1..4095)
			MAX-ACCESS read-write
			STATUS current
			DESCRIPTION
				"look at table"
			::= { sheXdslCustomNotchProfileControl 28 }

		
		sheXdslCustomNotchProfileControlStartIndex11 OBJECT-TYPE
			SYNTAX Unsigned32 (0 | 1..4095)
			MAX-ACCESS read-write
			STATUS current
			DESCRIPTION
				"look at table"
			::= { sheXdslCustomNotchProfileControl 29 }

		
		sheXdslCustomNotchProfileControlStopIndex11 OBJECT-TYPE
			SYNTAX Unsigned32 (0 | 1..4095)
			MAX-ACCESS read-write
			STATUS current
			DESCRIPTION
				"look at table"
			::= { sheXdslCustomNotchProfileControl 30 }

		
		sheXdslCustomNotchProfileControlStartIndex12 OBJECT-TYPE
			SYNTAX Unsigned32 (0 | 1..4095)
			MAX-ACCESS read-write
			STATUS current
			DESCRIPTION
				"look at table"
			::= { sheXdslCustomNotchProfileControl 31 }

		
		sheXdslCustomNotchProfileControlStopIndex12 OBJECT-TYPE
			SYNTAX Unsigned32 (0 | 1..4095)
			MAX-ACCESS read-write
			STATUS current
			DESCRIPTION
				"look at table"
			::= { sheXdslCustomNotchProfileControl 32 }

		
		sheXdslCustomNotchProfileControlStartIndex13 OBJECT-TYPE
			SYNTAX Unsigned32 (0 | 1..4095)
			MAX-ACCESS read-write
			STATUS current
			DESCRIPTION
				"look at table"
			::= { sheXdslCustomNotchProfileControl 33 }

		
		sheXdslCustomNotchProfileControlStopIndex13 OBJECT-TYPE
			SYNTAX Unsigned32 (0 | 1..4095)
			MAX-ACCESS read-write
			STATUS current
			DESCRIPTION
				"look at table"
			::= { sheXdslCustomNotchProfileControl 34 }

		
		sheXdslCustomNotchProfileControlStartIndex14 OBJECT-TYPE
			SYNTAX Unsigned32 (0 | 1..4095)
			MAX-ACCESS read-write
			STATUS current
			DESCRIPTION
				"look at table"
			::= { sheXdslCustomNotchProfileControl 35 }

		
		sheXdslCustomNotchProfileControlStopIndex14 OBJECT-TYPE
			SYNTAX Unsigned32 (0 | 1..4095)
			MAX-ACCESS read-write
			STATUS current
			DESCRIPTION
				"look at table"
			::= { sheXdslCustomNotchProfileControl 36 }

		
		sheXdslCustomNotchProfileControlStartIndex15 OBJECT-TYPE
			SYNTAX Unsigned32 (0 | 1..4095)
			MAX-ACCESS read-write
			STATUS current
			DESCRIPTION
				"look at table"
			::= { sheXdslCustomNotchProfileControl 37 }

		
		sheXdslCustomNotchProfileControlStopIndex15 OBJECT-TYPE
			SYNTAX Unsigned32 (0 | 1..4095)
			MAX-ACCESS read-write
			STATUS current
			DESCRIPTION
				"look at table"
			::= { sheXdslCustomNotchProfileControl 38 }

		
		sheXdslCustomNotchProfileControlStartIndex16 OBJECT-TYPE
			SYNTAX Unsigned32 (0 | 1..4095)
			MAX-ACCESS read-write
			STATUS current
			DESCRIPTION
				"look at table"
			::= { sheXdslCustomNotchProfileControl 39 }

		
		sheXdslCustomNotchProfileControlStopIndex16 OBJECT-TYPE
			SYNTAX Unsigned32 (0 | 1..4095)
			MAX-ACCESS read-write
			STATUS current
			DESCRIPTION
				"look at table"
			::= { sheXdslCustomNotchProfileControl 40 }

		
		sheXdslLineBandTable OBJECT-TYPE
			SYNTAX SEQUENCE OF SheXdslLineBandEntry
			MAX-ACCESS not-accessible
			STATUS current
			DESCRIPTION
				"Because some of the defined LineStatus-Parameters should be presented per
				used band, this table is needed for supporting also Vdsl2 systems. Where 
				adsl-systems use always one band per direction, Vdsl2 systems use a minimum
				of two bands per direction   
				"
			::= { sheXdslMibObjects 21 }

		
		sheXdslLineBandEntry OBJECT-TYPE
			SYNTAX SheXdslLineBandEntry
			MAX-ACCESS not-accessible
			STATUS current
			DESCRIPTION
				"Each entry contains information per used band. For a adsl-sytem, this table
				contains per line one entry per direction. A Vdsl2 system will contain a
				minimum of four entrys per line."
			INDEX { ifIndex, sheXdslLineBandDirection, sheXdslLineBandNumber }
			::= { sheXdslLineBandTable 1 }

		
		SheXdslLineBandEntry ::=
			SEQUENCE { 
				sheXdslLineBandDirection
					SheXdsl2LineDirectionType,
				sheXdslLineBandNumber
					SheXdslLineBandNumberType,
				sheXdslLineStatusLnAtten
					Unsigned32,
				sheXdslLineStatusSigAtten
					Unsigned32,
				sheXdslLineStatusSnrMargin
					Integer32
			 }

		sheXdslLineBandDirection OBJECT-TYPE
			SYNTAX SheXdsl2LineDirectionType
			MAX-ACCESS read-only
			STATUS current
			DESCRIPTION
				"Second index for that table.
				
				1 - downstream
				2 - upstream "
			::= { sheXdslLineBandEntry 1 }

		
		sheXdslLineBandNumber OBJECT-TYPE
			SYNTAX SheXdslLineBandNumberType
			MAX-ACCESS read-only
			STATUS current
			DESCRIPTION
				"Index of the used band on this line.
				band0 (1) will only be used on Vdsl2 lines if the optional band 0 is used (upstream only).
				band1 (2) will be used on adsl lines (US and DS) and Xdsl2 lines (US1 and DS1)
				band2 (3) and more will only be used on Vdsl2 lines (US2 and DS2...).
				
				"
			::= { sheXdslLineBandEntry 2 }

		
		sheXdslLineStatusLnAtten OBJECT-TYPE
			SYNTAX Unsigned32 (0..1270 | 1271 | 32768)
			UNITS "0.1 dB"
			MAX-ACCESS read-only
			STATUS current
			DESCRIPTION
				"The measured difference in the total power transmitted by the
				one xTU-x and the total power received by the other xTU-x over all subcarriers
				during diagnostics mode and initialization. It ranges from 0 to 1270 in units 
				of 0.1 dB (Physical values are 0 to 127 dB). Special recommendations (G992.3 or G993.2)
				can restrict the used value range in detail. 
				
				Note:
				A special value of 0x8000 (32768) means that the current line attenuation is not available
				(line not trained or band not used or measurement not finished).
				A special value of 1271 means that the current line attenuation is outOfRange for measurement.
				"
			REFERENCE
				"ITU-T G.997.1, paragraph 7.5.1.9 / 7.5.1.10"
			::= { sheXdslLineBandEntry 3 }

		
		sheXdslLineStatusSigAtten OBJECT-TYPE
			SYNTAX Unsigned32 (0..1270 | 1271 | 32768)
			UNITS "0.1 dB"
			MAX-ACCESS read-only
			STATUS current
			DESCRIPTION
				"The measured difference in the total power transmitted by the
				one xTU-x and the total power received by the other xTU-x over all subcarriers
				during Showtime. It ranges from 0 to 1270 in units of 0.1 dB (Physical values 
				are 0 to 127 dB). Special recommendations (G992.3 or G993.2) can restrict the used 
				value range in detail. 
				
				Note:
				A special value of 0x8000 (32768) means that the current signal attenuation is not available
				(line not trained or band not used or measurement not finished).
				A special value of 1271 means that the current signal attenuation is outOfRange for measurement.
				"
			REFERENCE
				"ITU-T G.997.1, paragraph 7.5.1.11  / 7.5.1.12"
			::= { sheXdslLineBandEntry 4 }

		
		sheXdslLineStatusSnrMargin OBJECT-TYPE
			SYNTAX Integer32 (-641 | -640..630 | 32768)
			UNITS "0.1 dB"
			MAX-ACCESS read-only
			STATUS current
			DESCRIPTION
				"SNR Margin per band is the maximum increase in dB of the noise power received at
				the xTU-x, such that the BER requirements are met for all bearer channels. It ranges
				from -640 to 630 in units of 0.1 dB (Physical values are -64 to 63 dB).
				Special recommendations (G992.3 or G993.2) can restrict the used value range in detail.
				
				Note:
				A value of 0x8000 (32768) means that the current line margin is not available
				(line not trained or band not used or measurement not finished).
				A special value of -641 means that the current line margin is outOfRange for measurement."
			REFERENCE
				"ITU-T G.997.1, paragraph 7.5.1.14 / 7.5.1.17"
			::= { sheXdslLineBandEntry 5 }

		
		sheXdslLineDeltStatusControl OBJECT IDENTIFIER ::= { sheXdslMibObjects 23 }

		
		sheXdslLineDeltStatusControlRequest OBJECT-TYPE
			SYNTAX SheXdslControlRequestType
			MAX-ACCESS read-write
			STATUS current
			DESCRIPTION
				"getXdslLineDeltResult:
				sheXdslLineDeltStatusControlIndex
				
				Result's will be presented in the following status tables.
				sheXdslSCGDnStatusTable
				sheXdslSCGUpStatusTable
				Also the controlgroup members for Delt-Result (GroupSize, Scale, Mtime) will be filled.
				
				Command will be rejected if no DELT was successfully runnig before on the
				requested interface.
				
				getXdslLineShowtimeStatusResult:
				sheXdslLineDeltStatusControlIndex
				
				Result's will be presented in the following status tables.
				sheXdslSCDnStatusTable
				sheXdslSCUpStatusTable
				sheXdslSCGDnStatusTable (no HLinxx)
				sheXdslSCGUpStatusTable (no Hlinxx)
				Also the controlgroup members for Showtime-Result (MRefPsd) will be filled.
				
				Command will be rejected if requested interface is not in Showtime state.
				"
			::= { sheXdslLineDeltStatusControl 1 }

		
		sheXdslLineDeltStatusControlIndex OBJECT-TYPE
			SYNTAX Unsigned32
			MAX-ACCESS read-write
			STATUS current
			DESCRIPTION
				"IfIndex of the xdsl-interface, where DELT was running before and the result data
				are requested. Result's will be presented in the following status tables.
				sheXdslSCDnStatusTable
				sheXdslSCUpStatusTable
				sheXdslSCGDnStatusTable
				sheXdslSCGUpStatusTable"
			::= { sheXdslLineDeltStatusControl 2 }

		
		sheXdslLineDeltStatusControlStatus OBJECT-TYPE
			SYNTAX SheControlStatusType
			MAX-ACCESS read-only
			STATUS current
			DESCRIPTION
				"The status of a user command. 
				"
			::= { sheXdslLineDeltStatusControl 3 }

		
		sheXdslLineDeltStatusControlTimer OBJECT-TYPE
			SYNTAX Gauge32
			MAX-ACCESS read-only
			STATUS current
			DESCRIPTION
				"The maximum wait time for the manager for a long running user command."
			::= { sheXdslLineDeltStatusControl 4 }

		
		sheXdslLineDeltStatusControlReqResult OBJECT-TYPE
			SYNTAX SheXdslControlRequestResultType
			MAX-ACCESS read-only
			STATUS current
			DESCRIPTION
				"The result of the last user command."
			::= { sheXdslLineDeltStatusControl 5 }

		
		sheXdslLineDeltStatusControlTimeStamp OBJECT-TYPE
			SYNTAX Unsigned32
			UNITS "sec"
			MAX-ACCESS read-only
			STATUS current
			DESCRIPTION
				"The time stamp of the last command (end of command)."
			::= { sheXdslLineDeltStatusControl 6 }

		
		sheXdslLineDeltStatusControlSCGDnGroupSize OBJECT-TYPE
			SYNTAX SheXdslLineDeltStatusSCGGroupSizeType
			MAX-ACCESS read-only
			STATUS current
			DESCRIPTION
				"The number of subcarriers in one subcarrier-group shall be equal to the highest
				power of 2 not greather than ceil((maxUsedCarrier+1)/512), where maxUsedCarrier
				is the index of the highest frequency subcarrier such that all higher-index
				subcarriers either have a channel characteristic Hlog lower than -96 dB or do not
				 belong to the passband.
				Valid values are 1, 2, 4 or 8.
				0 means notAvailable.
				
				This parameter is the number of subcarriers per group used to report SNRpsds."
			REFERENCE
				"ITU-T G.997.1 chapter 7.5.2.28.2"
			::= { sheXdslLineDeltStatusControl 7 }

		
		sheXdslLineDeltStatusControlSCGUpGroupSize OBJECT-TYPE
			SYNTAX SheXdslLineDeltStatusSCGGroupSizeType
			MAX-ACCESS read-only
			STATUS current
			DESCRIPTION
				"The number of subcarriers in one subcarrier-group shall be equal to the highest
				power of 2 not greather than ceil((maxUsedCarrier+1)/512), where maxUsedCarrier
				is the index of the highest frequency subcarrier such that all higher-index
				subcarriers either have a channel characteristic Hlog lower than -96 dB or do not
				 belong to the passband.
				Valid values are 1, 2, 4 or 8.
				0 means notAvailable.
				
				This parameter is the number of subcarriers per group used to report SNRpsus."
			REFERENCE
				"ITU-T G.997.1 chapter 7.5.2.28.5 "
			::= { sheXdslLineDeltStatusControl 8 }

		
		sheXdslLineDeltStatusControlSCGDnSnrMtime OBJECT-TYPE
			SYNTAX Unsigned32 (0 | 1..65535)
			UNITS "symbols"
			MAX-ACCESS read-only
			STATUS current
			DESCRIPTION
				"SNR Measurement Time.  The number of symbols used to
				measure the SNR values on the respective transmission
				direction.  It should correspond to the value specified in the
				recommendation (e.g., the number of symbols in 1 second
				time interval).  This parameter corresponds to 1 second in loop
				diagnostic procedure and should be updated otherwise.
				
				This information is only available, if DELT was running and result data are requested
				from a single line.0 means not available."
			REFERENCE
				"ITU-T G.997.1, paragraph 7.5.1.20.1 (SNRMTds)"
			::= { sheXdslLineDeltStatusControl 9 }

		
		sheXdslLineDeltStatusControlSCGUpSnrMtime OBJECT-TYPE
			SYNTAX Unsigned32 (0 | 1..65535)
			UNITS "symbols"
			MAX-ACCESS read-only
			STATUS current
			DESCRIPTION
				"SNR Measurement Time.  The number of symbols used to
				measure the SNR values on the respective transmission
				direction.  It should correspond to the value specified in the
				recommendation (e.g., the number of symbols in 1 second
				time interval).  This parameter corresponds to 1 second in loop
				diagnostic procedure and should be updated otherwise.
				
				This information is only available, if DELT was running and result data are requested
				from a single line.0 means not available."
			REFERENCE
				"ITU-T G.997.1, paragraph 7.5.1.20.3 (SNRMTus)"
			::= { sheXdslLineDeltStatusControl 10 }

		
		sheXdslLineDeltStatusControlSCGDnLinScale OBJECT-TYPE
			SYNTAX Unsigned32 (0 | 1..65535)
			MAX-ACCESS read-only
			STATUS current
			DESCRIPTION
				"The scale factor to be applied to the H(f) linear
				representation values for the respective transmission direction.
				
				This information is only available, if DELT was running and result data are requested
				from a single line.0 means not available."
			REFERENCE
				"ITU-T G.997.1, paragraph 7.5.1.18.1 (HLINSCds)"
			::= { sheXdslLineDeltStatusControl 11 }

		
		sheXdslLineDeltStatusControlSCGUpLinScale OBJECT-TYPE
			SYNTAX Unsigned32 (0 | 1..65535)
			MAX-ACCESS read-only
			STATUS current
			DESCRIPTION
				"The scale factor to be applied to the H(f) linear
				representation values for the respective transmission direction.
				
				This information is only available, if DELT was running and result data are requested
				from a single line.0 means not available."
			REFERENCE
				"ITU-T G.997.1, paragraph 7.5.1.18.5 (HLINSCus)"
			::= { sheXdslLineDeltStatusControl 12 }

		
		sheXdslLineDeltStatusControlSCGDnHLogMtime OBJECT-TYPE
			SYNTAX Unsigned32 (0 | 1..65535)
			UNITS "symbols"
			MAX-ACCESS read-only
			STATUS current
			DESCRIPTION
				"The number of symbols used to measure the H(f) logarithmic measurement values
				for the respective transmission direction.
				This parameter should correspond to the value specified in the recommendation
				(e.g., the number of symbols in 1 second time interval).
				This parameter corresponds to 1 second in loop diagnostic procedure and should be updated in
				initialization
				
				This information is only available, if DELT was running and result data are requested
				from a single line.0 means not available."
			REFERENCE
				"ITU-T G.997.1, paragraph 7.5.1.18.3 (HLOGMTds)"
			::= { sheXdslLineDeltStatusControl 13 }

		
		sheXdslLineDeltStatusControlSCGUpHLogMtime OBJECT-TYPE
			SYNTAX Unsigned32 (0 | 1..65535)
			UNITS "symbols"
			MAX-ACCESS read-only
			STATUS current
			DESCRIPTION
				"The number of symbols used to measure the H(f) logarithmic measurement values
				for the respective transmission direction.
				This parameter should correspond to the value specified in the recommendation
				(e.g., the number of symbols in 1 second time interval).
				This parameter corresponds to 1 second in loop diagnostic procedure and should be updated in
				initialization
				
				This information is only available, if DELT was running and result data are requested
				from a single line.0 means not available."
			REFERENCE
				"ITU-T G.997.1, paragraph 7.5.1.18.7 (HLOGMTus)"
			::= { sheXdslLineDeltStatusControl 14 }

		
		sheXdslLineDeltStatusControlSCGDnQlnMtime OBJECT-TYPE
			SYNTAX Unsigned32 (0 | 1..65535)
			UNITS "symbols"
			MAX-ACCESS read-only
			STATUS current
			DESCRIPTION
				"The number of symbols used to measure the Quiet Line Noise values on the
				respective transmission direction.
				This parameter should correspond to the value specified in the recommendation
				(e.g., the number of symbols in 1 second time interval).
				This parameter corresponds to 1 second in loop diagnostic procedure and 
				should be updated in initialization.
				
				This information is only available, if DELT was running and result data are requested
				from a single line.0 means not available."
			REFERENCE
				"ITU-T G.997.1, paragraph 7.5.1.19.1 (QLNMTds)"
			::= { sheXdslLineDeltStatusControl 15 }

		
		sheXdslLineDeltStatusControlSCGUpQlnMtime OBJECT-TYPE
			SYNTAX Unsigned32 (0 | 1..65535)
			UNITS "symbols"
			MAX-ACCESS read-only
			STATUS current
			DESCRIPTION
				"The number of symbols used to measure the Quiet Line Noise values on the
				respective transmission direction.
				This parameter should correspond to the value specified in the recommendation
				(e.g., the number of symbols in 1 second time interval).
				This parameter corresponds to 1 second in loop diagnostic procedure and 
				should be updated in initialization.
				
				This information is only available, if DELT was running and result data are requested
				from a single line. 0 means not available."
			REFERENCE
				"ITU-T G.997.1, paragraph 7.5.1.19.3 (QLNMTus)"
			::= { sheXdslLineDeltStatusControl 16 }

		
		sheXdslShowtimeStatusMRefPsdDs OBJECT-TYPE
			SYNTAX OCTET STRING (SIZE (0..192))
			MAX-ACCESS read-only
			STATUS current
			DESCRIPTION
				"This parameter shall contain the set of breakpoints exchanged in the MREFPSDds fields of the OPRM
				message of G.993.2. 
				Each breakpoint shall consist of a subcarrier index t and a MIB PSD mask level (expressed in dBm/Hz)
				at that subcarrier (four octets). The set of breakpoints can then be represented as [(t1, PSD1),
				(t2, PSD2),..., (tN, PSDN)]. 
				The subcarrier index shall be coded as an unsigned integer (two octets)
				representing the range from 0..4093.
				The MIB PSD mask level shall be coded as an unsigned integer (two octet) representing the 
				MIB PSD mask levels in steps of 0.1dB with an offset of -140dBm/Hz.
				
				For example, a breakpoint value (t1,PSD1) of '04000320' means:
				PSD of 0x320 × 0.1 - 140 = -60 dBm/Hz on sub-carrier index 0x400 = 1024.
				
				The effective range for MRefPSD is -95..-35 dBM/Hz where given MIB value is 450..1050.
				The maximum number of breakpoints is 48.
				
				Only valid for lines running mode VDSL2 and if the line has reached Showtime state.
				Value could be requested with getXdslLineShowtimeStatusResult command."
			REFERENCE
				"ITU-T G.997.1, paragraph 7.5.1.29.7 (MREFPSDds) and paragraph 12.2.4.2.1.1 of G.993.2."
			::= { sheXdslLineDeltStatusControl 17 }

		
		sheXdslShowtimeStatusMRefPsdUs OBJECT-TYPE
			SYNTAX OCTET STRING (SIZE (0..128))
			MAX-ACCESS read-only
			STATUS current
			DESCRIPTION
				"This parameter shall contain the set of breakpoints exchanged in the MREFPSDus fields of the OPRM
				message of G.993.2. 
				Each breakpoint shall consist of a subcarrier index t and a MIB PSD mask level (expressed in dBm/Hz)
				at that subcarrier (four octets). The set of breakpoints can then be represented as [(t1, PSD1),
				(t2, PSD2),..., (tN, PSDN)]. 
				The subcarrier index shall be coded as an unsigned integer (two octets)
				representing the range from 0..4093.
				The MIB PSD mask level shall be coded as an unsigned integer (two octet) representing the 
				MIB PSD mask levels in steps of 0.1dB with an offset of -140dBm/Hz.
				
				For example, a breakpoint value (t1,PSD1) of '04000320' means:
				PSD of 0x320 × 0.1 - 140 = -60 dBm/Hz on sub-carrier index 0x400 = 1024.
				
				The effective range for MRefPSD is -95..-35 dBM/Hz where given MIB value is 450..1050.
				The maximum number of breakpoints is 32.
				
				Only valid for lines running mode VDSL2 and if the line has reached Showtime state.
				Value could be requested with getXdslLineShowtimeStatusResult command."
			REFERENCE
				"ITU-T G.997.1, paragraph 7.5.1.29.8 (MREFPSDus) and paragraph 12.2.4.2.1.1 of G.993.2."
			::= { sheXdslLineDeltStatusControl 18 }

		
		sheXdslLineDeltStatusControlSCGDnGroupSizeHLin OBJECT-TYPE
			SYNTAX SheXdslLineDeltStatusSCGGroupSizeType
			MAX-ACCESS read-only
			STATUS current
			DESCRIPTION
				"The number of subcarriers in one subcarrier-group shall be equal to the highest
				power of 2 not greather than ceil((maxUsedCarrier+1)/512), where maxUsedCarrier
				is the index of the highest frequency subcarrier such that all higher-index
				subcarriers either have a channel characteristic Hlog lower than -96 dB or do not
				 belong to the passband.
				Valid values are 1, 2, 4 or 8.
				0 means notAvailable.
				
				
				This parameter is the number of subcarriers per group used to report HLINpsds."
			REFERENCE
				"ITU-T G.997.1 chapter 7.5.2.26.2"
			::= { sheXdslLineDeltStatusControl 19 }

		
		sheXdslLineDeltStatusControlSCGUpGroupSizeHLin OBJECT-TYPE
			SYNTAX SheXdslLineDeltStatusSCGGroupSizeType
			MAX-ACCESS read-only
			STATUS current
			DESCRIPTION
				"The number of subcarriers in one subcarrier-group shall be equal to the highest
				power of 2 not greather than ceil((maxUsedCarrier+1)/512), where maxUsedCarrier
				is the index of the highest frequency subcarrier such that all higher-index
				subcarriers either have a channel characteristic Hlog lower than -96 dB or do not
				 belong to the passband.
				Valid values are 1, 2, 4 or 8.
				0 means notAvailable.
				
				
				This parameter is the number of subcarriers per group used to report HLINpsus."
			REFERENCE
				"ITU-T G.997.1 chapter 7.5.2.26.8"
			::= { sheXdslLineDeltStatusControl 20 }

		
		sheXdslLineDeltStatusControlSCGDnGroupSizeHLog OBJECT-TYPE
			SYNTAX SheXdslLineDeltStatusSCGGroupSizeType
			MAX-ACCESS read-only
			STATUS current
			DESCRIPTION
				"The number of subcarriers in one subcarrier-group shall be equal to the highest
				power of 2 not greather than ceil((maxUsedCarrier+1)/512), where maxUsedCarrier
				is the index of the highest frequency subcarrier such that all higher-index
				subcarriers either have a channel characteristic Hlog lower than -96 dB or do not
				 belong to the passband.
				Valid values are 1, 2, 4 or 8.
				0 means notAvailable.
				
				
				This parameter is the number of subcarriers per group used to report HLOGpsds."
			REFERENCE
				"ITU-T G.997.1 chapter 7.5.2.26.5 "
			::= { sheXdslLineDeltStatusControl 21 }

		
		sheXdslLineDeltStatusControlSCGUpGroupSizeHLog OBJECT-TYPE
			SYNTAX SheXdslLineDeltStatusSCGGroupSizeType
			MAX-ACCESS read-only
			STATUS current
			DESCRIPTION
				"The number of subcarriers in one subcarrier-group shall be equal to the highest
				power of 2 not greather than ceil((maxUsedCarrier+1)/512), where maxUsedCarrier
				is the index of the highest frequency subcarrier such that all higher-index
				subcarriers either have a channel characteristic Hlog lower than -96 dB or do not
				 belong to the passband.
				Valid values are 1, 2, 4 or 8.
				0 means notAvailable.
				
				
				This parameter is the number of subcarriers per group used to report HLOGpsus."
			REFERENCE
				"ITU-T G.997.1 chapter 7.5.2.26.11 "
			::= { sheXdslLineDeltStatusControl 22 }

		
		sheXdslLineDeltStatusControlSCGDnGroupSizeQln OBJECT-TYPE
			SYNTAX SheXdslLineDeltStatusSCGGroupSizeType
			MAX-ACCESS read-only
			STATUS current
			DESCRIPTION
				"The number of subcarriers in one subcarrier-group shall be equal to the highest
				power of 2 not greather than ceil((maxUsedCarrier+1)/512), where maxUsedCarrier
				is the index of the highest frequency subcarrier such that all higher-index
				subcarriers either have a channel characteristic Hlog lower than -96 dB or do not
				 belong to the passband.
				Valid values are 1, 2, 4 or 8.
				0 means notAvailable.
				
				
				This parameter is the number of subcarriers per group used to report QLNpsds."
			REFERENCE
				"ITU-T G.997.1 chapter 7.5.2.27.2"
			::= { sheXdslLineDeltStatusControl 23 }

		
		sheXdslLineDeltStatusControlSCGUpGroupSizeQln OBJECT-TYPE
			SYNTAX SheXdslLineDeltStatusSCGGroupSizeType
			MAX-ACCESS read-only
			STATUS current
			DESCRIPTION
				"The number of subcarriers in one subcarrier-group shall be equal to the highest
				power of 2 not greather than ceil((maxUsedCarrier+1)/512), where maxUsedCarrier
				is the index of the highest frequency subcarrier such that all higher-index
				subcarriers either have a channel characteristic Hlog lower than -96 dB or do not
				 belong to the passband.
				Valid values are 1, 2, 4 or 8.
				0 means notAvailable.
				
				
				This parameter is the number of subcarriers per group used to report QLNpsus."
			REFERENCE
				"ITU-T G.997.1 chapter 7.5.2.27.5"
			::= { sheXdslLineDeltStatusControl 24 }

		
--  info - IMPL: R2.7->
		sheXdslShowtimeStatusTssiDs OBJECT-TYPE
			SYNTAX OCTET STRING (SIZE (0..240))
			MAX-ACCESS read-only
			STATUS current
			DESCRIPTION
				"This parameter contains the downstream transmit spectrum shaping parameters expressed as the set
				of breakpoints exchanged during G.994.1.
				Each breakpoint shall consist of a subcarrier index t and a MIB PSD mask level at that
				subcarrier. The set of breakpoints can then be represented as [(t1, PSD1),
				(t2, PSD2),..., (tN, PSDN)].
				The subcarrier index shall be coded as an unsigned integer (two octets)
				representing the range from 0..511.
				The shaping parameter is an integer value in the 0 to 126 range. It is
				represented as a multiple of -0.5 dB. The value 126 should be interpreted as special value and means
				interpolation.
				
				The maximum number of breakpoints is 60.
				Only valid if lines runs in ADSL mode and showtime was reached."
			REFERENCE
				"ITU-T G.997.1, paragraph 7.5.1.29.5 (TSSpsds)"
			::= { sheXdslLineDeltStatusControl 25 }

		
--  info - IMPL: R2.7->
		sheXdslShowtimeStatusTssiUs OBJECT-TYPE
			SYNTAX OCTET STRING (SIZE (0..240))
			MAX-ACCESS read-only
			STATUS current
			DESCRIPTION
				"This parameter contains the upstream transmit spectrum shaping parameters expressed as the set
				of breakpoints exchanged during G.994.1.
				Each breakpoint shall consist of a subcarrier index t and a MIB PSD mask level at that
				subcarrier. The set of breakpoints can then be represented as [(t1, PSD1),
				(t2, PSD2),..., (tN, PSDN)].
				The subcarrier index shall be coded as an unsigned integer (two octets)
				representing the range from 0..511.
				The shaping parameter is an integer value in the 0 to 126 range. It is
				represented as a multiple of -0.5 dB. The value 126 should be interpreted as special value and means
				interpolation.
				
				The maximum number of breakpoints is 60.
				Only valid if lines runs in ADSL mode and showtime was reached."
			REFERENCE
				"ITU-T G.997.1, paragraph 7.5.1.29.6 (TSSpsus)"
			::= { sheXdslLineDeltStatusControl 26 }

		
		sheXdslSCDnStatusTable OBJECT-TYPE
			SYNTAX SEQUENCE OF SheXdslSCDnStatusEntry
			MAX-ACCESS not-accessible
			STATUS current
			DESCRIPTION
				"The table sheXdslSCDnStatusTable contains status parameters of xDSL sub-carriers
				for downstream direction.
				This table could only be requested for interfaces, which are in showtime state or
				after a successfull DELT run.
				The controlrequest commands 'getXdslLineDeltResult' or 'getXdslLineShowtimeStatusResult' are
				needed to send before, to fill these table for are requested interface."
			::= { sheXdslMibObjects 24 }

		
		sheXdslSCDnStatusEntry OBJECT-TYPE
			SYNTAX SheXdslSCDnStatusEntry
			MAX-ACCESS not-accessible
			STATUS current
			DESCRIPTION
				"The table sheXdslSCDnStatusEntry contains status parameters
				of xDSL2 sub-carriers for downstream direction.
				The index of this table is the real subcarrierIndex + 1 (real range 0..4095)."
			INDEX { sheXdslSCDnIndex }
			::= { sheXdslSCDnStatusTable 1 }

		
		SheXdslSCDnStatusEntry ::=
			SEQUENCE { 
				sheXdslSCDnIndex
					INTEGER,
				sheXdslSCDnStatusBitsAlloc
					INTEGER,
				sheXdslSCDnStatusGainAlloc
					INTEGER,
				sheXdslSCDnStatusTss
					INTEGER
			 }

		sheXdslSCDnIndex OBJECT-TYPE
			SYNTAX INTEGER (1..4096)
			MAX-ACCESS read-only
			STATUS current
			DESCRIPTION
				"The index of this table is the real subcarrierIndex + 1 (real range 0..4095) in downstream direction."
			::= { sheXdslSCDnStatusEntry 1 }

		
		sheXdslSCDnStatusBitsAlloc OBJECT-TYPE
			SYNTAX INTEGER (0..15)
			MAX-ACCESS read-only
			STATUS current
			DESCRIPTION
				"This parameter defines the downstream bits allocation table for a 
				particular sub-carrier. It is a integer values in the 0 to 15 range 
				for subcarriers 1 to NSCds"
			REFERENCE
				"ITU-T G.997.1, paragraph 7.5.1.29.1 (BITSpsds)
				"
			::= { sheXdslSCDnStatusEntry 2 }

		
		sheXdslSCDnStatusGainAlloc OBJECT-TYPE
			SYNTAX INTEGER (0..4093)
			UNITS "1/512"
			MAX-ACCESS read-only
			STATUS current
			DESCRIPTION
				"This parameter defines the downstream gains allocation table a 
				particular sub-carrier. It is a integer values in the 0 to 4093 range 
				for subcarriers 1 to NSCds. The gain value is represented as a 
				multiple of 1/512 on linear scale.
				"
			REFERENCE
				"ITU-T G.997.1, paragraph 7.5.1.29.3 (GAINSpsds)
				"
			::= { sheXdslSCDnStatusEntry 3 }

		
--  info - IMPL: <-R2.6 
		sheXdslSCDnStatusTss OBJECT-TYPE
			SYNTAX INTEGER (0..126 | 255)
			UNITS "-0.5 dB"
			MAX-ACCESS read-only
			STATUS obsolete
			DESCRIPTION
				"This parameter contains the downstream transmit spectrum shaping parameters expressed as the set
				of breakpoints exchanged during G.994.1. Each breakpoint consists of a subcarrier index and the
				associated shaping parameter. The shaping parameter is an integer value in the 0 to 126 range. It is
				represented as a multiple of -0.5 dB. 
				A special value (255) indicates that the subcarrier is not transmitted.
				Only valid if lines runs in ADSL mode."
			REFERENCE
				"ITU-T G.997.1, paragraph 7.5.1.29.5 (TSSpsds)"
			::= { sheXdslSCDnStatusEntry 4 }

		
		sheXdslSCUpStatusTable OBJECT-TYPE
			SYNTAX SEQUENCE OF SheXdslSCUpStatusEntry
			MAX-ACCESS not-accessible
			STATUS current
			DESCRIPTION
				"The table sheXdslSCDnStatusTable contains status parameters of xDSL sub-carriers
				for upstream direction.
				This table could only be requested for interfaces, which are in showtime state or
				after a successfull DELT run.
				The controlrequest commands 'getXdslLineDeltResult' or 'getXdslLineShowtimeStatusResult' are
				needed to send before, to fill these table for are requested interface."
			::= { sheXdslMibObjects 25 }

		
		sheXdslSCUpStatusEntry OBJECT-TYPE
			SYNTAX SheXdslSCUpStatusEntry
			MAX-ACCESS not-accessible
			STATUS current
			DESCRIPTION
				"The table sheXdslSCUpStatusEntry contains status parameters
				of xDSL2 sub-carriers for upstream direction.
				The index of this table is the real subcarrierIndex + 1 (real range 0..4095)."
			INDEX { sheXdslSCUpIndex }
			::= { sheXdslSCUpStatusTable 1 }

		
		SheXdslSCUpStatusEntry ::=
			SEQUENCE { 
				sheXdslSCUpIndex
					INTEGER,
				sheXdslSCUpStatusBitsAlloc
					INTEGER,
				sheXdslSCUpStatusGainAlloc
					INTEGER,
				sheXdslSCUpStatusTss
					INTEGER
			 }

		sheXdslSCUpIndex OBJECT-TYPE
			SYNTAX INTEGER (1..4096)
			MAX-ACCESS read-only
			STATUS current
			DESCRIPTION
				"The index of this table is the real subcarrierIndex + 1 (real range 0..4095) in upstream direction."
			::= { sheXdslSCUpStatusEntry 1 }

		
		sheXdslSCUpStatusBitsAlloc OBJECT-TYPE
			SYNTAX INTEGER (0..15)
			MAX-ACCESS read-only
			STATUS current
			DESCRIPTION
				"This parameter defines the upstream bits allocation table for a 
				particular sub-carrier. It is a integer values in the 0 to 15 range 
				for subcarriers 1 to NSCus"
			REFERENCE
				"ITU-T G.997.1, paragraph 7.5.1.29.2 (BITSpsus)"
			::= { sheXdslSCUpStatusEntry 2 }

		
		sheXdslSCUpStatusGainAlloc OBJECT-TYPE
			SYNTAX INTEGER (0..4093)
			UNITS "1/512"
			MAX-ACCESS read-only
			STATUS current
			DESCRIPTION
				"This parameter defines the upstream gains allocation table a 
				particular sub-carrier. It is a integer values in the 0 to 4093 range 
				for subcarriers 1 to NSCus. The gain value is represented as a 
				multiple of 1/512 on linear scale.
				"
			REFERENCE
				"ITU-T G.997.1, paragraph 7.5.1.29.4 (GAINSpsus)"
			::= { sheXdslSCUpStatusEntry 3 }

		
--  info - IMPL: <-R2.6
		sheXdslSCUpStatusTss OBJECT-TYPE
			SYNTAX INTEGER (0..126 | 255)
			UNITS "-0.5 dB"
			MAX-ACCESS read-only
			STATUS obsolete
			DESCRIPTION
				"This parameter contains the upstream transmit spectrum shaping parameters expressed as the set
				of breakpoints exchanged during G.994.1. Each breakpoint consists of a subcarrier index and the
				associated shaping parameter. The shaping parameter is an integer value in the 0 to 126 range. It is
				represented as a multiple of -0.5 dB. 
				A special value (255) indicates that the subcarrier is not transmitted.
				Only valid if lines runs in ADSL mode."
			REFERENCE
				"ITU-T G.997.1, paragraph 7.5.1.29.6 (TSSpsus)"
			::= { sheXdslSCUpStatusEntry 4 }

		
		sheXdslSCGDnStatusTable OBJECT-TYPE
			SYNTAX SEQUENCE OF SheXdslSCGDnStatusEntry
			MAX-ACCESS not-accessible
			STATUS current
			DESCRIPTION
				"The table sheXdslSCGDnStatusTable contains status parameters of xDSL sub-carriers groups
				for downstream direction.
				This table could only be requested for interfaces, which are in showtime state or
				after a successfull DELT run.
				The controlrequest commands 'getXdslLineDeltResult' or 'getXdslLineShowtimeStatusResult' are
				needed to send before, to fill these table for are requested interface."
			::= { sheXdslMibObjects 26 }

		
		sheXdslSCGDnStatusEntry OBJECT-TYPE
			SYNTAX SheXdslSCGDnStatusEntry
			MAX-ACCESS not-accessible
			STATUS current
			DESCRIPTION
				"The table sheXdslSCGDnStatusEntry contains status parameters
				of xDSL2 sub-carrier groups for downstream direction.
				The index of this table are the subcarrier group index."
			INDEX { sheXdslSCGDnIndex }
			::= { sheXdslSCGDnStatusTable 1 }

		
		SheXdslSCGDnStatusEntry ::=
			SEQUENCE { 
				sheXdslSCGDnIndex
					INTEGER,
				sheXdslSCGDnStatusSnr
					Unsigned32,
				sheXdslSCGDnStatusHLinReal
					Integer32,
				sheXdslSCGDnStatusHLinImg
					Integer32,
				sheXdslSCGDnStatusHLog
					Unsigned32,
				sheXdslSCGDnStatusQln
					Unsigned32
			 }

		sheXdslSCGDnIndex OBJECT-TYPE
			SYNTAX INTEGER (1..4096)
			MAX-ACCESS read-only
			STATUS current
			DESCRIPTION
				"The index of a used subcarrier group in downstream direction.
				"
			::= { sheXdslSCGDnStatusEntry 1 }

		
		sheXdslSCGDnStatusSnr OBJECT-TYPE
			SYNTAX Unsigned32 (0..255)
			UNITS "dB"
			MAX-ACCESS read-only
			STATUS current
			DESCRIPTION
				"This parameter is a real downstream SNR(f) values in dB. Represents 
				the SNR(f = i* f) value for a particular sub-carrier index i, ranging 
				from 1 to NSCds. The SNR(f) is represented as (  32 + snr(i)/2), 
				with snr(i) an 8 bit unsigned integer in the 0 to 254 range.
				A special value snr(i)=255 indicates that no measurement could be done for the 
				subcarrier because it is out of the passband or that the noise PSD is 
				out of range to be represented."
			REFERENCE
				"ITU-T G.997.1, paragraph 7.5.1.20.2 (SNRpsds)"
			::= { sheXdslSCGDnStatusEntry 4 }

		
		sheXdslSCGDnStatusHLinReal OBJECT-TYPE
			SYNTAX Integer32
			MAX-ACCESS read-only
			STATUS current
			DESCRIPTION
				"This parameter is the real part a(i) of the 2 16-bit 2's complement signed integers.   
				This parameter is a complex downstream Hlin(f) value in linear 
				scale. Represents the Hlin(f = i* f) value for a particular 
				sub-carrier index i, ranging from 1 to NSCds. The Hlin(f) is represented as 
				((scale/2^15)*((a(i)+j*b(i))/2^15)), where a(i) and b(i) 16-bit 2's 
				complement signed integers in the (-2^15 + 1) to (+2^15 - 1) range. 
				A special value a(i)=b(i)= -2^15 indicates that no measurement could be done for the 
				subcarrier because it is out of the passband or that the attenuation is out 
				of range to be represented. 
				This parameter is only available after a loop diagnostic procedure.
				"
			REFERENCE
				"ITU-T G.997.1, paragraph 7.5.1.18.2 (HLINpsds)"
			::= { sheXdslSCGDnStatusEntry 6 }

		
		sheXdslSCGDnStatusHLinImg OBJECT-TYPE
			SYNTAX Integer32
			MAX-ACCESS read-only
			STATUS current
			DESCRIPTION
				"This parameter is the imagened part b(i) of the 2 16-bit 2's complement signed integers.   
				This parameter is a complex downstream Hlin(f) value in linear 
				scale. Represents the Hlin(f = i* f) value for a particular 
				sub-carrier index i, ranging from 1 to NSCds. The Hlin(f) is represented as 
				((scale/2^15)*((a(i)+j*b(i))/2^15)), where a(i) and b(i) 16-bit 2's 
				complement signed integers in the (-2^15 + 1) to (+2^15 - 1) range. 
				A special value a(i)=b(i)= -2^15 indicates that no measurement could be done for the 
				subcarrier because it is out of the passband or that the attenuation is out 
				of range to be represented. 
				This parameter is only available after a loop diagnostic procedure.
				"
			REFERENCE
				"ITU-T G.997.1, paragraph 7.5.1.18.2 (HLINpsds)"
			::= { sheXdslSCGDnStatusEntry 7 }

		
		sheXdslSCGDnStatusHLog OBJECT-TYPE
			SYNTAX Unsigned32 (0..1023)
			UNITS "dB"
			MAX-ACCESS read-only
			STATUS current
			DESCRIPTION
				"This parameter is a real downstream Hlog(f) values in dB. Represents 
				the real Hlog(f = i* delta f) value for a particular sub-carrier index i, 
				ranging from 1 to NSCds. The real Hlog(f) value is represented as 
				(6-m(i)/10), with m(i) 10 bit unsigned integer in the 0 to 1022 range. 
				A special value m=1023 indicates that no measurement could be done for 
				the subcarrier because it is out of the passband or that the 
				attenuation is out of range to be represented."
			REFERENCE
				"ITU-T G.997.1, paragraph 7.5.1.18.4 (HLOGpsds)"
			::= { sheXdslSCGDnStatusEntry 9 }

		
		sheXdslSCGDnStatusQln OBJECT-TYPE
			SYNTAX Unsigned32 (0..255)
			UNITS "dBm/Hz"
			MAX-ACCESS read-only
			STATUS current
			DESCRIPTION
				"This parameter is a real downstream QLN(f) values in dBm/Hz. Represents 
				the QLN(f = i* delta f) value for a particular sub-carrier index i, ranging 
				from 1 to NSCds. The QLN(f) is represented as ( -23 -n(i)/2), with 
				n(i) an 8 bit unsigned integer in the 0 to 254 range. 
				A special value n(i)=255 indicates that no measurement could be done for the 
				subcarrier because it is out of the passband or that the noise PSD is 
				out of range to be represented.
				
				This parameter is applicable in loop diagnostic procedure and initialization.
				"
			REFERENCE
				"ITU-T G.997.1, paragraph 7.5.1.19.2 (QLNpsds)"
			::= { sheXdslSCGDnStatusEntry 11 }

		
		sheXdslSCGUpStatusTable OBJECT-TYPE
			SYNTAX SEQUENCE OF SheXdslSCGUpStatusEntry
			MAX-ACCESS not-accessible
			STATUS current
			DESCRIPTION
				"The table sheXdslSCGDnStatusTable contains status parameters of xDSL sub-carriers groups
				for upstream direction.
				This table could only be requested for interfaces, which are in showtime state or
				after a successfull DELT run.
				The controlrequest commands 'getXdslLineDeltResult' or 'getXdslLineShowtimeStatusResult' are
				needed to send before, to fill these table for are requested interface."
			::= { sheXdslMibObjects 27 }

		
		sheXdslSCGUpStatusEntry OBJECT-TYPE
			SYNTAX SheXdslSCGUpStatusEntry
			MAX-ACCESS not-accessible
			STATUS current
			DESCRIPTION
				"The table sheXdslSCGDnStatusEntry contains status parameters
				of xDSL2 sub-carrier groups for upstream direction.
				The index of this table are the subcarrier group index."
			INDEX { sheXdslSCGUpIndex }
			::= { sheXdslSCGUpStatusTable 1 }

		
		SheXdslSCGUpStatusEntry ::=
			SEQUENCE { 
				sheXdslSCGUpIndex
					INTEGER,
				sheXdslSCGUpStatusSnr
					Unsigned32,
				sheXdslSCGUpStatusHLinReal
					Integer32,
				sheXdslSCGUpStatusHLinImg
					Integer32,
				sheXdslSCGUpStatusHLog
					Unsigned32,
				sheXdslSCGUpStatusQln
					Unsigned32
			 }

		sheXdslSCGUpIndex OBJECT-TYPE
			SYNTAX INTEGER (1..4096)
			MAX-ACCESS read-only
			STATUS current
			DESCRIPTION
				"The index of a used subcarrier group in upstream direction.
				"
			::= { sheXdslSCGUpStatusEntry 1 }

		
		sheXdslSCGUpStatusSnr OBJECT-TYPE
			SYNTAX Unsigned32 (0..255)
			UNITS "dB"
			MAX-ACCESS read-only
			STATUS current
			DESCRIPTION
				"This parameter is a real upstream SNR(f) values in dB. Represents 
				the SNR(f = i* f) value for a particular sub-carrier index i, ranging 
				from 1 to NSCus. The SNR(f) is represented as (  32 + snr(i)/2), 
				with snr(i) an 8 bit unsigned integer in the 0 to 254 range.
				A special value snr(i)=255 indicates that no measurement could be done for the 
				subcarrier because it is out of the passband or that the noise PSD is 
				out of range to be represented."
			REFERENCE
				"ITU-T G.997.1, paragraph 7.5.1.20.4 (SNRpsus)"
			::= { sheXdslSCGUpStatusEntry 4 }

		
		sheXdslSCGUpStatusHLinReal OBJECT-TYPE
			SYNTAX Integer32
			MAX-ACCESS read-only
			STATUS current
			DESCRIPTION
				"This parameter is the real part a(i) of the 2 16-bit 2's complement signed integers.   
				This parameter is a complex upstream Hlin(f) value in linear 
				scale. Represents the Hlin(f = i* f) value for a particular 
				sub-carrier index i, ranging from 1 to NSCus. The Hlin(f) is represented as 
				((scale/2^15)*((a(i)+j*b(i))/2^15)), where a(i) and b(i) 16-bit 2's 
				complement signed integers in the (-2^15 + 1) to (+2^15 - 1) range. 
				A special value a(i)=b(i)= -2^15 indicates that no measurement could be done for the 
				subcarrier because it is out of the passband or that the attenuation is out 
				of range to be represented. 
				This parameter is only available after a loop diagnostic procedure.
				"
			REFERENCE
				"ITU-T G.997.1, paragraph 7.5.1.18.6 (HLINpsds)"
			::= { sheXdslSCGUpStatusEntry 6 }

		
		sheXdslSCGUpStatusHLinImg OBJECT-TYPE
			SYNTAX Integer32
			MAX-ACCESS read-only
			STATUS current
			DESCRIPTION
				"This parameter is the imagened part b(i) of the 2 16-bit 2's complement signed integers.   
				This parameter is a complex upstream Hlin(f) value in linear 
				scale. Represents the Hlin(f = i* f) value for a particular 
				sub-carrier index i, ranging from 1 to NSCus. The Hlin(f) is represented as 
				((scale/2^15)*((a(i)+j*b(i))/2^15)), where a(i) and b(i) 16-bit 2's 
				complement signed integers in the (-2^15 + 1) to (+2^15 - 1) range. 
				A special value a(i)=b(i)= -2^15 indicates that no measurement could be done for the 
				subcarrier because it is out of the passband or that the attenuation is out 
				of range to be represented. 
				This parameter is only available after a loop diagnostic procedure.
				"
			REFERENCE
				"ITU-T G.997.1, paragraph 7.5.1.18.6 (HLINpsds)"
			::= { sheXdslSCGUpStatusEntry 7 }

		
		sheXdslSCGUpStatusHLog OBJECT-TYPE
			SYNTAX Unsigned32 (0..1023)
			UNITS "dB"
			MAX-ACCESS read-only
			STATUS current
			DESCRIPTION
				"This parameter is a real upstream Hlog(f) values in dB. Represents 
				the real Hlog(f = i* delta f) value for a particular sub-carrier index i, 
				ranging from 1 to NSCus. The real Hlog(f) value is represented as 
				(6-m(i)/10), with m(i) 10 bit unsigned integer in the 0 to 1022 range. 
				A special value m=1023 indicates that no measurement could be done for 
				the subcarrier because it is out of the passband or that the 
				attenuation is out of range to be represented."
			REFERENCE
				"ITU-T G.997.1, paragraph 7.5.1.18.8 (HLOGpsus)"
			::= { sheXdslSCGUpStatusEntry 9 }

		
		sheXdslSCGUpStatusQln OBJECT-TYPE
			SYNTAX Unsigned32 (0..255)
			UNITS "dBm/Hz"
			MAX-ACCESS read-only
			STATUS current
			DESCRIPTION
				"This parameter is a real upstream QLN(f) values in dBm/Hz. Represents 
				the QLN(f = i* delta f) value for a particular sub-carrier index i, ranging 
				from 1 to NSCus. The QLN(f) is represented as ( -23 -n(i)/2), with 
				n(i) an 8 bit unsigned integer in the 0 to 254 range. 
				A special value n(i)=255 indicates that no measurement could be done for the 
				subcarrier because it is out of the passband or that the noise PSD is 
				out of range to be represented.
				
				This parameter is applicable in loop diagnostic procedure and initialization.
				"
			REFERENCE
				"ITU-T G.997.1, paragraph 7.5.1.19.4 (QLNpsus)"
			::= { sheXdslSCGUpStatusEntry 11 }

		
		sheXdslChannelProfileTable OBJECT-TYPE
			SYNTAX SEQUENCE OF SheXdslChannelProfileEntry
			MAX-ACCESS not-accessible
			STATUS current
			DESCRIPTION
				"Description."
			::= { sheXdslMibObjects 28 }

		
		sheXdslChannelProfileEntry OBJECT-TYPE
			SYNTAX SheXdslChannelProfileEntry
			MAX-ACCESS not-accessible
			STATUS current
			DESCRIPTION
				"These table contains DSL channel profile configuration.
				Default profiles will always exist and its parameters will be set to
				vendor-specific values, unless otherwise specified in this document.
				
				Dynamic' profiles are implemented.The profile name is user specified.
				There are two different default profiles in the NE, which could not be modified!
				'DEFVAL'  - default profile for interfaces with iftype 'vdsl' (97)
				            used by ‘DEFVAL’ lineprofile
				'DEFVAL_ADSL' - default profile for interfaces with iftype 'adsl2' (230)
				                used by ‘DEFVAL_ADSL_A’ and ‘DEFVAL_ADSL_B’ lineprofiles
				"
			INDEX { sheXdslChannelProfileIndex }
			::= { sheXdslChannelProfileTable 1 }

		
		SheXdslChannelProfileEntry ::=
			SEQUENCE { 
				sheXdslChannelProfileIndex
					Unsigned32,
				sheXdslChannelProfileName
					SnmpAdminString,
				sheXdslChannelProfileMinDataRateDs
					Unsigned32,
				sheXdslChannelProfileMinDataRateUs
					Unsigned32,
				sheXdslChannelProfileMinResDataRateDs
					Unsigned32,
				sheXdslChannelProfileMinResDataRateUs
					Unsigned32,
				sheXdslChannelProfileMaxDataRateDs
					Unsigned32,
				sheXdslChannelProfileMaxDataRateUs
					Unsigned32,
				sheXdslChannelProfileMinDataRateLowPwrDs
					Unsigned32,
				sheXdslChannelProfileMaxInterleaveDelayDs
					Unsigned32,
				sheXdslChannelProfileMaxInterleaveDelayUs
					Unsigned32,
				sheXdslChannelProfileMinINPDs
					SheXdslConfMinInpType,
				sheXdslChannelProfileMinINPUs
					SheXdslConfMinInpType,
				sheXdslChannelProfileMaxBerDs
					SheXdslMaxErrorRateType,
				sheXdslChannelProfileMaxBerUs
					SheXdslMaxErrorRateType,
				sheXdslChannelProfileThresholdRateDownShiftDs
					Unsigned32,
				sheXdslChannelProfileThresholdRateUpShiftDs
					Unsigned32,
				sheXdslChannelProfileThresholdRateDownShiftUs
					Unsigned32,
				sheXdslChannelProfileThresholdRateUpShiftUs
					Unsigned32
			 }

		sheXdslChannelProfileIndex OBJECT-TYPE
			SYNTAX Unsigned32 (1..300)
			MAX-ACCESS read-only
			STATUS current
			DESCRIPTION
				"Index of this table."
			::= { sheXdslChannelProfileEntry 1 }

		
		sheXdslChannelProfileName OBJECT-TYPE
			SYNTAX SnmpAdminString (SIZE (1..32))
			MAX-ACCESS read-only
			STATUS current
			DESCRIPTION
				"This object identifies a row in this table.  
				
				Dynamic' profiles are implemented.The profile name is user specified.
				There are two different default profiles in the NE, which could not be modified!
				'DEFVAL'  - default profile for interfaces with iftype 'vdsl' (97)
				            used by ‘DEFVAL’ and ‘DEFVAL_VDSL2_P’ lineprofile
				'DEFVAL_ADSL' - default profile for interfaces with iftype 'adsl2' (230)
				                used by ‘DEFVAL_ADSL_A’ and ‘DEFVAL_ADSL_B’ lineprofiles
				
				This characters are not allowed:  space : ?"
			::= { sheXdslChannelProfileEntry 2 }

		
		sheXdslChannelProfileMinDataRateDs OBJECT-TYPE
			SYNTAX Unsigned32 (32..103980)
			UNITS "kbps"
			MAX-ACCESS read-only
			STATUS current
			DESCRIPTION
				"Minimum Data Rate on Downstream direction.  The minimum net
				data rate for the bearer channel, coded in kbps.
				
				Remark:
				For lines using an ADSL standard the maximum datarate value in ds direction
				is limited to 32736 kbps."
			REFERENCE
				"ITU-T G.997.1, paragraph 7.3.2.1"
			::= { sheXdslChannelProfileEntry 3 }

		
		sheXdslChannelProfileMinDataRateUs OBJECT-TYPE
			SYNTAX Unsigned32 (32..103980)
			UNITS "kbps"
			MAX-ACCESS read-only
			STATUS current
			DESCRIPTION
				"Minimum Data Rate on Upstream direction.  The minimum net data
				rate for the bearer channel, coded in kbps.
				
				Remark:
				For lines using an ADSL standard the maximum datarate value in us direction
				is limited to 3520 kbps."
			REFERENCE
				"ITU-T G.997.1, paragraph 7.3.2.1"
			::= { sheXdslChannelProfileEntry 4 }

		
		sheXdslChannelProfileMinResDataRateDs OBJECT-TYPE
			SYNTAX Unsigned32 (32..103980)
			UNITS "kbps"
			MAX-ACCESS read-only
			STATUS current
			DESCRIPTION
				"Minimum Reserved Data Rate on Downstream direction.  The
				minimum reserved net data rate for the bearer channel, coded
				in kbps.  This parameter is used only if the Rate Adaptation
				Mode in the direction of the line is set to DynamicRa.
				
				Remark:
				For lines using an ADSL standard the maximum datarate value in ds direction
				is limited to 32736 kbps."
			REFERENCE
				"ITU-T G.997.1, paragraph 7.3.2.1"
			::= { sheXdslChannelProfileEntry 5 }

		
		sheXdslChannelProfileMinResDataRateUs OBJECT-TYPE
			SYNTAX Unsigned32 (32..103980)
			UNITS "kbps"
			MAX-ACCESS read-only
			STATUS current
			DESCRIPTION
				"Minimum Reserved Data Rate on Upstream direction.  The minimum
				reserved net data rate for the bearer channel, coded in
				kbps.  This parameter is used only if the Rate Adaptation
				Mode in the direction of the Line is set to DynamicRa.
				
				Remark:
				For lines using an ADSL standard the maximum datarate value in us direction
				is limited to 3520 kbps."
			REFERENCE
				"ITU-T G.997.1, paragraph 7.3.2.1"
			::= { sheXdslChannelProfileEntry 6 }

		
		sheXdslChannelProfileMaxDataRateDs OBJECT-TYPE
			SYNTAX Unsigned32 (32..103980)
			UNITS "kbps"
			MAX-ACCESS read-only
			STATUS current
			DESCRIPTION
				"Maximum Data Rate on Downstream direction.  The maximum net
				data rate for the bearer channel, coded in kbps.
				
				Remark:
				For lines using an ADSL standard the maximum datarate value in ds direction
				is limited to 32736 kbps."
			REFERENCE
				"ITU-T G.997.1, paragraph 7.3.2.1"
			::= { sheXdslChannelProfileEntry 7 }

		
		sheXdslChannelProfileMaxDataRateUs OBJECT-TYPE
			SYNTAX Unsigned32 (32..103980)
			UNITS "kbps"
			MAX-ACCESS read-only
			STATUS current
			DESCRIPTION
				"Maximum Data Rate on Upstream direction.  The maximum net data
				rate for the bearer channel, coded in kbps.
				
				Remark:
				For lines using an ADSL standard the maximum datarate value in us direction
				is limited to 3520 kbps."
			REFERENCE
				"ITU-T G.997.1, paragraph 7.3.2.1"
			::= { sheXdslChannelProfileEntry 8 }

		
		sheXdslChannelProfileMinDataRateLowPwrDs OBJECT-TYPE
			SYNTAX Unsigned32 (32..103980)
			UNITS "kbps"
			MAX-ACCESS read-only
			STATUS current
			DESCRIPTION
				"Minimum Data Rate in Low Power state on Downstream direction.
				The minimum net data rate for the bearer channel, coded in
				kbps, during the low power state (L1 in G.992.2, L2 in
				G.992.3).
				
				Remark:
				For lines using an ADSL standard the maximum datarate value in ds direction
				is limited to 32736 kbps."
			REFERENCE
				"ITU-T G.997.1, paragraph 7.3.2.1"
			::= { sheXdslChannelProfileEntry 9 }

		
		sheXdslChannelProfileMaxInterleaveDelayDs OBJECT-TYPE
			SYNTAX Unsigned32 (0 | 1 | 2..63 | 255)
			UNITS "milliseconds"
			MAX-ACCESS read-only
			STATUS current
			DESCRIPTION
				"Maximum Interleave Delay on Downstream direction. The maximum
				one-way interleaving delay introduced by the PMS-TC on
				Downstream direction. The xTUs shall choose the S (factor)
				and D (depth) values such that the actual one-way interleaving
				delay (XdslChanInterleaveDelay) is as close as possible to,
				but less than or equal to this parameter.
				There are three special values defined:
				0   -> 'no bound (S0)' - indicates no delay bound is being imposed
				1   -> 'none (fast, S1)' - indicates the Fast Latency Path shall be used in the G.992.1
				       and S and D shall be selected such that S <= 1 and D = 1 in ITU-T
				       Recommendations G.992.2, G.992.3, G.992.4, G.992.5 and G.993.2 
				255 -> '1 (VDSL only, S2)' - indicates a delay bound of 1 ms in ITU-T Recommendation G.993.2.
				
				If the value 1 is selected, then the configured value for
				sheXdslChannelProfileMinINPDs should be null (0).
				"
			REFERENCE
				"ITU-T G.997.1, paragraph 7.3.2.2"
			DEFVAL { 8 }
			::= { sheXdslChannelProfileEntry 11 }

		
		sheXdslChannelProfileMaxInterleaveDelayUs OBJECT-TYPE
			SYNTAX Unsigned32 (0 | 1 | 2..63 | 255)
			UNITS "milliseconds"
			MAX-ACCESS read-only
			STATUS current
			DESCRIPTION
				"Maximum Interleave Delay on Upstream direction. The maximum
				one-way interleaving delay introduced by the PMS-TC on
				Upstream direction. The xTUs shall choose the S (factor) and
				D (depth) values such that the actual one-way interleaving
				delay (XdslChanInterleaveDelay) is as close as possible to,
				but less than or equal to this parameter.
				There are three special values defined:
				0   -> 'no bound (S0)' - indicates no delay bound is being imposed
				1   -> 'none (fast, S1)' - indicates the Fast Latency Path shall be used in the G.992.1
				       and S and D shall be selected such that S <= 1 and D = 1 in ITU-T
				       Recommendations G.992.2, G.992.3, G.992.4, G.992.5 and G.993.2 
				255 -> '1 (VDSL only, S2)' - indicates a delay bound of 1 ms in ITU-T Recommendation G.993.2.
				
				If the value 1 is selected, then the configured value for
				sheXdslChannelProfileMinINPUs should be null (0)."
			REFERENCE
				"ITU-T G.997.1, paragraph 7.3.2.2"
			DEFVAL { 8 }
			::= { sheXdslChannelProfileEntry 12 }

		
		sheXdslChannelProfileMinINPDs OBJECT-TYPE
			SYNTAX SheXdslConfMinInpType
			UNITS "symbols"
			MAX-ACCESS read-only
			STATUS current
			DESCRIPTION
				"Minimum Impulse Noise Protection on Downstream direction.  The
				minimum impulse noise protection for the bearer channel,
				expressed in symbols.  The parameter can take the following
				values: 
				null         -> 0  -> i.e., INP not required
				halfSymbol   -> 50 -> i.e., INP length is 1/2 symbol
				and 1-16 symbols in steps of 1 symbol."
			REFERENCE
				"ITU-T G.997.1, paragraph 7.3.2.3"
			DEFVAL { use2Symbols }
			::= { sheXdslChannelProfileEntry 13 }

		
		sheXdslChannelProfileMinINPUs OBJECT-TYPE
			SYNTAX SheXdslConfMinInpType
			UNITS "symbols"
			MAX-ACCESS read-only
			STATUS current
			DESCRIPTION
				"Minimum Impulse Noise Protection on Upstream direction.  The
				minimum impulse noise protection for the bearer channel,
				expressed in symbols.  The parameter can take the following
				values:
				null        -> 0  -> i.e., INP not required
				halfSymbol  -> 50 -> i.e., INP length is 1/2 symbol
				and 1-16 symbols in steps of 1 symbol."
			REFERENCE
				"ITU-T G.997.1, paragraph 7.3.2.3"
			DEFVAL { use2Symbols }
			::= { sheXdslChannelProfileEntry 14 }

		
		sheXdslChannelProfileMaxBerDs OBJECT-TYPE
			SYNTAX SheXdslMaxErrorRateType
			MAX-ACCESS read-only
			STATUS current
			DESCRIPTION
				"Maximum Bit Error Ratio on Downstream direction.  The maximum
				bit error ratio for the bearer channel.  The parameter can
				take the following values (for 1E-3, 1E-5 or 1E-7):
				   eMinus3 (0),
				   eMinus5 (1),
				   eMinus7 (2)"
			REFERENCE
				"ITU-T G.997.1, paragraph 7.3.2.6"
			DEFVAL { eMinus7 }
			::= { sheXdslChannelProfileEntry 15 }

		
		sheXdslChannelProfileMaxBerUs OBJECT-TYPE
			SYNTAX SheXdslMaxErrorRateType
			MAX-ACCESS read-only
			STATUS current
			DESCRIPTION
				"Maximum Bit Error Ratio on Upstream direction.  The maximum
				bit error ratio for the bearer channel.  The parameter can
				take the following values (for 1E-3, 1E-5 or 1E-7):
				   eMinus3 (0),
				   eMinus5 (1),
				   eMinus7 (2)"
			REFERENCE
				"ITU-T G.997.1, paragraph 7.3.2.6"
			DEFVAL { eMinus7 }
			::= { sheXdslChannelProfileEntry 16 }

		
		sheXdslChannelProfileThresholdRateDownShiftDs OBJECT-TYPE
			SYNTAX Unsigned32 (0..1000000)
			UNITS "bps"
			MAX-ACCESS read-only
			STATUS current
			DESCRIPTION
				"Configured rate change threshold causing an xdslRateChangeDownShiftTrap.
				A trap is produced when for downstream direction:
				     ChanCurrTxRate <= ChanPrevTxRate minus the value of this object.
				
				A value of `0' will disable the trap."
			REFERENCE
				"ITU-T G.997.1, paragraph 7.3.2.8.2"
			DEFVAL { 0 }
			::= { sheXdslChannelProfileEntry 17 }

		
		sheXdslChannelProfileThresholdRateUpShiftDs OBJECT-TYPE
			SYNTAX Unsigned32 (0..1000000)
			UNITS "bps"
			MAX-ACCESS read-only
			STATUS current
			DESCRIPTION
				"Configured rate change threshold causing an xdslRateChangeUpShiftTrap.
				A trap is produced when for downstream direction:
				       ChanCurrTxRate >= ChanPrevTxRate plus the value of this object.
				
				A value of `0' will disable the trap."
			REFERENCE
				"ITU-T G.997.1, paragraph 7.3.2.8.1"
			DEFVAL { 0 }
			::= { sheXdslChannelProfileEntry 18 }

		
		sheXdslChannelProfileThresholdRateDownShiftUs OBJECT-TYPE
			SYNTAX Unsigned32 (0..1000000)
			UNITS "bps"
			MAX-ACCESS read-only
			STATUS current
			DESCRIPTION
				"Configured rate change threshold causing an xdslRateChangeDownShiftTrap.
				A trap is produced when for upstream direction:
				     ChanCurrTxRate <= ChanPrevTxRate minus the value of this object.
				
				A value of `0' will disable the trap."
			REFERENCE
				"ITU-T G.997.1, paragraph 7.3.2.8.2"
			DEFVAL { 0 }
			::= { sheXdslChannelProfileEntry 19 }

		
		sheXdslChannelProfileThresholdRateUpShiftUs OBJECT-TYPE
			SYNTAX Unsigned32 (0..1000000)
			UNITS "bps"
			MAX-ACCESS read-only
			STATUS current
			DESCRIPTION
				"Configured rate change threshold causing an xdslRateChangeUpShiftTrap.
				A trap is produced when for upstream direction:
				       ChanCurrTxRate >= ChanPrevTxRate plus the value of this object.
				
				A value of `0' will disable the trap."
			REFERENCE
				"ITU-T G.997.1, paragraph 7.3.2.8.1"
			DEFVAL { 0 }
			::= { sheXdslChannelProfileEntry 20 }

		
		sheXdslChannelProfileControl OBJECT IDENTIFIER ::= { sheXdslMibObjects 29 }

		
		sheXdslChannelProfileControlRequest OBJECT-TYPE
			SYNTAX SheXdslControlRequestType
			MAX-ACCESS read-write
			STATUS current
			DESCRIPTION
				"createXdslChannelProfileEntry:
				sheXdslChannelProfileControlName
				
				modifyXdslChannelProfileEntry:
				sheXdslLineControlIndex
				...all group members
				
				deleteXdslChannelProfileEntry:
				sheXdslChannelProfileControlIndex
				
				NOTE:
				During create, the NE will select a free index value.
				Modification is not allowed for used profiles.
				Delete is not allowed for used profiles.
				
				"
			::= { sheXdslChannelProfileControl 1 }

		
		sheXdslChannelProfileControlIndex OBJECT-TYPE
			SYNTAX Unsigned32 (1..300)
			MAX-ACCESS read-write
			STATUS current
			DESCRIPTION
				"Index of a channel profile table entry for modify or delete."
			::= { sheXdslChannelProfileControl 2 }

		
		sheXdslChannelProfileControlStatus OBJECT-TYPE
			SYNTAX SheControlStatusType
			MAX-ACCESS read-only
			STATUS current
			DESCRIPTION
				"The status of a user command. 
				"
			::= { sheXdslChannelProfileControl 3 }

		
		sheXdslChannelProfileControlTimer OBJECT-TYPE
			SYNTAX Gauge32
			MAX-ACCESS read-only
			STATUS current
			DESCRIPTION
				"The maximum wait time for the manager for a long running user command. 
				"
			::= { sheXdslChannelProfileControl 4 }

		
		sheXdslChannelProfileControlReqResult OBJECT-TYPE
			SYNTAX SheXdslControlRequestResultType
			MAX-ACCESS read-only
			STATUS current
			DESCRIPTION
				"The result of the last user command."
			::= { sheXdslChannelProfileControl 5 }

		
		sheXdslChannelProfileControlTimeStamp OBJECT-TYPE
			SYNTAX Unsigned32
			UNITS "sec"
			MAX-ACCESS read-only
			STATUS current
			DESCRIPTION
				"The time stamp of the last command (end of command)."
			::= { sheXdslChannelProfileControl 6 }

		
		sheXdslChannelProfileControlName OBJECT-TYPE
			SYNTAX SnmpAdminString (SIZE (1..32))
			MAX-ACCESS read-write
			STATUS current
			DESCRIPTION
				"The name for a new created profile."
			::= { sheXdslChannelProfileControl 7 }

		
		sheXdslChannelProfileControlMinDataRateDs OBJECT-TYPE
			SYNTAX Unsigned32 (32..103980)
			UNITS "kbps"
			MAX-ACCESS read-write
			STATUS current
			DESCRIPTION
				"Look at table."
			::= { sheXdslChannelProfileControl 8 }

		
		sheXdslChannelProfileControlMinDataRateUs OBJECT-TYPE
			SYNTAX Unsigned32 (32..103980)
			UNITS "kbps"
			MAX-ACCESS read-write
			STATUS current
			DESCRIPTION
				"Look at table."
			::= { sheXdslChannelProfileControl 9 }

		
		sheXdslChannelProfileControlMinResDataRateDs OBJECT-TYPE
			SYNTAX Unsigned32 (32..103980)
			UNITS "kbps"
			MAX-ACCESS read-write
			STATUS current
			DESCRIPTION
				"Look at table."
			::= { sheXdslChannelProfileControl 10 }

		
		sheXdslChannelProfileControlMinResDataRateUs OBJECT-TYPE
			SYNTAX Unsigned32 (32..103980)
			UNITS "kbps"
			MAX-ACCESS read-write
			STATUS current
			DESCRIPTION
				"Look at table."
			::= { sheXdslChannelProfileControl 11 }

		
		sheXdslChannelProfileControlMaxDataRateDs OBJECT-TYPE
			SYNTAX Unsigned32 (32..103980)
			UNITS "kbps"
			MAX-ACCESS read-write
			STATUS current
			DESCRIPTION
				"Look at table."
			::= { sheXdslChannelProfileControl 12 }

		
		sheXdslChannelProfileControlMaxDataRateUs OBJECT-TYPE
			SYNTAX Unsigned32 (32..103980)
			UNITS "kbps"
			MAX-ACCESS read-write
			STATUS current
			DESCRIPTION
				"Look at table."
			::= { sheXdslChannelProfileControl 13 }

		
		sheXdslChannelProfileControlMinDataRateLowPwrDs OBJECT-TYPE
			SYNTAX Unsigned32 (32..103980)
			UNITS "kbps"
			MAX-ACCESS read-write
			STATUS current
			DESCRIPTION
				"Look at table."
			::= { sheXdslChannelProfileControl 14 }

		
		sheXdslChannelProfileControlMaxInterleaveDelayDs OBJECT-TYPE
			SYNTAX Unsigned32 (0 | 1 | 2..63 | 255)
			MAX-ACCESS read-write
			STATUS current
			DESCRIPTION
				"look at table."
			::= { sheXdslChannelProfileControl 16 }

		
		sheXdslChannelProfileControlMaxInterleaveDelayUs OBJECT-TYPE
			SYNTAX Unsigned32 (0 | 1 | 2..63 | 255)
			MAX-ACCESS read-write
			STATUS current
			DESCRIPTION
				"look at table."
			::= { sheXdslChannelProfileControl 17 }

		
		sheXdslChannelProfileControlMinINPDs OBJECT-TYPE
			SYNTAX SheXdslConfMinInpType
			MAX-ACCESS read-write
			STATUS current
			DESCRIPTION
				"look at table"
			::= { sheXdslChannelProfileControl 18 }

		
		sheXdslChannelProfileControlMinINPUs OBJECT-TYPE
			SYNTAX SheXdslConfMinInpType
			MAX-ACCESS read-write
			STATUS current
			DESCRIPTION
				"look at table"
			::= { sheXdslChannelProfileControl 19 }

		
		sheXdslChannelProfileControlMaxBerDs OBJECT-TYPE
			SYNTAX SheXdslMaxErrorRateType
			MAX-ACCESS read-write
			STATUS current
			DESCRIPTION
				"look at table"
			::= { sheXdslChannelProfileControl 20 }

		
		sheXdslChannelProfileControlMaxBerUs OBJECT-TYPE
			SYNTAX SheXdslMaxErrorRateType
			MAX-ACCESS read-write
			STATUS current
			DESCRIPTION
				"look at table"
			::= { sheXdslChannelProfileControl 21 }

		
		sheXdslChannelProfileControlThresholdRateDownShiftDs OBJECT-TYPE
			SYNTAX Unsigned32 (0..1000000)
			UNITS "bps"
			MAX-ACCESS read-write
			STATUS current
			DESCRIPTION
				"Configured rate change threshold causing an xdslRateChangeDownShiftTrap."
			::= { sheXdslChannelProfileControl 22 }

		
		sheXdslChannelProfileControlThresholdRateUpShiftDs OBJECT-TYPE
			SYNTAX Unsigned32 (0..1000000)
			UNITS "bps"
			MAX-ACCESS read-write
			STATUS current
			DESCRIPTION
				"Configured rate change threshold causing an xdslRateChangeUpShiftTrap."
			::= { sheXdslChannelProfileControl 23 }

		
		sheXdslChannelProfileControlThresholdRateDownShiftUs OBJECT-TYPE
			SYNTAX Unsigned32 (0..1000000)
			UNITS "bps"
			MAX-ACCESS read-write
			STATUS current
			DESCRIPTION
				"Configured rate change threshold causing an xdslRateChangeDownShiftTrap."
			::= { sheXdslChannelProfileControl 24 }

		
		sheXdslChannelProfileControlThresholdRateUpShiftUs OBJECT-TYPE
			SYNTAX Unsigned32 (0..1000000)
			UNITS "bps"
			MAX-ACCESS read-write
			STATUS current
			DESCRIPTION
				"Configured rate change threshold causing an xdslRateChangeUpShiftTrap."
			::= { sheXdslChannelProfileControl 25 }

		
		sheXdslNotifications OBJECT IDENTIFIER ::= { sheXdslLineMib 2 }

		
		sheXdslPerfLofsThreshNotification NOTIFICATION-TYPE
			OBJECTS { sheXdslPerfDataCurr15MinLofs, sheXdslThresh15MinLofs }
			STATUS current
			DESCRIPTION 
				"Loss of Framing 15-minute interval threshold 
				(xdslThresh15MinLofs) reached."
			::= { sheXdslNotifications 1 }

		
		sheXdslPerfLossThreshNotification NOTIFICATION-TYPE
			OBJECTS { sheXdslPerfDataCurr15MinLoss, sheXdslThresh15MinLoss }
			STATUS current
			DESCRIPTION 
				"Loss of Signal 15-minute interval threshold 
				(xdslThresh15MinLoss) reached."
			::= { sheXdslNotifications 2 }

		
		sheXdslPerfLprsThreshNotification NOTIFICATION-TYPE
			OBJECTS { sheXdslPerfDataCurr15MinLprs, sheXdslThresh15MinLprs }
			STATUS current
			DESCRIPTION 
				"Loss of Power 15-minute interval threshold 
				(xdslThresh15MinLprs) reached."
			::= { sheXdslNotifications 3 }

		
		sheXdslPerfLolsThreshNotification NOTIFICATION-TYPE
			OBJECTS { sheXdslPerfDataCurr15MinLols, sheXdslThresh15MinLols }
			STATUS current
			DESCRIPTION 
				"Loss of Link 15-minute interval threshold 
				(xdslThresh15MinLols) reached."
			::= { sheXdslNotifications 4 }

		
		sheXdslPerfESsThreshNotification NOTIFICATION-TYPE
			OBJECTS { sheXdslPerfDataCurr15MinESs, sheXdslThresh15MinESs }
			STATUS current
			DESCRIPTION 
				"Errored Seconds 15-minute interval threshold
				(xdslThresh15MinESs) reached."
			::= { sheXdslNotifications 5 }

		
		sheXdslPerfSESsThreshNotification NOTIFICATION-TYPE
			OBJECTS { sheXdslPerfDataCurr15MinSESs, sheXdslThresh15MinSESs }
			STATUS current
			DESCRIPTION 
				"Severely Errored Seconds 15-minute interval threshold 
				(xdslThresh15MinSESs) reached."
			::= { sheXdslNotifications 6 }

		
		sheXdslPerfUASsThreshNotification NOTIFICATION-TYPE
			OBJECTS { sheXdslPerfDataCurr15MinUASs, sheXdslThresh15MinUASs }
			STATUS current
			DESCRIPTION 
				"Unavailable Seconds 15-minute interval threshold 
				(xdslThresh15MinUASs) reached."
			::= { sheXdslNotifications 7 }

		
		sheXdslInitFailureNotification NOTIFICATION-TYPE
			OBJECTS { sheXdslPhysCurrStatus }
			STATUS current
			DESCRIPTION 
				"Xtu initialization failed.  See xdslPhysCurrStatus for potential reasons."
			::= { sheXdslNotifications 8 }

		
		sheXdslLineModified NOTIFICATION-TYPE
			OBJECTS { sheXdslLineControlIndex, sheXdslLineControlTimeStamp, sheXdslLineControlGsAction, sheXdslLineControlConfProfile }
			STATUS current
			DESCRIPTION 
				"Configuration trap."
			::= { sheXdslNotifications 10 }

		
		sheXdslLineAlarmConfModified NOTIFICATION-TYPE
			OBJECTS { sheXdslLineControlIndex, sheXdslLineControlTimeStamp, sheXdslLineControlAlarmConfProfile }
			STATUS current
			DESCRIPTION 
				"Configuration trap."
			::= { sheXdslNotifications 11 }

		
		sheXdslLineConfProfileCreated NOTIFICATION-TYPE
			OBJECTS { sheXdslLineConfProfileControlIndex, sheXdslLineConfProfileControlTimeStamp, sheXdslLineConfProfileControlName, sheXdslLineConfProfileControlDownRateMode, sheXdslLineConfProfileControlUpRateMode, 
				sheXdslLineConfProfileControlDownMaxPwr, sheXdslLineConfProfileControlUpMaxPwr, sheXdslLineConfProfileControlMaxUpRxPower, sheXdslLineConfProfileControlDownMaxSnrMgn, sheXdslLineConfProfileControlDownMinSnrMgn, 
				sheXdslLineConfProfileControlDownTargetSnrMgn, sheXdslLineConfProfileControlUpMaxSnrMgn, sheXdslLineConfProfileControlUpMinSnrMgn, sheXdslLineConfProfileControlUpTargetSnrMgn, sheXdslLineConfProfileControlVtucDownshiftSnrMgn, 
				sheXdslLineConfProfileControlVtucUpshiftSnrMgn, sheXdslLineConfProfileControlVtucMinDownshiftTime, sheXdslLineConfProfileControlVtucMinUpshiftTime, sheXdslLineConfProfileControlVturDownshiftSnrMgn, sheXdslLineConfProfileControlVturUpshiftSnrMgn, 
				sheXdslLineConfProfileControlVturMinDownshiftTime, sheXdslLineConfProfileControlVturMinUpshiftTime, sheXdslLineConfProfileControlUseVdsl2BandPlanNumber, sheXdslLineConfProfileControlUseVdsl2ProfileNumber, sheXdslLineConfProfileControlGsStandard
				 }
			STATUS current
			DESCRIPTION 
				"Configuration trap."
			::= { sheXdslNotifications 12 }

		
		sheXdslLineConfProfileModified NOTIFICATION-TYPE
			OBJECTS { sheXdslLineConfProfileControlIndex, sheXdslLineConfProfileControlTimeStamp, sheXdslLineConfProfileControlName, sheXdslLineConfProfileControlDownRateMode, sheXdslLineConfProfileControlUpRateMode, 
				sheXdslLineConfProfileControlDownMaxPwr, sheXdslLineConfProfileControlUpMaxPwr, sheXdslLineConfProfileControlMaxUpRxPower, sheXdslLineConfProfileControlDownMaxSnrMgn, sheXdslLineConfProfileControlDownMinSnrMgn, 
				sheXdslLineConfProfileControlDownTargetSnrMgn, sheXdslLineConfProfileControlUpMaxSnrMgn, sheXdslLineConfProfileControlUpMinSnrMgn, sheXdslLineConfProfileControlUpTargetSnrMgn, sheXdslLineConfProfileControlVtucDownshiftSnrMgn, 
				sheXdslLineConfProfileControlVtucUpshiftSnrMgn, sheXdslLineConfProfileControlVtucMinDownshiftTime, sheXdslLineConfProfileControlVtucMinUpshiftTime, sheXdslLineConfProfileControlVturDownshiftSnrMgn, sheXdslLineConfProfileControlVturUpshiftSnrMgn, 
				sheXdslLineConfProfileControlVturMinDownshiftTime, sheXdslLineConfProfileControlVturMinUpshiftTime, sheXdslLineConfProfileControlUseVdsl2BandPlanNumber, sheXdslLineConfProfileControlUseVdsl2ProfileNumber, sheXdslLineConfProfileControlGsStandard
				 }
			STATUS current
			DESCRIPTION 
				"Configuration trap."
			::= { sheXdslNotifications 13 }

		
		sheXdslLineConfProfileDeleted NOTIFICATION-TYPE
			OBJECTS { sheXdslLineConfProfileControlIndex, sheXdslLineConfProfileControlTimeStamp }
			STATUS current
			DESCRIPTION 
				"Configuration trap."
			::= { sheXdslNotifications 14 }

		
		sheXdslLineConfExtnProfileModified NOTIFICATION-TYPE
			OBJECTS { sheXdslLineConfExtnProfileControlIndex, sheXdslLineConfExtnProfileControlTimeStamp, sheXdslLineConfExtnProfileControlDownBitSwap, sheXdslLineConfExtnProfileControlUpBitSwap, sheXdslLineConfExtnProfileControlXtucPwrMgmtL0Time, 
				sheXdslLineConfExtnProfileControlXtucPwrMgmtL2Time, sheXdslLineConfExtnProfileControlXtucPwrMgmtL2ATPR, sheXdslLineConfExtnProfileControlXtucPwrMgmtMode, sheXdslLineConfExtnProfileControlUseCustomSubcarrierMask, sheXdslLineConfExtnProfileControlCustomSubcarrierMask, 
				sheXdslLineConfExtnProfileControlXtucPwrMgmtL2ATPRT, sheXdslLineConfExtnProfileControlDownPboEpsd, sheXdslLineConfExtnProfileControlDownPboEScmA, sheXdslLineConfExtnProfileControlDownPboEScmB, sheXdslLineConfExtnProfileControlDownPboEScmC, 
				sheXdslLineConfExtnProfileControlUpPboA, sheXdslLineConfExtnProfileControlUpPboB, sheXdslLineConfExtnProfileControlMaxDownNomPsd, sheXdslLineConfExtnProfileControlUpPboBoostMode, sheXdslLineConfExtnProfileControlMaxUpNomPsd, 
				sheXdslLineConfExtnProfileControlDownPboEsel, sheXdslLineConfExtnProfileControlDownPboMus, sheXdslLineConfExtnProfileControlDownPboFMin, sheXdslLineConfExtnProfileControlDownPboFMax, sheXdslLineConfExtnProfileControlDownPboEselMin, 
				sheXdslLineConfExtnProfileControlDownPboMof, sheXdslLineConfExtnProfileControlUpPboKL, sheXdslLineConfExtnProfileControlUpPboKO, sheXdslLineConfExtnProfileControlMsgMinUp, sheXdslLineConfExtnProfileControlMsgMinDown, 
				sheXdslLineConfExtnProfileControlUsPsdMaskSelection, sheXdslLineConfExtnProfileControlCustomUsSubcarrierMask, sheXdslLineConfExtnProfileControlSnrModeDown, sheXdslLineConfExtnProfileControlSnrModeUp, sheXdslLineConfExtnProfileControlTxRefVnDown, 
				sheXdslLineConfExtnProfileControlTxRefVnUp }
			STATUS current
			DESCRIPTION 
				"Configuration notification."
			::= { sheXdslNotifications 15 }

		
		sheXdslLineAlarmConfProfileCreated NOTIFICATION-TYPE
			OBJECTS { sheXdslLineAlarmConfProfileControlIndex, sheXdslLineAlarmConfProfileControlTimeStamp, sheXdslLineAlarmConfProfileControlName, sheXdslLineAlarmConfProfileControlThresh15MinLofs, sheXdslLineAlarmConfProfileControlThresh15MinLoss, 
				sheXdslLineAlarmConfProfileControlThresh15MinLprs, sheXdslLineAlarmConfProfileControlThresh15MinLols, sheXdslLineAlarmConfProfileControlThresh15MinESs, sheXdslLineAlarmConfProfileControlThresh15MinSESs, sheXdslLineAlarmConfProfileControlThresh15MinUASs, 
				sheXdslLineAlarmConfProfileControlInitFailureNotifyEnable, sheXdslLineAlarmConfProfileOperationalStateNotifyEnable, sheXdslLineAlarmConfProfileViolationCheck }
			STATUS current
			DESCRIPTION 
				"Configuration trap."
			::= { sheXdslNotifications 16 }

		
		sheXdslLineAlarmConfProfileModified NOTIFICATION-TYPE
			OBJECTS { sheXdslLineAlarmConfProfileControlIndex, sheXdslLineAlarmConfProfileControlTimeStamp, sheXdslLineAlarmConfProfileControlName, sheXdslLineAlarmConfProfileControlThresh15MinLofs, sheXdslLineAlarmConfProfileControlThresh15MinLoss, 
				sheXdslLineAlarmConfProfileControlThresh15MinLprs, sheXdslLineAlarmConfProfileControlThresh15MinLols, sheXdslLineAlarmConfProfileControlThresh15MinESs, sheXdslLineAlarmConfProfileControlThresh15MinSESs, sheXdslLineAlarmConfProfileControlThresh15MinUASs, 
				sheXdslLineAlarmConfProfileControlInitFailureNotifyEnable, sheXdslLineAlarmConfProfileOperationalStateNotifyEnable, sheXdslLineAlarmConfProfileViolationCheck }
			STATUS current
			DESCRIPTION 
				"Configuration trap."
			::= { sheXdslNotifications 17 }

		
		sheXdslLineAlarmConfProfileDeleted NOTIFICATION-TYPE
			OBJECTS { sheXdslLineAlarmConfProfileControlIndex, sheXdslLineAlarmConfProfileControlTimeStamp }
			STATUS current
			DESCRIPTION 
				"Configuration trap."
			::= { sheXdslNotifications 18 }

		
		sheXdslPsdMaskProfileCreated NOTIFICATION-TYPE
			OBJECTS { sheXdslPsdMaskProfileControlIndex, sheXdslPsdMaskProfileControlTimeStamp, sheXdslPsdMaskProfileControlName }
			STATUS current
			DESCRIPTION 
				"Configuration notification."
			::= { sheXdslNotifications 19 }

		
		sheXdslPsdMaskProfileModified NOTIFICATION-TYPE
			OBJECTS { sheXdslPsdMaskProfileControlIndex, sheXdslPsdMaskProfileControlTimeStamp }
			STATUS current
			DESCRIPTION 
				"Configuration notification."
			::= { sheXdslNotifications 20 }

		
		sheXdslPsdMaskProfileDeleted NOTIFICATION-TYPE
			OBJECTS { sheXdslPsdMaskProfileControlIndex, sheXdslPsdMaskProfileControlTimeStamp }
			STATUS current
			DESCRIPTION 
				"Configuration notification."
			::= { sheXdslNotifications 21 }

		
		sheXdslCustomNotchProfileCreated NOTIFICATION-TYPE
			OBJECTS { sheXdslCustomNotchProfileControlIndex, sheXdslCustomNotchProfileControlTimeStamp, sheXdslCustomNotchProfileControlName, sheXdslCustomNotchProfileControlUsedNotches, sheXdslCustomNotchProfileControlStartIndex01, 
				sheXdslCustomNotchProfileControlStopIndex01, sheXdslCustomNotchProfileControlStartIndex02, sheXdslCustomNotchProfileControlStopIndex02, sheXdslCustomNotchProfileControlStartIndex03, sheXdslCustomNotchProfileControlStopIndex03, 
				sheXdslCustomNotchProfileControlStartIndex04, sheXdslCustomNotchProfileControlStopIndex04, sheXdslCustomNotchProfileControlStartIndex05, sheXdslCustomNotchProfileControlStopIndex05, sheXdslCustomNotchProfileControlStartIndex06, 
				sheXdslCustomNotchProfileControlStopIndex06, sheXdslCustomNotchProfileControlStartIndex07, sheXdslCustomNotchProfileControlStopIndex07, sheXdslCustomNotchProfileControlStartIndex08, sheXdslCustomNotchProfileControlStopIndex08, 
				sheXdslCustomNotchProfileControlStartIndex09, sheXdslCustomNotchProfileControlStopIndex09, sheXdslCustomNotchProfileControlStartIndex10, sheXdslCustomNotchProfileControlStopIndex10, sheXdslCustomNotchProfileControlStartIndex11, 
				sheXdslCustomNotchProfileControlStopIndex11, sheXdslCustomNotchProfileControlStartIndex12, sheXdslCustomNotchProfileControlStopIndex12, sheXdslCustomNotchProfileControlStartIndex13, sheXdslCustomNotchProfileControlStopIndex13, 
				sheXdslCustomNotchProfileControlStartIndex14, sheXdslCustomNotchProfileControlStopIndex14, sheXdslCustomNotchProfileControlStartIndex15, sheXdslCustomNotchProfileControlStopIndex15, sheXdslCustomNotchProfileControlStartIndex16, 
				sheXdslCustomNotchProfileControlStopIndex16 }
			STATUS current
			DESCRIPTION 
				"Configuration notification."
			::= { sheXdslNotifications 22 }

		
		sheXdslCustomNotchProfileModified NOTIFICATION-TYPE
			OBJECTS { sheXdslCustomNotchProfileControlIndex, sheXdslCustomNotchProfileControlTimeStamp, sheXdslCustomNotchProfileControlName, sheXdslCustomNotchProfileControlUsedNotches, sheXdslCustomNotchProfileControlStartIndex01, 
				sheXdslCustomNotchProfileControlStopIndex01, sheXdslCustomNotchProfileControlStartIndex02, sheXdslCustomNotchProfileControlStopIndex02, sheXdslCustomNotchProfileControlStartIndex03, sheXdslCustomNotchProfileControlStopIndex03, 
				sheXdslCustomNotchProfileControlStartIndex04, sheXdslCustomNotchProfileControlStopIndex04, sheXdslCustomNotchProfileControlStartIndex05, sheXdslCustomNotchProfileControlStopIndex05, sheXdslCustomNotchProfileControlStartIndex06, 
				sheXdslCustomNotchProfileControlStopIndex06, sheXdslCustomNotchProfileControlStartIndex07, sheXdslCustomNotchProfileControlStopIndex07, sheXdslCustomNotchProfileControlStartIndex08, sheXdslCustomNotchProfileControlStopIndex08, 
				sheXdslCustomNotchProfileControlStartIndex09, sheXdslCustomNotchProfileControlStopIndex09, sheXdslCustomNotchProfileControlStartIndex10, sheXdslCustomNotchProfileControlStopIndex10, sheXdslCustomNotchProfileControlStartIndex11, 
				sheXdslCustomNotchProfileControlStopIndex11, sheXdslCustomNotchProfileControlStartIndex12, sheXdslCustomNotchProfileControlStopIndex12, sheXdslCustomNotchProfileControlStartIndex13, sheXdslCustomNotchProfileControlStopIndex13, 
				sheXdslCustomNotchProfileControlStartIndex14, sheXdslCustomNotchProfileControlStopIndex14, sheXdslCustomNotchProfileControlStartIndex15, sheXdslCustomNotchProfileControlStopIndex15, sheXdslCustomNotchProfileControlStartIndex16, 
				sheXdslCustomNotchProfileControlStopIndex16 }
			STATUS current
			DESCRIPTION 
				"Configuration notification."
			::= { sheXdslNotifications 23 }

		
		sheXdslCustomNotchProfileDeleted NOTIFICATION-TYPE
			OBJECTS { sheXdslCustomNotchProfileControlIndex, sheXdslCustomNotchProfileControlTimeStamp }
			STATUS current
			DESCRIPTION 
				"Configuration notification."
			::= { sheXdslNotifications 24 }

		
		sheXdslOperationalStateChangedNotification NOTIFICATION-TYPE
			OBJECTS { sheXdslPhysCurrOperationalState }
			STATUS current
			DESCRIPTION 
				"Xtu-C operational state changed.  See xdslPhysCurrOperationalState."
			::= { sheXdslNotifications 25 }

		
		sheXdslLineModifiedReqResult NOTIFICATION-TYPE
			OBJECTS { sheXdslLineControlRequest, sheXdslLineControlIndex, sheXdslLineControlTimeStamp, sheXdslLineControlStatus, sheXdslLineControlReqResult
				 }
			STATUS current
			DESCRIPTION 
				"Request result trap for long running configuration command of a dsl line."
			::= { sheXdslNotifications 26 }

		
		sheXdslLineProfileModifiedReqResult NOTIFICATION-TYPE
			OBJECTS { sheXdslLineConfProfileControlRequest, sheXdslLineConfProfileControlIndex, sheXdslLineConfProfileControlTimeStamp, sheXdslLineConfProfileControlReqResult, sheXdslLineConfProfileControlStatus
				 }
			STATUS current
			DESCRIPTION 
				"Request result trap for long running configuration command of a dsl line profile."
			::= { sheXdslNotifications 27 }

		
		sheXdslLineExtnProfileModifiedReqResult NOTIFICATION-TYPE
			OBJECTS { sheXdslLineConfExtnProfileControlRequest, sheXdslLineConfExtnProfileControlIndex, sheXdslLineConfExtnProfileControlStatus, sheXdslLineConfExtnProfileControlReqResult, sheXdslLineConfExtnProfileControlTimeStamp
				 }
			STATUS current
			DESCRIPTION 
				"Request result trap for long running configuration command of a dsl line 
				extention profile."
			::= { sheXdslNotifications 28 }

		
		sheXdslAlarmProfileModifiedReqResult NOTIFICATION-TYPE
			OBJECTS { sheXdslLineAlarmConfProfileControlRequest, sheXdslLineAlarmConfProfileControlIndex, sheXdslLineAlarmConfProfileControlStatus, sheXdslLineAlarmConfProfileControlReqResult, sheXdslLineAlarmConfProfileControlTimeStamp
				 }
			STATUS current
			DESCRIPTION 
				"Request result trap for long running configuration command of a dsl alarm profile."
			::= { sheXdslNotifications 29 }

		
		sheXdslPsdMaskProfileModifiedReqResult NOTIFICATION-TYPE
			OBJECTS { sheXdslPsdMaskProfileControlRequest, sheXdslPsdMaskProfileControlIndex, sheXdslPsdMaskProfileControlStatus, sheXdslPsdMaskProfileControlReqResult, sheXdslPsdMaskProfileControlTimeStamp
				 }
			STATUS current
			DESCRIPTION 
				"Request result trap for long running configuration command of a dsl psdmask profile."
			::= { sheXdslNotifications 30 }

		
		sheXdslLineDeltStateModified NOTIFICATION-TYPE
			OBJECTS { sheXdslLineControlIndex, sheXdslLineControlTimeStamp, sheXdslLineControlLdsf, sheXdslLineControlStatus, sheXdslLineControlReqResult
				 }
			STATUS current
			DESCRIPTION 
				"Configuration trap."
			::= { sheXdslNotifications 31 }

		
		sheXdslLineDeltResultStateChanged NOTIFICATION-TYPE
			OBJECTS { sheXdslLineLdsfResult }
			STATUS current
			DESCRIPTION 
				"This notification will inform the TMN about changes for sheXdslLineLdsfResult if a 
				loop test was startet by operator or on remote request. "
			::= { sheXdslNotifications 32 }

		
		sheXdslLineDeltStatusReqResult NOTIFICATION-TYPE
			OBJECTS { sheXdslLineDeltStatusControlIndex, sheXdslLineDeltStatusControlStatus, sheXdslLineDeltStatusControlReqResult, sheXdslLineDeltStatusControlTimeStamp, sheXdslLineDeltStatusControlSCGDnGroupSize, 
				sheXdslLineDeltStatusControlSCGUpGroupSize, sheXdslLineDeltStatusControlSCGDnSnrMtime, sheXdslLineDeltStatusControlSCGUpSnrMtime, sheXdslLineDeltStatusControlSCGDnLinScale, sheXdslLineDeltStatusControlSCGUpLinScale, 
				sheXdslLineDeltStatusControlSCGDnHLogMtime, sheXdslLineDeltStatusControlSCGUpHLogMtime, sheXdslLineDeltStatusControlSCGDnQlnMtime, sheXdslLineDeltStatusControlSCGUpQlnMtime }
			STATUS current
			DESCRIPTION 
				"Result trap for long running command of delt status request."
			::= { sheXdslNotifications 33 }

		
		sheXdslLineDownPsdMaskProfileEntryModified NOTIFICATION-TYPE
			OBJECTS { sheXdslLineControlIndex, sheXdslLineControlTimeStamp, sheXdslLineControlStatus, sheXdslLineControlReqResult, sheXdslLineControlCustomDownPsdMaskProfile
				 }
			STATUS current
			DESCRIPTION 
				"Configuration trap."
			::= { sheXdslNotifications 34 }

		
		sheXdslLineUpPsdMaskProfileEntryModified NOTIFICATION-TYPE
			OBJECTS { sheXdslLineControlIndex, sheXdslLineControlTimeStamp, sheXdslLineControlStatus, sheXdslLineControlReqResult, sheXdslLineControlCustomUpPsdMaskProfile
				 }
			STATUS current
			DESCRIPTION 
				"Configuration trap."
			::= { sheXdslNotifications 35 }

		
		sheXdslLineNotchConfigurationModified NOTIFICATION-TYPE
			OBJECTS { sheXdslLineControlIndex, sheXdslLineControlTimeStamp, sheXdslLineControlStatus, sheXdslLineControlReqResult, sheXdslLineControlCustomNotchProfile, 
				sheXdslLineControlRfiBandMask }
			STATUS current
			DESCRIPTION 
				"Configuration trap."
			::= { sheXdslNotifications 36 }

		
		sheXdslLineShowtimeStatusReqResult NOTIFICATION-TYPE
			OBJECTS { sheXdslLineDeltStatusControlIndex, sheXdslLineDeltStatusControlStatus, sheXdslLineDeltStatusControlReqResult, sheXdslLineDeltStatusControlTimeStamp }
			STATUS current
			DESCRIPTION 
				"Result trap for long running command of showtime status request."
			::= { sheXdslNotifications 37 }

		
		sheXdslChannelProfileCreated NOTIFICATION-TYPE
			OBJECTS { sheXdslChannelProfileControlIndex, sheXdslChannelProfileControlStatus, sheXdslChannelProfileControlTimeStamp, sheXdslChannelProfileControlName, sheXdslChannelProfileControlMinDataRateDs, 
				sheXdslChannelProfileControlMinDataRateUs, sheXdslChannelProfileControlMinResDataRateDs, sheXdslChannelProfileControlMinResDataRateUs, sheXdslChannelProfileControlMaxDataRateDs, sheXdslChannelProfileControlMaxDataRateUs, 
				sheXdslChannelProfileControlMinDataRateLowPwrDs, sheXdslChannelProfileControlMaxBerDs, sheXdslChannelProfileControlMaxBerUs, sheXdslChannelProfileControlMaxInterleaveDelayDs, sheXdslChannelProfileControlMaxInterleaveDelayUs, 
				sheXdslChannelProfileControlMinINPDs, sheXdslChannelProfileControlMinINPUs, sheXdslChannelProfileControlThresholdRateDownShiftDs, sheXdslChannelProfileControlThresholdRateUpShiftDs, sheXdslChannelProfileControlThresholdRateDownShiftUs, 
				sheXdslChannelProfileControlThresholdRateUpShiftUs }
			STATUS current
			DESCRIPTION 
				"Description."
			::= { sheXdslNotifications 39 }

		
		sheXdslChannelProfileModified NOTIFICATION-TYPE
			OBJECTS { sheXdslChannelProfileControlIndex, sheXdslChannelProfileControlStatus, sheXdslChannelProfileControlTimeStamp, sheXdslChannelProfileControlName, sheXdslChannelProfileControlMinDataRateDs, 
				sheXdslChannelProfileControlMinDataRateUs, sheXdslChannelProfileControlMinResDataRateDs, sheXdslChannelProfileControlMinResDataRateUs, sheXdslChannelProfileControlMaxDataRateDs, sheXdslChannelProfileControlMaxDataRateUs, 
				sheXdslChannelProfileControlMinDataRateLowPwrDs, sheXdslChannelProfileControlMaxBerDs, sheXdslChannelProfileControlMaxBerUs, sheXdslChannelProfileControlMaxInterleaveDelayDs, sheXdslChannelProfileControlMaxInterleaveDelayUs, 
				sheXdslChannelProfileControlMinINPDs, sheXdslChannelProfileControlMinINPUs, sheXdslChannelProfileControlThresholdRateDownShiftDs, sheXdslChannelProfileControlThresholdRateUpShiftDs, sheXdslChannelProfileControlThresholdRateDownShiftUs, 
				sheXdslChannelProfileControlThresholdRateUpShiftUs }
			STATUS current
			DESCRIPTION 
				"Description."
			::= { sheXdslNotifications 40 }

		
		sheXdslChannelProfileDeleted NOTIFICATION-TYPE
			OBJECTS { sheXdslChannelProfileControlIndex, sheXdslChannelProfileControlStatus, sheXdslChannelProfileControlReqResult, sheXdslChannelProfileControlTimeStamp }
			STATUS current
			DESCRIPTION 
				"Description."
			::= { sheXdslNotifications 41 }

		
		sheXdslChannelProfileModifiedReqResult NOTIFICATION-TYPE
			OBJECTS { sheXdslChannelProfileControlRequest, sheXdslChannelProfileControlIndex, sheXdslChannelProfileControlStatus, sheXdslChannelProfileControlReqResult, sheXdslChannelProfileControlTimeStamp
				 }
			STATUS current
			DESCRIPTION 
				"Request result trap for long running configuration command of a dsl line."
			::= { sheXdslNotifications 42 }

		
		sheXdslChannelRateChangeDownShiftTrap NOTIFICATION-TYPE
			OBJECTS { sheXdslChanCurrTxRate }
			STATUS current
			DESCRIPTION 
				"The configured rate change downshift threshold for a dsl channel was reached. "
			::= { sheXdslNotifications 43 }

		
		sheXdslChannelRateChangeUpShiftTrap NOTIFICATION-TYPE
			OBJECTS { sheXdslChanCurrTxRate }
			STATUS current
			DESCRIPTION 
				"The configured rate change upshift threshold for a dsl channel was reached. "
			::= { sheXdslNotifications 44 }

		
		sheXdslLinePMSFStateModified NOTIFICATION-TYPE
			OBJECTS { sheXdslLineControlIndex, sheXdslLineControlTimeStamp, sheXdslLineControlStatus, sheXdslLineControlReqResult, sheXdslLineControlPMSF
				 }
			STATUS current
			DESCRIPTION 
				"Configuration trap."
			::= { sheXdslNotifications 45 }

		
		sheXdslLineForceInpModified NOTIFICATION-TYPE
			OBJECTS { sheXdslLineControlIndex, sheXdslLineControlTimeStamp, sheXdslLineControlForceINPDs, sheXdslLineControlForceINPUs }
			STATUS current
			DESCRIPTION 
				"Configuration trap."
			::= { sheXdslNotifications 46 }

		
		sheXdslLineChannelConfigurationModified NOTIFICATION-TYPE
			OBJECTS { sheXdslLineControlIndex, sheXdslLineControlTimeStamp, sheXdslLineControlChan1ConfProfile, sheXdslLineControlChan1RaRatioDs, sheXdslLineControlChan1RaRatioUs, 
				sheXdslLineControlChan2ConfProfile }
			STATUS current
			DESCRIPTION 
				"Configuration trap."
			::= { sheXdslNotifications 47 }

		
		sheXdslLinePerformanceHistoryModified NOTIFICATION-TYPE
			OBJECTS { sheXdslLineControlIndex, sheXdslLineControlTimeStamp, sheXdslLineControlPerformance15MinHistoryEnabled, sheXdslLineControlPerformance1DayHistoryEnabled }
			STATUS current
			DESCRIPTION 
				"Configuration trap."
			::= { sheXdslNotifications 48 }

		
		sheXdslAlarmNotifications OBJECT IDENTIFIER ::= { sheXdslLineMib 3 }

		
		sheXdslDownMaxSnrMgnNotification NOTIFICATION-TYPE
			OBJECTS { sheAlarmTimeAndDate, sheAlarmReportingSource, sheAlarmReportingSourceType, sheAlarmSeverity }
			STATUS current
			DESCRIPTION 
				"The downstream Signal to Noise Margin exceeded xdslLineConfDownMaxSnrMgn.
				The object xdslPhysCurrSnrMgn will contain the Signal to Noise
				margin as measured by the XTU-R."
			::= { sheXdslAlarmNotifications 1 }

		
		sheXdslDownMinSnrMgnNotification NOTIFICATION-TYPE
			OBJECTS { sheAlarmTimeAndDate, sheAlarmReportingSource, sheAlarmReportingSourceType, sheAlarmSeverity }
			STATUS current
			DESCRIPTION 
				"The downstream Signal to Noise Margin fell below xdslLineConfDownMinSnrMgn.
				The object xdslPhysCurrSnrMgn will contain the Signal to Noise margin as measured by 
				the XTU-R."
			::= { sheXdslAlarmNotifications 2 }

		
		sheXdslUpMaxSnrMgnNotification NOTIFICATION-TYPE
			OBJECTS { sheAlarmTimeAndDate, sheAlarmReportingSource, sheAlarmReportingSourceType, sheAlarmSeverity }
			STATUS current
			DESCRIPTION 
				"The upstream Signal to Noise Margin exceeded xdslLineConfUpMaxSnrMgn.
				The object xdslPhysCurrSnrMgn will contain the Signal to Noise margin as measured
				by the XTU-C."
			::= { sheXdslAlarmNotifications 3 }

		
		sheXdslUpMinSnrMgnNotification NOTIFICATION-TYPE
			OBJECTS { sheAlarmTimeAndDate, sheAlarmReportingSource, sheAlarmReportingSourceType, sheAlarmSeverity }
			STATUS current
			DESCRIPTION 
				"The upstream Signal to Noise Margin fell below xdslLineConfUpMinSnrMgn.
				The object xdslPhysCurrSnrMgn will contain the Signal to Noise margin as measured
				by the XTU-C."
			::= { sheXdslAlarmNotifications 4 }

		
		sheXdslLineAlarmTraps OBJECT IDENTIFIER ::= { sheXdslAlarmNotifications 5 }

		
		sheXdslLineAlarmLOS NOTIFICATION-TYPE
			OBJECTS { sheAlarmTimeAndDate, sheAlarmReportingSource, sheAlarmReportingSourceType, sheAlarmSeverity }
			STATUS current
			DESCRIPTION 
				"xTUC failure due to not receiving signal"
			::= { sheXdslLineAlarmTraps 1 }

		
		sheXdslLineAlarmLOF NOTIFICATION-TYPE
			OBJECTS { sheAlarmTimeAndDate, sheAlarmReportingSource, sheAlarmReportingSourceType, sheAlarmSeverity }
			STATUS current
			DESCRIPTION 
				"xTUC failure due to not receiving valid frame."
			::= { sheXdslLineAlarmTraps 2 }

		
		sheXdslLineAlarmLOL NOTIFICATION-TYPE
			OBJECTS { sheAlarmTimeAndDate, sheAlarmReportingSource, sheAlarmReportingSourceType, sheAlarmSeverity }
			STATUS current
			DESCRIPTION 
				"xTUC failure due to inability to link with xTUR"
			::= { sheXdslLineAlarmTraps 3 }

		
		sheXdslLineAlarmLPR NOTIFICATION-TYPE
			OBJECTS { sheAlarmTimeAndDate, sheAlarmReportingSource, sheAlarmReportingSourceType, sheAlarmSeverity }
			STATUS current
			DESCRIPTION 
				"xTUR failure due to loss of power"
			::= { sheXdslLineAlarmTraps 4 }

		
		sheXdslLineAlarmIMNR NOTIFICATION-TYPE
			OBJECTS { sheAlarmTimeAndDate, sheAlarmReportingSource, sheAlarmReportingSourceType, sheAlarmSeverity }
			STATUS current
			DESCRIPTION 
				"Loss of Signal Quality is declared when the Noise Margin falls below the Minimum Noise Margin,
				or the bit-error-rate exceeds the configured level."
			::= { sheXdslLineAlarmTraps 5 }

		
		sheXdslLineAlarmActivationFailed NOTIFICATION-TYPE
			OBJECTS { sheAlarmTimeAndDate, sheAlarmReportingSource, sheAlarmReportingSourceType, sheAlarmSeverity }
			STATUS current
			DESCRIPTION 
				"The line activation procedure on the IU returns with an error and the line
				will not start training sequence!"
			::= { sheXdslLineAlarmTraps 6 }

		
		sheXdslLineAlarmHWUnitDefect NOTIFICATION-TYPE
			OBJECTS { sheAlarmTimeAndDate, sheAlarmReportingSource, sheAlarmReportingSourceType, sheAlarmSeverity }
			STATUS current
			DESCRIPTION 
				"The xTUC has detected a HW defect for this line."
			::= { sheXdslLineAlarmTraps 7 }

		
		sheXdslLineAlarmConfigViolationDetected NOTIFICATION-TYPE
			OBJECTS { sheAlarmTimeAndDate, sheAlarmReportingSource, sheAlarmReportingSourceType, sheAlarmSeverity }
			STATUS current
			DESCRIPTION 
				"Only if config violation check was enabled for a line, the alarm will be send if a violation
				was detected. The alarm will always be send, doesn't matter if the line will reach showtime state
				or not. The line configuration and connected xtur equipment has to be checked.
				The alarm will be cleared if the line was disabled or retrain without config violation."
			::= { sheXdslLineAlarmTraps 9 }

		
		sheXdslVccTp OBJECT IDENTIFIER ::= { sheXdslLineMib 5 }

		
		sheXdslVccTpTable OBJECT-TYPE
			SYNTAX SEQUENCE OF SheXdslVccTpEntry
			MAX-ACCESS not-accessible
			STATUS current
			DESCRIPTION
				"The VccTp-Table."
			::= { sheXdslVccTp 1 }

		
		sheXdslVccTpEntry OBJECT-TYPE
			SYNTAX SheXdslVccTpEntry
			MAX-ACCESS not-accessible
			STATUS current
			DESCRIPTION
				"This table contains the VccTp-Configurations. There will be one
				entry for every xdsl-interface available per default. This default
				entry should never be deleted. 
				
				If the underlaying xdsl-line (SublayerIndex) use VDSL2 as currently supported standard,
				all ATM specific configurations in this table for THIS line are don't care!! "
			INDEX { sheXdslVccTpIndex }
			::= { sheXdslVccTpTable 1 }

		
		SheXdslVccTpEntry ::=
			SEQUENCE { 
				sheXdslVccTpIndex
					Integer32,
				sheXdslVccTpSubLayerIndex
					InterfaceIndex,
				sheXdslVccTpNumber
					Integer32,
				sheXdslVccTpVpi
					Integer32,
				sheXdslVccTpVci
					Integer32,
				sheXdslVccTpEncapsulation
					SheXdslVccTpEncapsulationType,
				sheXdslVccTpAdminState
					SheXdslEnableType,
				sheXdslVccTpAlarmSeverityIndex
					SheAlarmSevProfileIndex,
				sheXdslVccTpUsedDslChannel
					SheXdslChannelNumType,
				sheXdslVccTpLoopTest
					SheXdslOamLoopTestType,
				sheXdslVccTpLoopTestResult
					SheXdslVccTpLoopTestResultType,
				sheXdslVccTpPerformanceCountEnabled
					TruthValue
			 }

		sheXdslVccTpIndex OBJECT-TYPE
			SYNTAX Integer32 (1..65565)
			MAX-ACCESS read-only
			STATUS current
			DESCRIPTION
				"Index for that table. The index will follow this rule:
				VccTpIndex = (VccTpSubLayerIndex << 4) + VccTpNumber"
			::= { sheXdslVccTpEntry 1 }

		
		sheXdslVccTpSubLayerIndex OBJECT-TYPE
			SYNTAX InterfaceIndex
			MAX-ACCESS read-only
			STATUS current
			DESCRIPTION
				"ifIndex of the underlaying xdsl-interface."
			::= { sheXdslVccTpEntry 2 }

		
		sheXdslVccTpNumber OBJECT-TYPE
			SYNTAX Integer32 (1..8)
			MAX-ACCESS read-only
			STATUS current
			DESCRIPTION
				"This is the logical number of VccTP on the corresponding interface. Maximum value is 8."
			::= { sheXdslVccTpEntry 3 }

		
		sheXdslVccTpVpi OBJECT-TYPE
			SYNTAX Integer32 (0..255)
			MAX-ACCESS read-only
			STATUS current
			DESCRIPTION
				"The VPI - Value.
				Only valid if sublayer uses a ADSL standard."
			DEFVAL { 1 }
			::= { sheXdslVccTpEntry 4 }

		
		sheXdslVccTpVci OBJECT-TYPE
			SYNTAX Integer32 (32..65535)
			MAX-ACCESS read-only
			STATUS current
			DESCRIPTION
				"The Vci - Value.
				Only valid if sublayer uses a ADSL standard.
				
				NOTE:
				If the NE support atm bonding according G998.1, the usable VCI range for
				ATM channels which should be bonded is restricted to 32..255. Background is,
				that only 8 bit could be used for VCI coding in the modified ATM-Header if
				atm bonding is supported. The other 8 bit's of the VCI field from the standard
				ATM-Header are needed for SID (sequence index) coding.
				The result is, that only VccTp's with a VCI configuration smaller then 256 could
				be used in a bonding scenario!"
			DEFVAL { 32 }
			::= { sheXdslVccTpEntry 5 }

		
		sheXdslVccTpEncapsulation OBJECT-TYPE
			SYNTAX SheXdslVccTpEncapsulationType
			MAX-ACCESS read-only
			STATUS current
			DESCRIPTION
				"Used encapsulation over AAL5.
				Only valid if sublayer uses a ADSL standard."
			DEFVAL { llc }
			::= { sheXdslVccTpEntry 6 }

		
		sheXdslVccTpAdminState OBJECT-TYPE
			SYNTAX SheXdslEnableType
			MAX-ACCESS read-only
			STATUS current
			DESCRIPTION
				"Enable/disable single VccTp. Default value is enabled."
			DEFVAL { 1 }
			::= { sheXdslVccTpEntry 7 }

		
		sheXdslVccTpAlarmSeverityIndex OBJECT-TYPE
			SYNTAX SheAlarmSevProfileIndex
			MAX-ACCESS read-only
			STATUS current
			DESCRIPTION
				"Index to the AlarmSeverityProfileTable. Defines the actual 
				AlarmSeverities for all alarms per VccTp."
			::= { sheXdslVccTpEntry 8 }

		
		sheXdslVccTpUsedDslChannel OBJECT-TYPE
			SYNTAX SheXdslChannelNumType
			MAX-ACCESS read-only
			STATUS current
			DESCRIPTION
				"This attribute defines the usage of a dsl bearer channel by this VccTp.
				The availability of dsl channels depends on the configuration of the underlaying 
				dsl line (VccTpSublayerIndex points to this line).
				
				Valid values for configuration:
				channel1(1)     - always available (default)         
				channel2(2)     - only in dualLatency mode available          
				
				Note:
				Depending on the used DslLineProfile configuration, the following scenarios are possible:
				1. default state:
				->line uses single channel only
				->VccTp's uses always the available channel.
				->A modification of sheXdslVccTpUsedDslChannel will be rejected!
				2. modify line profile
				->line uses dualLatency (channel 2 is configured)
				->VccTp's uses the same channel as before.
				3. modify VccTp entry
				->line uses dualLatency
				->the slected VccTp uses channel1 or channel2 only according to the configuration.
				4. modify line profile
				->line goes back to use single channel1 only
				->VccTp's uses the available channel -> notification will be send if a change is needed."
			DEFVAL { channel1 }
			::= { sheXdslVccTpEntry 9 }

		
		sheXdslVccTpLoopTest OBJECT-TYPE
			SYNTAX SheXdslOamLoopTestType
			MAX-ACCESS read-only
			STATUS current
			DESCRIPTION
				"The type of loop test to be started.
				For EndToEnd loop test loop location ID is FF..FF.
				Only valid if sublayer uses a ADSL standard."
			DEFVAL { 0 }
			::= { sheXdslVccTpEntry 10 }

		
		sheXdslVccTpLoopTestResult OBJECT-TYPE
			SYNTAX SheXdslVccTpLoopTestResultType
			MAX-ACCESS read-only
			STATUS current
			DESCRIPTION
				"Possible values:
				endToEndSuccess(2),
				endToEndFailure(3),
				aborted(4),
				progress(5),
				notAvailable(65535)
				"
			::= { sheXdslVccTpEntry 11 }

		
--  info - IMPL: R2.7->
		sheXdslVccTpPerformanceCountEnabled OBJECT-TYPE
			SYNTAX TruthValue
			MAX-ACCESS read-only
			STATUS current
			DESCRIPTION
				"Enable/Disable performance counters for this VccTp. If enabled, results will be shown
				in sheXdslVccTpPerformanceTable.
				Support with SHE R2.7."
			DEFVAL { false }
			::= { sheXdslVccTpEntry 12 }

		
		sheXdslVccTpControl OBJECT IDENTIFIER ::= { sheXdslVccTp 2 }

		
		sheXdslVccTpControlRequest OBJECT-TYPE
			SYNTAX SheXdslVccControlRequestType
			MAX-ACCESS read-write
			STATUS current
			DESCRIPTION
				"createDslVccTp:
				sheXdslVccTpControlSubLayerIndex
				sheXdslVccTpControlVpi
				sheXdslVccTpControlVci
				sheXdslVccTpControlEncapsulation
				
				deleteDslVccTp:
				sheXdslVccTpControlIndex
				
				modifyDslVccTp:
				sheXdslVccTpControlIndex
				sheXdslVccTpControlVpi
				sheXdslVccTpControlVci
				sheXdslVccTpControlEncapsulation
				sheXdslVccTpControlAlarmSeverityIndex
				
				modifyDslVccTpLoopTest:
				sheXdslVccTpControlIndex
				sheXdslVccTpControlLoopTest
				
				modifyDslVccTpAdminState:
				sheXdslVccTpControlIndex
				sheXdslVccTpControlAdminState
				
				Only in dualLatency mode possible!!
				modifyDslVccTpUsedDslChannel:
				sheXdslVccTpControlIndex
				sheXdslVccTpControlUsedDslChannel
				
				##
				R 2.6
				deleteDslVccTpPerformanceCounters:
				sheXdslVccTpControlIndex
				
				##
				R 2.7
				modifyDslVccTpPerformanceCountEnable:
				sheXdslVccTpControlIndex
				sheXdslVccTpControlPerformanceCountEnabled"
			::= { sheXdslVccTpControl 1 }

		
		sheXdslVccTpControlIndex OBJECT-TYPE
			SYNTAX Integer32
			MAX-ACCESS read-write
			STATUS current
			DESCRIPTION
				"Index of the Table-entry to be configured."
			::= { sheXdslVccTpControl 2 }

		
		sheXdslVccTpControlStatus OBJECT-TYPE
			SYNTAX SheControlStatusType
			MAX-ACCESS read-only
			STATUS current
			DESCRIPTION
				"The status of a user command. 
				"
			::= { sheXdslVccTpControl 3 }

		
		sheXdslVccTpControlTimer OBJECT-TYPE
			SYNTAX Gauge32
			MAX-ACCESS read-only
			STATUS current
			DESCRIPTION
				"The maximum wait time for the manager for a long running user command. 
				"
			::= { sheXdslVccTpControl 4 }

		
		sheXdslVccTpControlReqResult OBJECT-TYPE
			SYNTAX SheXdslControlRequestResultType
			MAX-ACCESS read-only
			STATUS current
			DESCRIPTION
				"The result of the last user command."
			::= { sheXdslVccTpControl 5 }

		
		sheXdslVccTpControlTimeStamp OBJECT-TYPE
			SYNTAX Unsigned32
			UNITS "sec"
			MAX-ACCESS read-only
			STATUS current
			DESCRIPTION
				"The time stamp of the last command (end of command)."
			::= { sheXdslVccTpControl 6 }

		
		sheXdslVccTpControlSubLayerIndex OBJECT-TYPE
			SYNTAX InterfaceIndex
			MAX-ACCESS read-write
			STATUS current
			DESCRIPTION
				"IfIndex of the underlaying dsl-interface."
			::= { sheXdslVccTpControl 7 }

		
		sheXdslVccTpControlVpi OBJECT-TYPE
			SYNTAX Integer32 (0..255)
			MAX-ACCESS read-write
			STATUS current
			DESCRIPTION
				"Vpi"
			::= { sheXdslVccTpControl 8 }

		
		sheXdslVccTpControlVci OBJECT-TYPE
			SYNTAX Integer32 (32..65535)
			MAX-ACCESS read-write
			STATUS current
			DESCRIPTION
				"Vci
				
				NOTE:
				If the NE support atm bonding according G998.1, the usable VCI range for
				ATM channels which should be bonded is restricted to 32..255. Background is,
				that only 8 bit could be used for VCI coding in the modified ATM-Header if
				atm bonding is supported. The other 8 bit's of the VCI field from the standard
				ATM-Header are needed for SID (sequence index) coding.
				The result is, that only VccTp's with a VCI configuration smaller then 256 could
				be used in a bonding scenario!"
			::= { sheXdslVccTpControl 9 }

		
		sheXdslVccTpControlEncapsulation OBJECT-TYPE
			SYNTAX SheXdslVccTpEncapsulationType
			MAX-ACCESS read-write
			STATUS current
			DESCRIPTION
				"Used encapsulation over AAL5."
			::= { sheXdslVccTpControl 10 }

		
		sheXdslVccTpControlAdminState OBJECT-TYPE
			SYNTAX SheXdslEnableType
			MAX-ACCESS read-write
			STATUS current
			DESCRIPTION
				"look at table"
			::= { sheXdslVccTpControl 11 }

		
		sheXdslVccTpControlAlarmSeverityIndex OBJECT-TYPE
			SYNTAX SheAlarmSevProfileIndex
			MAX-ACCESS read-write
			STATUS current
			DESCRIPTION
				"Index of the used AlarmSeverityProfile."
			::= { sheXdslVccTpControl 12 }

		
		sheXdslVccTpControlUsedDslChannel OBJECT-TYPE
			SYNTAX SheXdslChannelNumType
			MAX-ACCESS read-write
			STATUS current
			DESCRIPTION
				"Look at table.       
				In singleLatency mode , no configuration is possible."
			::= { sheXdslVccTpControl 13 }

		
		sheXdslVccTpControlLoopTest OBJECT-TYPE
			SYNTAX SheXdslOamLoopTestType
			MAX-ACCESS read-write
			STATUS current
			DESCRIPTION
				"Actual LoopTest-Value. Only None or endToEnd will be accepted."
			::= { sheXdslVccTpControl 14 }

		
--  info - IMPL: R2.7->
		sheXdslVccTpControlPerformanceCountEnabled OBJECT-TYPE
			SYNTAX TruthValue
			MAX-ACCESS read-write
			STATUS current
			DESCRIPTION
				"Enable/Disable performance counters for this VccTp. If enabled, results will be shown
				in sheXdslVccTpPerformanceTable.
				
				Support with SHE R2.7."
			::= { sheXdslVccTpControl 15 }

		
		sheXdslVccTpNotifications OBJECT IDENTIFIER ::= { sheXdslVccTp 3 }

		
		sheXdslVccTpCreated NOTIFICATION-TYPE
			OBJECTS { sheXdslVccTpControlIndex, sheXdslVccTpControlTimeStamp, sheXdslVccTpControlSubLayerIndex, sheXdslVccTpControlVpi, sheXdslVccTpControlVci, 
				sheXdslVccTpControlEncapsulation, sheXdslVccTpControlAdminState, sheXdslVccTpControlAlarmSeverityIndex, sheXdslVccTpControlLoopTest, sheXdslVccTpControlUsedDslChannel
				 }
			STATUS current
			DESCRIPTION 
				"Configuration notification."
			::= { sheXdslVccTpNotifications 1 }

		
		sheXdslVccTpModified NOTIFICATION-TYPE
			OBJECTS { sheXdslVccTpControlIndex, sheXdslVccTpControlTimeStamp, sheXdslVccTpControlSubLayerIndex, sheXdslVccTpControlVpi, sheXdslVccTpControlVci, 
				sheXdslVccTpControlEncapsulation, sheXdslVccTpControlAlarmSeverityIndex }
			STATUS current
			DESCRIPTION 
				"Configuration notification."
			::= { sheXdslVccTpNotifications 2 }

		
		sheXdslVccTpDeleted NOTIFICATION-TYPE
			OBJECTS { sheXdslVccTpControlIndex, sheXdslVccTpControlTimeStamp }
			STATUS current
			DESCRIPTION 
				"Configuration notification."
			::= { sheXdslVccTpNotifications 3 }

		
		sheXdslVccRDIAlarm NOTIFICATION-TYPE
			OBJECTS { sheAlarmTimeAndDate, sheAlarmReportingSource, sheAlarmReportingSourceType, sheAlarmSeverity }
			STATUS current
			DESCRIPTION 
				"RDI detected."
			::= { sheXdslVccTpNotifications 4 }

		
		sheXdslVccAISAlarm NOTIFICATION-TYPE
			OBJECTS { sheAlarmTimeAndDate, sheAlarmReportingSource, sheAlarmReportingSourceType, sheAlarmSeverity }
			STATUS current
			DESCRIPTION 
				"AIS detected. "
			::= { sheXdslVccTpNotifications 5 }

		
		sheXdslVccTpConfigurationFailed NOTIFICATION-TYPE
			OBJECTS { sheXdslVccTpControlRequest, sheXdslVccTpControlIndex, sheXdslVccTpControlStatus, sheXdslVccTpControlTimer, sheXdslVccTpControlReqResult, 
				sheXdslVccTpControlTimeStamp, sheXdslVccTpControlSubLayerIndex, sheXdslVccTpControlVpi, sheXdslVccTpControlVci, sheXdslVccTpControlEncapsulation, 
				sheXdslVccTpControlAdminState, sheXdslVccTpControlAlarmSeverityIndex, sheXdslVccTpControlUsedDslChannel, sheXdslVccTpControlLoopTest }
			STATUS current
			DESCRIPTION 
				"Notification in case of failed VccTp-Configuration."
			::= { sheXdslVccTpNotifications 6 }

		
		sheXdslVccTpAdminStateChanged NOTIFICATION-TYPE
			OBJECTS { sheXdslVccTpControlIndex, sheXdslVccTpControlTimeStamp, sheXdslVccTpControlAdminState }
			STATUS current
			DESCRIPTION 
				"Configuration notification."
			::= { sheXdslVccTpNotifications 7 }

		
		sheXdslVccTpUsedDslChannelChanged NOTIFICATION-TYPE
			OBJECTS { sheXdslVccTpControlIndex, sheXdslVccTpControlTimeStamp, sheXdslVccTpControlUsedDslChannel }
			STATUS current
			DESCRIPTION 
				"Modification trap."
			::= { sheXdslVccTpNotifications 8 }

		
		sheXdslVccTpLoopTestModified NOTIFICATION-TYPE
			OBJECTS { sheXdslVccTpControlIndex, sheXdslVccTpControlTimeStamp, sheXdslVccTpControlLoopTest, sheXdslVccTpLoopTestResult }
			STATUS current
			DESCRIPTION 
				"Configuration notification."
			::= { sheXdslVccTpNotifications 9 }

		
		sheXdslVccTpPerformanceCountersCleared NOTIFICATION-TYPE
			OBJECTS { sheXdslVccTpControlIndex, sheXdslVccTpControlTimeStamp }
			STATUS current
			DESCRIPTION 
				"Configuration notification."
			::= { sheXdslVccTpNotifications 10 }

		
		sheXdslVccTpPerformanceCountEnableModified NOTIFICATION-TYPE
			OBJECTS { sheXdslVccTpControlIndex, sheXdslVccTpControlTimeStamp, sheXdslVccTpControlPerformanceCountEnabled }
			STATUS current
			DESCRIPTION 
				"Configuration notification."
			::= { sheXdslVccTpNotifications 11 }

		
		sheXdslVccTpPerformanceTable OBJECT-TYPE
			SYNTAX SEQUENCE OF SheXdslVccTpPerformanceEntry
			MAX-ACCESS not-accessible
			STATUS current
			DESCRIPTION
				"The VccTpPerformance-Table."
			::= { sheXdslVccTp 4 }

		
		sheXdslVccTpPerformanceEntry OBJECT-TYPE
			SYNTAX SheXdslVccTpPerformanceEntry
			MAX-ACCESS not-accessible
			STATUS current
			DESCRIPTION
				"This table contains the VccTp-PerformanceCounters.
				Counters could be reseted by command 
				deleteDslVccTpPerformanceCounters via sheXdslVccTpControl-Group."
			INDEX { sheXdslVccTpIndex }
			::= { sheXdslVccTpPerformanceTable 1 }

		
		SheXdslVccTpPerformanceEntry ::=
			SEQUENCE { 
				sheXdslVccTpIngressBytes
					Counter64,
				sheXdslVccTpIngressPackets
					Counter32,
				sheXdslVccTpIngressDropedPackets
					Counter32,
				sheXdslVccTpEgressBytes
					Counter64,
				sheXdslVccTpEgressPackets
					Counter32,
				sheXdslVccTpEgressDropedPackets
					Counter32
			 }

		sheXdslVccTpIngressBytes OBJECT-TYPE
			SYNTAX Counter64
			MAX-ACCESS read-only
			STATUS current
			DESCRIPTION
				"Ingress byte counter for this VccTp."
			::= { sheXdslVccTpPerformanceEntry 1 }

		
		sheXdslVccTpIngressPackets OBJECT-TYPE
			SYNTAX Counter32
			MAX-ACCESS read-only
			STATUS current
			DESCRIPTION
				"Ingress packet counter for this VccTp."
			::= { sheXdslVccTpPerformanceEntry 2 }

		
		sheXdslVccTpIngressDropedPackets OBJECT-TYPE
			SYNTAX Counter32
			MAX-ACCESS read-only
			STATUS current
			DESCRIPTION
				"Ingress droped packet counter for this VccTp. 
				Possible reason's for dropping are CRC errors, reassemply errors or packet could
				not process by Convergate FW."
			::= { sheXdslVccTpPerformanceEntry 3 }

		
		sheXdslVccTpEgressBytes OBJECT-TYPE
			SYNTAX Counter64
			MAX-ACCESS read-only
			STATUS current
			DESCRIPTION
				"Egress byte counter for this VccTp."
			::= { sheXdslVccTpPerformanceEntry 4 }

		
		sheXdslVccTpEgressPackets OBJECT-TYPE
			SYNTAX Counter32
			MAX-ACCESS read-only
			STATUS current
			DESCRIPTION
				"Egress packet counter for this VccTp."
			::= { sheXdslVccTpPerformanceEntry 5 }

		
		sheXdslVccTpEgressDropedPackets OBJECT-TYPE
			SYNTAX Counter32
			MAX-ACCESS read-only
			STATUS current
			DESCRIPTION
				"Egress droped packet counter for this VccTp. 
				Possible reason's for dropping are CRC errors, reassemply errors or packet could
				not process by Convergate FW."
			::= { sheXdslVccTpPerformanceEntry 6 }

		
		sheXdslVccTpConformance OBJECT IDENTIFIER ::= { sheXdslVccTp 100 }

		
		sheXdslVccTpCompliances OBJECT IDENTIFIER ::= { sheXdslVccTpConformance 1 }

		
--  this module
		sheXdslVccTpCompliance MODULE-COMPLIANCE
			STATUS current
			DESCRIPTION 
				"Description."
			MODULE -- this module
				MANDATORY-GROUPS { sheXdslVccTpGroup, sheXdslVccTpControlGroup, sheXdslVccTpNotificationGroup }
			::= { sheXdslVccTpCompliances 1 }

		
		sheXdslVccTpGroups OBJECT IDENTIFIER ::= { sheXdslVccTpConformance 2 }

		
		sheXdslVccTpGroup OBJECT-GROUP
			OBJECTS { sheXdslVccTpIndex, sheXdslVccTpSubLayerIndex, sheXdslVccTpNumber, sheXdslVccTpVpi, sheXdslVccTpVci, 
				sheXdslVccTpLoopTest, sheXdslVccTpLoopTestResult, sheXdslVccTpAlarmSeverityIndex, sheXdslVccTpAdminState, sheXdslVccTpIngressBytes, 
				sheXdslVccTpIngressPackets, sheXdslVccTpIngressDropedPackets, sheXdslVccTpEgressBytes, sheXdslVccTpEgressPackets, sheXdslVccTpEgressDropedPackets, 
				sheXdslVccTpPerformanceCountEnabled, sheXdslVccTpUsedDslChannel, sheXdslVccTpEncapsulation }
			STATUS current
			DESCRIPTION 
				"Description."
			::= { sheXdslVccTpGroups 1 }

		
		sheXdslVccTpControlGroup OBJECT-GROUP
			OBJECTS { sheXdslVccTpControlRequest, sheXdslVccTpControlIndex, sheXdslVccTpControlStatus, sheXdslVccTpControlTimer, sheXdslVccTpControlReqResult, 
				sheXdslVccTpControlTimeStamp, sheXdslVccTpControlSubLayerIndex, sheXdslVccTpControlVpi, sheXdslVccTpControlVci, sheXdslVccTpControlLoopTest, 
				sheXdslVccTpControlAlarmSeverityIndex, sheXdslVccTpControlAdminState, sheXdslVccTpControlPerformanceCountEnabled, sheXdslVccTpControlUsedDslChannel, sheXdslVccTpControlEncapsulation
				 }
			STATUS current
			DESCRIPTION 
				"Description."
			::= { sheXdslVccTpGroups 2 }

		
		sheXdslVccTpNotificationGroup NOTIFICATION-GROUP
			NOTIFICATIONS { sheXdslVccTpCreated, sheXdslVccTpModified, sheXdslVccTpDeleted, sheXdslVccRDIAlarm, sheXdslVccAISAlarm, 
				sheXdslVccTpConfigurationFailed, sheXdslVccTpAdminStateChanged, sheXdslVccTpUsedDslChannelChanged, sheXdslVccTpLoopTestModified, sheXdslVccTpPerformanceCountersCleared, 
				sheXdslVccTpPerformanceCountEnableModified }
			STATUS current
			DESCRIPTION 
				"Description."
			::= { sheXdslVccTpGroups 3 }

		
		sheXdslConformance OBJECT IDENTIFIER ::= { sheXdslLineMib 100 }

		
		sheXdslCompliances OBJECT IDENTIFIER ::= { sheXdslConformance 1 }

		
--  this module
		sheXdslLineMibCompliance MODULE-COMPLIANCE
			STATUS current
			DESCRIPTION 
				"The compliance statement for SNMP entities which 
				manage XDSL interfaces in SHE."
			MODULE -- this module
				MANDATORY-GROUPS { sheXdslGroup, sheXdslControlGroup, sheXdslNotificationGroup }
			::= { sheXdslCompliances 1 }

		
		sheXdslGroups OBJECT IDENTIFIER ::= { sheXdslConformance 2 }

		
		sheXdslGroup OBJECT-GROUP
			OBJECTS { sheXdslLineConfProfile, sheXdslLineAlarmConfProfile, sheXdslPhysInvSerialNumber, sheXdslPhysInvVersionNumber, sheXdslPhysCurrStatus, 
				sheXdslPhysCurrOutputPwr, sheXdslChanInterleaveDelay, sheXdslChanCurrTxRate, sheXdslPerfDataValidIntervals, sheXdslPerfDataInvalidIntervals, 
				sheXdslPerfDataLofs, sheXdslPerfDataLoss, sheXdslPerfDataLprs, sheXdslPerfDataLols, sheXdslPerfDataESs, 
				sheXdslPerfDataSESs, sheXdslPerfDataUASs, sheXdslPerfDataInits, sheXdslPerfDataCurr15MinTimeElapsed, sheXdslPerfDataCurr15MinLofs, 
				sheXdslPerfDataCurr15MinLoss, sheXdslPerfDataCurr15MinLprs, sheXdslPerfDataCurr15MinLols, sheXdslPerfDataCurr15MinESs, sheXdslPerfDataCurr15MinSESs, 
				sheXdslPerfDataCurr15MinUASs, sheXdslPerfDataCurr15MinInits, sheXdslPerfData1DayValidIntervals, sheXdslPerfData1DayInvalidIntervals, sheXdslPerfDataCurr1DayTimeElapsed, 
				sheXdslPerfDataCurr1DayLofs, sheXdslPerfDataCurr1DayLoss, sheXdslPerfDataCurr1DayLprs, sheXdslPerfDataCurr1DayLols, sheXdslPerfDataCurr1DayESs, 
				sheXdslPerfDataCurr1DaySESs, sheXdslPerfDataCurr1DayUASs, sheXdslPerfDataCurr1DayInits, sheXdslPerfIntervalLoss, sheXdslPerfIntervalLprs, 
				sheXdslPerfIntervalLols, sheXdslPerfIntervalESs, sheXdslPerfIntervalSESs, sheXdslPerfIntervalUASs, sheXdslPerfIntervalInits, 
				sheXdslPerf1DayIntervalMoniSecs, sheXdslPerf1DayIntervalLofs, sheXdslPerf1DayIntervalLoss, sheXdslPerf1DayIntervalLprs, sheXdslPerf1DayIntervalLols, 
				sheXdslPerf1DayIntervalESs, sheXdslPerf1DayIntervalSESs, sheXdslPerf1DayIntervalUASs, sheXdslPerf1DayIntervalInits, sheXdslChanValidIntervals, 
				sheXdslChanInvalidIntervals, sheXdslChanCurr15MinTimeElapsed, sheXdslChan1DayValidIntervals, sheXdslChan1DayInvalidIntervals, sheXdslChanCurr1DayTimeElapsed, 
				sheXdslChan1DayIntervalMoniSecs, sheXdslLineConfProfileName, sheXdslLineConfDownRateMode, sheXdslLineConfUpRateMode, sheXdslLineConfDownMaxPwr, 
				sheXdslLineConfUpMaxPwr, sheXdslLineConfDownMaxSnrMgn, sheXdslLineConfDownMinSnrMgn, sheXdslLineConfDownTargetSnrMgn, sheXdslLineConfUpMaxSnrMgn, 
				sheXdslLineConfUpMinSnrMgn, sheXdslLineConfUpTargetSnrMgn, sheXdslLineAlarmConfProfileName, sheXdslThresh15MinLofs, sheXdslThresh15MinLoss, 
				sheXdslThresh15MinLprs, sheXdslThresh15MinLols, sheXdslThresh15MinESs, sheXdslThresh15MinSESs, sheXdslThresh15MinUASs, 
				sheXdslLineXtucCapability, sheXdslLineXturCapability, sheXdslLineConfExtnDownBitSwap, sheXdslLineConfExtnUpBitSwap, sheXdslLineConfExtnXtucPwrMgmtL0Time, 
				sheXdslLineConfExtnXtucPwrMgmtL2Time, sheXdslLineConfExtnXtucPwrMgmtL2ATPR, sheXdslLineConfExtnXtucPwrMgmtMode, sheXdslChanIntervalValidData, sheXdslChanIntervalEndTime, 
				sheXdslPerfIntervalLofs, sheXdslPerfIntervalValidData, sheXdslPerfIntervalEndTime, sheXdslInitFailureNotifyEnable, sheXdslLineGsAction, 
				sheXdslPhysActualStandard, sheXdslChanCurrAtmStatus, sheXdslLineXtuCurrCapability, sheXdslCustomNotchProfileName, sheXdslCustomNotchProfileUsedNotches, 
				sheXdslCustomNotchProfileStartIndex01, sheXdslCustomNotchProfileStopIndex01, sheXdslCustomNotchProfileStartIndex02, sheXdslCustomNotchProfileStopIndex02, sheXdslCustomNotchProfileStartIndex03, 
				sheXdslCustomNotchProfileStopIndex03, sheXdslCustomNotchProfileStartIndex04, sheXdslCustomNotchProfileStopIndex04, sheXdslCustomNotchProfileStartIndex05, sheXdslCustomNotchProfileStopIndex05, 
				sheXdslCustomNotchProfileStartIndex06, sheXdslCustomNotchProfileStopIndex06, sheXdslCustomNotchProfileStartIndex07, sheXdslCustomNotchProfileStopIndex07, sheXdslCustomNotchProfileStartIndex08, 
				sheXdslCustomNotchProfileStopIndex08, sheXdslPsdMaskProfileName, sheXdslPsdMaskProfileUsedBreakpoints, sheXdslPsdMaskProfileSubcarrierIndex01, sheXdslPsdMaskProfilePsdLevel01, 
				sheXdslPsdMaskProfileSubcarrierIndex02, sheXdslPsdMaskProfilePsdLevel02, sheXdslPsdMaskProfileSubcarrierIndex03, sheXdslPsdMaskProfilePsdLevel03, sheXdslPsdMaskProfileSubcarrierIndex04, 
				sheXdslPsdMaskProfilePsdLevel04, sheXdslPsdMaskProfileSubcarrierIndex05, sheXdslPsdMaskProfilePsdLevel05, sheXdslPsdMaskProfileSubcarrierIndex06, sheXdslPsdMaskProfilePsdLevel06, 
				sheXdslPsdMaskProfileSubcarrierIndex07, sheXdslPsdMaskProfilePsdLevel07, sheXdslPsdMaskProfileSubcarrierIndex08, sheXdslPsdMaskProfilePsdLevel08, sheXdslPsdMaskProfileSubcarrierIndex09, 
				sheXdslPsdMaskProfilePsdLevel09, sheXdslPsdMaskProfileSubcarrierIndex10, sheXdslPsdMaskProfilePsdLevel10, sheXdslPsdMaskProfileSubcarrierIndex11, sheXdslPsdMaskProfilePsdLevel11, 
				sheXdslPsdMaskProfileSubcarrierIndex12, sheXdslPsdMaskProfilePsdLevel12, sheXdslPsdMaskProfileSubcarrierIndex13, sheXdslPsdMaskProfilePsdLevel13, sheXdslPsdMaskProfileSubcarrierIndex14, 
				sheXdslPsdMaskProfilePsdLevel14, sheXdslPsdMaskProfileSubcarrierIndex15, sheXdslPsdMaskProfilePsdLevel15, sheXdslPsdMaskProfileSubcarrierIndex16, sheXdslPsdMaskProfilePsdLevel16, 
				sheXdslPsdMaskProfileSubcarrierIndex17, sheXdslPsdMaskProfilePsdLevel17, sheXdslPsdMaskProfileSubcarrierIndex18, sheXdslPsdMaskProfilePsdLevel18, sheXdslPsdMaskProfileSubcarrierIndex19, 
				sheXdslPsdMaskProfilePsdLevel19, sheXdslPsdMaskProfileSubcarrierIndex20, sheXdslPsdMaskProfilePsdLevel20, sheXdslPsdMaskProfileSubcarrierIndex21, sheXdslPsdMaskProfilePsdLevel21, 
				sheXdslPsdMaskProfileSubcarrierIndex22, sheXdslPsdMaskProfilePsdLevel22, sheXdslPsdMaskProfileSubcarrierIndex23, sheXdslPsdMaskProfilePsdLevel23, sheXdslPsdMaskProfileSubcarrierIndex24, 
				sheXdslPsdMaskProfilePsdLevel24, sheXdslPsdMaskProfileSubcarrierIndex25, sheXdslPsdMaskProfilePsdLevel25, sheXdslPsdMaskProfileSubcarrierIndex26, sheXdslPsdMaskProfilePsdLevel26, 
				sheXdslPsdMaskProfileSubcarrierIndex27, sheXdslPsdMaskProfilePsdLevel27, sheXdslPsdMaskProfileSubcarrierIndex28, sheXdslPsdMaskProfilePsdLevel28, sheXdslPsdMaskProfileSubcarrierIndex29, 
				sheXdslPsdMaskProfilePsdLevel29, sheXdslPsdMaskProfileSubcarrierIndex30, sheXdslPsdMaskProfilePsdLevel30, sheXdslPsdMaskProfileSubcarrierIndex31, sheXdslPsdMaskProfilePsdLevel31, 
				sheXdslPsdMaskProfileSubcarrierIndex32, sheXdslPsdMaskProfilePsdLevel32, sheXdslLineConfExtnCustomSubcarrierMask, sheXdslLineConfExtnUseCustomSubcarrierMask, sheXdslLineConfUseVdsl2ProfileNumber, 
				sheXdslLineConfMaxUpRxPower, sheXdslLineConfVtucDownshiftSnrMgn, sheXdslLineConfVtucUpshiftSnrMgn, sheXdslLineConfVtucMinDownshiftTime, sheXdslLineConfVtucMinUpshiftTime, 
				sheXdslLineConfVturDownshiftSnrMgn, sheXdslLineConfVturUpshiftSnrMgn, sheXdslLineConfVturMinDownshiftTime, sheXdslLineConfVturMinUpshiftTime, sheXdslLineConfGsStandard, 
				sheXdslCustomNotchProfileIndex, sheXdslPsdMaskProfileIndex, sheXdslPhysSide, sheXdslPerfIntervalNumber, sheXdslPerf1DayIntervalNumber, 
				sheXdslChanIntervalNumber, sheXdslChan1DayIntervalNumber, sheXdslLineConfProfileIndex, sheXdslLineAlarmConfProfileIndex, sheXdslLineConfExtnDownPboMus, 
				sheXdslLineConfExtnDownPboFMin, sheXdslLineConfExtnDownPboFMax, sheXdslLineConfExtnDownPboEsel, sheXdslPhysInvHSVendorID, sheXdslPhysInvSystemVendorID, 
				sheXdslLineBandDirection, sheXdslLineStatusLnAtten, sheXdslLineStatusSigAtten, sheXdslLineConfExtnMaxDownNomPsd, sheXdslLineConfExtnMaxUpNomPsd, 
				sheXdslLineAlarmOperationalStateNotifyEnable, sheXdslPhysCurrOperationalState, sheXdslLineStatusSnrMargin, sheXdslLineConfExtnDownPboEpsd, sheXdslLineConfExtnDownPboEScmA, 
				sheXdslLineConfExtnDownPboEScmB, sheXdslLineConfExtnDownPboEScmC, sheXdslLineConfExtnUpPboA, sheXdslLineConfExtnXtucPwrMgmtL2ATPRT, sheXdslLineConfExtnDownPboEselMin, 
				sheXdslLineConfExtnUpPboB, sheXdslChanCurrCrc, sheXdslChanCurrInp, sheXdslChanCurrFec, sheXdslLineConfExtnDownPboMof, 
				sheXdslLineLdsf, sheXdslLineLdsfResult, sheXdslCustomNotchProfileStartIndex09, sheXdslCustomNotchProfileStopIndex09, sheXdslCustomNotchProfileStartIndex10, 
				sheXdslCustomNotchProfileStopIndex10, sheXdslCustomNotchProfileStartIndex11, sheXdslCustomNotchProfileStopIndex11, sheXdslCustomNotchProfileStartIndex12, sheXdslCustomNotchProfileStopIndex12, 
				sheXdslCustomNotchProfileStartIndex13, sheXdslCustomNotchProfileStopIndex13, sheXdslCustomNotchProfileStartIndex14, sheXdslCustomNotchProfileStopIndex14, sheXdslCustomNotchProfileStartIndex15, 
				sheXdslCustomNotchProfileStopIndex15, sheXdslCustomNotchProfileStartIndex16, sheXdslCustomNotchProfileStopIndex16, sheXdslSCDnIndex, sheXdslSCDnStatusBitsAlloc, 
				sheXdslSCDnStatusGainAlloc, sheXdslSCUpIndex, sheXdslSCUpStatusBitsAlloc, sheXdslSCUpStatusGainAlloc, sheXdslSCGDnIndex, 
				sheXdslSCGDnStatusSnr, sheXdslSCGDnStatusHLinReal, sheXdslSCGDnStatusHLinImg, sheXdslSCGDnStatusHLog, sheXdslSCGDnStatusQln, 
				sheXdslSCGUpIndex, sheXdslSCGUpStatusSnr, sheXdslSCGUpStatusHLinReal, sheXdslSCGUpStatusHLinImg, sheXdslSCGUpStatusHLog, 
				sheXdslSCGUpStatusQln, sheXdslLineCustomDownPsdMaskProfile, sheXdslLineCustomUpPsdMaskProfile, sheXdslLineCustomNotchProfile, sheXdslLineConfExtnProfileUpPboBoostMode, 
				sheXdslLineRfiBandMask, sheXdslLineGsStandard, sheXdslPhysPwrMgmtState, sheXdslPsdMaskProfileUsage, sheXdslLineConfExtnProfileUpPboKL, 
				sheXdslLineConfExtnProfileUpPboKO, sheXdslLineBandNumber, sheXdslChanNum, sheXdslChannelProfileIndex, sheXdslChannelProfileName, 
				sheXdslChannelProfileMinDataRateDs, sheXdslChannelProfileMinDataRateUs, sheXdslChannelProfileMinResDataRateDs, sheXdslChannelProfileMinResDataRateUs, sheXdslChannelProfileMaxDataRateDs, 
				sheXdslChannelProfileMaxDataRateUs, sheXdslChannelProfileMinDataRateLowPwrDs, sheXdslChannelProfileMaxBerDs, sheXdslChannelProfileMaxBerUs, sheXdslChannelProfileMaxInterleaveDelayDs, 
				sheXdslChannelProfileMaxInterleaveDelayUs, sheXdslChannelProfileMinINPDs, sheXdslLineUpPboKLE, sheXdslChannelProfileMinINPUs, sheXdslLineConfUseVdsl2BandPlanNumber, 
				sheXdslChannelProfileThresholdRateDownShiftDs, sheXdslChannelProfileThresholdRateUpShiftDs, sheXdslChannelProfileThresholdRateDownShiftUs, sheXdslLinePMSF, sheXdslLineConfExtnMsgMinUp, 
				sheXdslLineConfExtnMsgMinDown, sheXdslChanCurrHec, sheXdslChanCrcCount, sheXdslChanHecCount, sheXdslChanDelineatedTotalCellCount, 
				sheXdslChanUserTotalCellCount, sheXdslChanIdleCellBitErrorCount, sheXdslChanCurr15MinCrcCount, sheXdslChanCurr15MinHecCount, sheXdslChanCurr15MinDelineatedTotalCellCount, 
				sheXdslChanCurr15MinUserTotalCellCount, sheXdslChanCurr15MinIdleCellBitErrorCount, sheXdslChanCurr1DayCrcCount, sheXdslChanCurr1DayHecCount, sheXdslChanCurr1DayDelineatedTotalCellCount, 
				sheXdslChanCurr1DayUserTotalCellCount, sheXdslChanCurr1DayIdleCellBitErrorCount, sheXdslChanIntervalCrcCount, sheXdslChanIntervalHecCount, sheXdslChanIntervalDelineatedTotalCellCount, 
				sheXdslChanIntervalUserTotalCellCount, sheXdslChanIntervalIdleCellBitErrorCount, sheXdslChan1DayIntervalCrcCount, sheXdslChan1DayIntervalHecCount, sheXdslChan1DayIntervalDelineatedTotalCellCount, 
				sheXdslChan1DayIntervalUserTotalCellCount, sheXdslChan1DayIntervalIdleCellBitErrorCount, sheXdslLineConfExtnUsPsdMaskSelection, sheXdslLineConfExtnCustomUsSubcarrierMask, sheXdslShowtimeStatusMRefPsdDs, 
				sheXdslShowtimeStatusMRefPsdUs, sheXdslPhysLastStateTransmitted, sheXdslLineConfExtnSnrModeDown, sheXdslLineConfExtnSnrModeUp, sheXdslLineConfExtnTxRefVnDown, 
				sheXdslLineConfExtnTxRefVnUp, sheXdslPhysActualPsd, sheXdslLinePerformance15MinHistoryEnabled, sheXdslLinePerformance1DayHistoryEnabled, sheXdslPhysSelfTestResult, 
				sheXdslChannelProfileThresholdRateUpShiftUs, sheXdslLineForceINPDs, sheXdslLineForceINPUs, sheXdslLineChan1ConfProfile, sheXdslLineChan1RaRatioDs, 
				sheXdslLineChan1RaRatioUs, sheXdslLineChan2ConfProfile, sheXdslChanFecCount, sheXdslChanCodingViolationCount, sheXdslChanCurr15MinFecCount, 
				sheXdslChanCurr15MinCodingViolationCount, sheXdslChanCurr1DayFecCount, sheXdslChanCurr1DayCodingViolationCount, sheXdslChanIntervalFecCount, sheXdslChanIntervalCodingViolationCount, 
				sheXdslChan1DayIntervalFecCount, sheXdslPerf1DayIntervalEndTime, sheXdslChan1DayIntervalEndTime, sheXdslChan1DayIntervalCodingViolationCount, sheXdslPhysCurrAttainableDataRate, 
				sheXdslPhysCurrDataRate, sheXdslPhysPrevDataRate, sheXdslLineConfigViolationCheckStatus, sheXdslLineAlarmConfigViolationCheck }
			STATUS current
			DESCRIPTION 
				"A collection of objects providing information about a XDSL Line."
			::= { sheXdslGroups 1 }

		
		sheXdslControlGroup OBJECT-GROUP
			OBJECTS { sheXdslLineControlRequest, sheXdslLineControlIndex, sheXdslPsdMaskProfileControlUsage, sheXdslLineControlStatus, sheXdslLineControlTimer, 
				sheXdslLineControlReqResult, sheXdslLineControlTimeStamp, sheXdslLineControlConfProfile, sheXdslLineControlAlarmConfProfile, sheXdslLineConfProfileControlRequest, 
				sheXdslLineConfProfileControlIndex, sheXdslLineConfProfileControlStatus, sheXdslLineConfProfileControlTimer, sheXdslLineConfProfileControlReqResult, sheXdslLineConfProfileControlTimeStamp, 
				sheXdslLineConfProfileControlName, sheXdslLineConfProfileControlDownRateMode, sheXdslLineConfProfileControlUpRateMode, sheXdslLineConfProfileControlDownMaxPwr, sheXdslLineConfProfileControlUpMaxPwr, 
				sheXdslLineConfProfileControlDownMaxSnrMgn, sheXdslLineConfProfileControlDownMinSnrMgn, sheXdslLineConfProfileControlDownTargetSnrMgn, sheXdslLineConfProfileControlUpMaxSnrMgn, sheXdslLineConfProfileControlUpMinSnrMgn, 
				sheXdslLineConfProfileControlUpTargetSnrMgn, sheXdslLineAlarmConfProfileControlRequest, sheXdslLineAlarmConfProfileControlIndex, sheXdslLineAlarmConfProfileControlStatus, sheXdslLineAlarmConfProfileControlTimer, 
				sheXdslLineAlarmConfProfileControlReqResult, sheXdslLineAlarmConfProfileControlTimeStamp, sheXdslLineAlarmConfProfileControlName, sheXdslLineAlarmConfProfileControlThresh15MinLofs, sheXdslLineAlarmConfProfileControlThresh15MinLoss, 
				sheXdslLineAlarmConfProfileControlThresh15MinLprs, sheXdslLineAlarmConfProfileControlThresh15MinLols, sheXdslLineAlarmConfProfileControlThresh15MinESs, sheXdslLineAlarmConfProfileControlThresh15MinSESs, sheXdslLineAlarmConfProfileControlThresh15MinUASs, 
				sheXdslLineAlarmConfProfileControlInitFailureNotifyEnable, sheXdslLineControlGsAction, sheXdslLineConfProfileControlGsStandard, sheXdslLineConfExtnProfileControlRequest, sheXdslLineConfExtnProfileControlIndex, 
				sheXdslLineConfExtnProfileControlStatus, sheXdslLineConfExtnProfileControlTimer, sheXdslLineConfExtnProfileControlReqResult, sheXdslLineConfExtnProfileControlTimeStamp, sheXdslLineConfExtnProfileControlDownBitSwap, 
				sheXdslLineConfExtnProfileControlUpBitSwap, sheXdslLineConfExtnProfileControlXtucPwrMgmtL0Time, sheXdslLineConfExtnProfileControlXtucPwrMgmtL2Time, sheXdslLineConfExtnProfileControlXtucPwrMgmtL2ATPR, sheXdslLineConfExtnProfileControlXtucPwrMgmtMode, 
				sheXdslLineConfProfileControlMaxUpRxPower, sheXdslLineConfProfileControlVtucDownshiftSnrMgn, sheXdslLineConfProfileControlVtucUpshiftSnrMgn, sheXdslLineConfProfileControlVtucMinDownshiftTime, sheXdslLineConfProfileControlVtucMinUpshiftTime, 
				sheXdslLineConfProfileControlVturDownshiftSnrMgn, sheXdslLineConfProfileControlVturUpshiftSnrMgn, sheXdslLineConfProfileControlVturMinDownshiftTime, sheXdslLineConfProfileControlVturMinUpshiftTime, sheXdslCustomNotchProfileControlRequest, 
				sheXdslCustomNotchProfileControlIndex, sheXdslCustomNotchProfileControlStatus, sheXdslCustomNotchProfileControlTimer, sheXdslCustomNotchProfileControlReqResult, sheXdslCustomNotchProfileControlTimeStamp, 
				sheXdslCustomNotchProfileControlName, sheXdslCustomNotchProfileControlUsedNotches, sheXdslCustomNotchProfileControlStartIndex01, sheXdslCustomNotchProfileControlStopIndex01, sheXdslCustomNotchProfileControlStartIndex02, 
				sheXdslCustomNotchProfileControlStopIndex02, sheXdslCustomNotchProfileControlStartIndex03, sheXdslCustomNotchProfileControlStopIndex03, sheXdslCustomNotchProfileControlStartIndex04, sheXdslCustomNotchProfileControlStopIndex04, 
				sheXdslCustomNotchProfileControlStartIndex05, sheXdslCustomNotchProfileControlStopIndex05, sheXdslCustomNotchProfileControlStartIndex06, sheXdslCustomNotchProfileControlStopIndex06, sheXdslCustomNotchProfileControlStartIndex07, 
				sheXdslCustomNotchProfileControlStopIndex07, sheXdslCustomNotchProfileControlStartIndex08, sheXdslCustomNotchProfileControlStopIndex08, sheXdslPsdMaskProfileControlRequest, sheXdslPsdMaskProfileControlIndex, 
				sheXdslPsdMaskProfileControlStatus, sheXdslPsdMaskProfileControlTimer, sheXdslPsdMaskProfileControlReqResult, sheXdslPsdMaskProfileControlTimeStamp, sheXdslPsdMaskProfileControlName, 
				sheXdslPsdMaskProfileControlUsedBreakpoints, sheXdslPsdMaskProfileControlSubcarrierIndex01, sheXdslPsdMaskProfileControlPsdLevel01, sheXdslPsdMaskProfileControlSubcarrierIndex02, sheXdslPsdMaskProfileControlPsdLevel02, 
				sheXdslPsdMaskProfileControlSubcarrierIndex03, sheXdslPsdMaskProfileControlPsdLevel03, sheXdslPsdMaskProfileControlSubcarrierIndex04, sheXdslPsdMaskProfileControlPsdLevel04, sheXdslPsdMaskProfileControlSubcarrierIndex05, 
				sheXdslPsdMaskProfileControlPsdLevel05, sheXdslPsdMaskProfileControlSubcarrierIndex06, sheXdslPsdMaskProfileControlPsdLevel06, sheXdslPsdMaskProfileControlSubcarrierIndex07, sheXdslPsdMaskProfileControlPsdLevel07, 
				sheXdslPsdMaskProfileControlSubcarrierIndex08, sheXdslPsdMaskProfileControlPsdLevel08, sheXdslPsdMaskProfileControlSubcarrierIndex09, sheXdslPsdMaskProfileControlPsdLevel09, sheXdslPsdMaskProfileControlSubcarrierIndex10, 
				sheXdslPsdMaskProfileControlPsdLevel10, sheXdslPsdMaskProfileControlSubcarrierIndex11, sheXdslPsdMaskProfileControlPsdLevel11, sheXdslPsdMaskProfileControlSubcarrierIndex12, sheXdslPsdMaskProfileControlPsdLevel12, 
				sheXdslPsdMaskProfileControlSubcarrierIndex13, sheXdslPsdMaskProfileControlPsdLevel13, sheXdslPsdMaskProfileControlSubcarrierIndex14, sheXdslPsdMaskProfileControlPsdLevel14, sheXdslPsdMaskProfileControlSubcarrierIndex15, 
				sheXdslPsdMaskProfileControlPsdLevel15, sheXdslPsdMaskProfileControlSubcarrierIndex16, sheXdslPsdMaskProfileControlPsdLevel16, sheXdslPsdMaskProfileControlSubcarrierIndex17, sheXdslPsdMaskProfileControlPsdLevel17, 
				sheXdslPsdMaskProfileControlSubcarrierIndex18, sheXdslPsdMaskProfileControlPsdLevel18, sheXdslPsdMaskProfileControlSubcarrierIndex19, sheXdslPsdMaskProfileControlPsdLevel19, sheXdslPsdMaskProfileControlSubcarrierIndex20, 
				sheXdslPsdMaskProfileControlPsdLevel20, sheXdslPsdMaskProfileControlSubcarrierIndex21, sheXdslPsdMaskProfileControlPsdLevel21, sheXdslPsdMaskProfileControlSubcarrierIndex22, sheXdslPsdMaskProfileControlPsdLevel22, 
				sheXdslPsdMaskProfileControlSubcarrierIndex23, sheXdslPsdMaskProfileControlPsdLevel23, sheXdslPsdMaskProfileControlSubcarrierIndex24, sheXdslPsdMaskProfileControlPsdLevel24, sheXdslPsdMaskProfileControlSubcarrierIndex25, 
				sheXdslPsdMaskProfileControlPsdLevel25, sheXdslPsdMaskProfileControlSubcarrierIndex26, sheXdslPsdMaskProfileControlPsdLevel26, sheXdslPsdMaskProfileControlSubcarrierIndex27, sheXdslPsdMaskProfileControlPsdLevel27, 
				sheXdslPsdMaskProfileControlSubcarrierIndex28, sheXdslPsdMaskProfileControlPsdLevel28, sheXdslPsdMaskProfileControlSubcarrierIndex29, sheXdslPsdMaskProfileControlPsdLevel29, sheXdslPsdMaskProfileControlSubcarrierIndex30, 
				sheXdslPsdMaskProfileControlPsdLevel30, sheXdslPsdMaskProfileControlSubcarrierIndex31, sheXdslPsdMaskProfileControlPsdLevel31, sheXdslPsdMaskProfileControlSubcarrierIndex32, sheXdslPsdMaskProfileControlPsdLevel32, 
				sheXdslLineConfExtnProfileControlUseCustomSubcarrierMask, sheXdslLineConfExtnProfileControlCustomSubcarrierMask, sheXdslLineConfProfileControlUseVdsl2ProfileNumber, sheXdslLineConfExtnProfileControlDownPboMus, sheXdslLineConfExtnProfileControlDownPboFMin, 
				sheXdslLineConfExtnProfileControlDownPboFMax, sheXdslLineConfExtnProfileControlDownPboEpsd, sheXdslLineConfExtnProfileControlDownPboEScmA, sheXdslLineConfExtnProfileControlDownPboEScmB, sheXdslLineConfExtnProfileControlDownPboEScmC, 
				sheXdslLineConfExtnProfileControlUpPboA, sheXdslLineConfExtnProfileControlUpPboB, sheXdslLineConfExtnProfileControlMaxDownNomPsd, sheXdslLineConfExtnProfileControlMaxUpNomPsd, sheXdslLineAlarmConfProfileOperationalStateNotifyEnable, 
				sheXdslLineConfExtnProfileControlXtucPwrMgmtL2ATPRT, sheXdslLineConfExtnProfileControlDownPboEselMin, sheXdslLineConfExtnProfileControlUpPboKL, sheXdslLineConfExtnProfileControlUpPboKO, sheXdslLineControlLdsf, 
				sheXdslCustomNotchProfileControlStartIndex09, sheXdslCustomNotchProfileControlStopIndex09, sheXdslCustomNotchProfileControlStartIndex10, sheXdslCustomNotchProfileControlStopIndex10, sheXdslCustomNotchProfileControlStartIndex11, 
				sheXdslCustomNotchProfileControlStopIndex11, sheXdslCustomNotchProfileControlStartIndex12, sheXdslCustomNotchProfileControlStopIndex12, sheXdslCustomNotchProfileControlStartIndex13, sheXdslCustomNotchProfileControlStopIndex13, 
				sheXdslCustomNotchProfileControlStartIndex14, sheXdslCustomNotchProfileControlStopIndex14, sheXdslCustomNotchProfileControlStartIndex15, sheXdslCustomNotchProfileControlStopIndex15, sheXdslCustomNotchProfileControlStartIndex16, 
				sheXdslCustomNotchProfileControlStopIndex16, sheXdslLineDeltStatusControlRequest, sheXdslLineDeltStatusControlIndex, sheXdslLineDeltStatusControlStatus, sheXdslLineDeltStatusControlTimer, 
				sheXdslLineDeltStatusControlReqResult, sheXdslLineDeltStatusControlTimeStamp, sheXdslLineDeltStatusControlSCGDnGroupSize, sheXdslLineDeltStatusControlSCGUpGroupSize, sheXdslLineDeltStatusControlSCGDnSnrMtime, 
				sheXdslLineDeltStatusControlSCGUpSnrMtime, sheXdslLineDeltStatusControlSCGDnLinScale, sheXdslLineDeltStatusControlSCGUpLinScale, sheXdslLineDeltStatusControlSCGDnHLogMtime, sheXdslLineDeltStatusControlSCGUpHLogMtime, 
				sheXdslLineDeltStatusControlSCGDnQlnMtime, sheXdslLineDeltStatusControlSCGUpQlnMtime, sheXdslLineControlCustomDownPsdMaskProfile, sheXdslLineControlCustomUpPsdMaskProfile, sheXdslLineControlCustomNotchProfile, 
				sheXdslLineConfExtnProfileControlUpPboBoostMode, sheXdslLineControlRfiBandMask, sheXdslLineConfExtnProfileControlDownPboEsel, sheXdslLineConfExtnProfileControlDownPboMof, sheXdslChannelProfileControlRequest, 
				sheXdslChannelProfileControlIndex, sheXdslChannelProfileControlStatus, sheXdslChannelProfileControlTimer, sheXdslChannelProfileControlReqResult, sheXdslChannelProfileControlTimeStamp, 
				sheXdslChannelProfileControlName, sheXdslChannelProfileControlMinDataRateDs, sheXdslChannelProfileControlMinDataRateUs, sheXdslChannelProfileControlMinResDataRateDs, sheXdslChannelProfileControlMinResDataRateUs, 
				sheXdslChannelProfileControlMaxDataRateDs, sheXdslChannelProfileControlMaxDataRateUs, sheXdslChannelProfileControlMinDataRateLowPwrDs, sheXdslChannelProfileControlMaxBerDs, sheXdslChannelProfileControlMaxBerUs, 
				sheXdslChannelProfileControlMaxInterleaveDelayDs, sheXdslChannelProfileControlMaxInterleaveDelayUs, sheXdslChannelProfileControlMinINPDs, sheXdslChannelProfileControlMinINPUs, sheXdslLineConfProfileControlUseVdsl2BandPlanNumber, 
				sheXdslChannelProfileControlThresholdRateDownShiftDs, sheXdslChannelProfileControlThresholdRateUpShiftDs, sheXdslChannelProfileControlThresholdRateDownShiftUs, sheXdslLineControlPMSF, sheXdslLineConfExtnProfileControlMsgMinUp, 
				sheXdslLineConfExtnProfileControlMsgMinDown, sheXdslLineConfExtnProfileControlUsPsdMaskSelection, sheXdslLineConfExtnProfileControlCustomUsSubcarrierMask, sheXdslShowtimeStatusMRefPsdDs, sheXdslShowtimeStatusMRefPsdUs, 
				sheXdslLineDeltStatusControlSCGDnGroupSizeHLin, sheXdslLineDeltStatusControlSCGUpGroupSizeHLin, sheXdslLineDeltStatusControlSCGDnGroupSizeHLog, sheXdslLineDeltStatusControlSCGUpGroupSizeHLog, sheXdslLineDeltStatusControlSCGDnGroupSizeQln, 
				sheXdslLineDeltStatusControlSCGUpGroupSizeQln, sheXdslLineConfExtnProfileControlSnrModeDown, sheXdslLineConfExtnProfileControlSnrModeUp, sheXdslLineConfExtnProfileControlTxRefVnDown, sheXdslLineConfExtnProfileControlTxRefVnUp, 
				sheXdslLineControlPerformance15MinHistoryEnabled, sheXdslLineControlPerformance1DayHistoryEnabled, sheXdslShowtimeStatusTssiDs, sheXdslShowtimeStatusTssiUs, sheXdslChannelProfileControlThresholdRateUpShiftUs, 
				sheXdslLineControlForceINPDs, sheXdslLineControlForceINPUs, sheXdslLineControlChan1ConfProfile, sheXdslLineControlChan1RaRatioDs, sheXdslLineControlChan1RaRatioUs, 
				sheXdslLineControlChan2ConfProfile, sheXdslLineAlarmConfProfileViolationCheck }
			STATUS current
			DESCRIPTION 
				"Description."
			::= { sheXdslGroups 2 }

		
		sheXdslNotificationGroup NOTIFICATION-GROUP
			NOTIFICATIONS { sheXdslPerfLofsThreshNotification, sheXdslPerfLossThreshNotification, sheXdslPerfLprsThreshNotification, sheXdslPerfLolsThreshNotification, sheXdslPerfESsThreshNotification, 
				sheXdslPerfSESsThreshNotification, sheXdslPerfUASsThreshNotification, sheXdslDownMaxSnrMgnNotification, sheXdslDownMinSnrMgnNotification, sheXdslUpMaxSnrMgnNotification, 
				sheXdslLineModified, sheXdslLineAlarmConfModified, sheXdslLineConfProfileCreated, sheXdslLineConfProfileModified, sheXdslLineConfProfileDeleted, 
				sheXdslLineAlarmConfProfileCreated, sheXdslLineAlarmConfProfileModified, sheXdslLineAlarmConfProfileDeleted, sheXdslLineConfExtnProfileModified, sheXdslLineAlarmLOS, 
				sheXdslLineAlarmLOF, sheXdslLineAlarmLOL, sheXdslLineAlarmLPR, sheXdslLineAlarmIMNR, sheXdslPsdMaskProfileCreated, 
				sheXdslPsdMaskProfileModified, sheXdslPsdMaskProfileDeleted, sheXdslCustomNotchProfileCreated, sheXdslCustomNotchProfileModified, sheXdslCustomNotchProfileDeleted, 
				sheXdslOperationalStateChangedNotification, sheXdslLineModifiedReqResult, sheXdslLineProfileModifiedReqResult, sheXdslLineExtnProfileModifiedReqResult, sheXdslAlarmProfileModifiedReqResult, 
				sheXdslPsdMaskProfileModifiedReqResult, sheXdslLineDeltStateModified, sheXdslLineDeltStatusReqResult, sheXdslLineDownPsdMaskProfileEntryModified, sheXdslLineUpPsdMaskProfileEntryModified, 
				sheXdslLineShowtimeStatusReqResult, sheXdslLineAlarmActivationFailed, sheXdslLineAlarmHWUnitDefect, sheXdslLineForceInpModified, sheXdslLineChannelConfigurationModified, 
				sheXdslLinePMSFStateModified, sheXdslLinePerformanceHistoryModified, sheXdslUpMinSnrMgnNotification, sheXdslInitFailureNotification, sheXdslLineDeltResultStateChanged, 
				sheXdslLineNotchConfigurationModified, sheXdslChannelProfileCreated, sheXdslChannelProfileModified, sheXdslChannelProfileDeleted, sheXdslChannelProfileModifiedReqResult, 
				sheXdslChannelRateChangeDownShiftTrap, sheXdslChannelRateChangeUpShiftTrap, sheXdslLineAlarmConfigViolationDetected }
			STATUS current
			DESCRIPTION 
				"This group supports notifications of significant 
				conditions associated with XDSL Lines."
			::= { sheXdslGroups 3 }

		
		sheXdslObsoleteGroup OBJECT-GROUP
			OBJECTS { sheXdslSCDnStatusTss, sheXdslSCUpStatusTss, sheXdslLineConfForceINPDs, sheXdslLineConfForceINPUs, sheXdslLineConfChan1ConfProfile, 
				sheXdslLineConfProfileControlForceINPDs, sheXdslLineConfProfileControlForceINPUs, sheXdslLineConfControlChan1ConfProfile, sheXdslLineConfControlChan1RaRatioDs, sheXdslLineConfControlChan1RaRatioUs, 
				sheXdslLineConfControlChan2ConfProfile, sheXdslLineConfChan1RaRatioDs, sheXdslLineConfChan1RaRatioUs, sheXdslLineConfChan2ConfProfile }
			STATUS obsolete
			DESCRIPTION 
				"Description."
			::= { sheXdslGroups 4 }

		
	
	END

--
-- she-xdsl-mib.mib
--
