----------------------------------------------
-- the file is created by Zhang.yilin for DPI-MIB
-- 2008-11-04
----------------------------------------------

DPI-MIB DEFINITIONS ::= BEGIN

IMPORTS
     
    MODULE-IDENTITY,  
    OBJECT-TYPE,    
    Integer32   
        FROM SNMPv2-SMI      
    enterprises                      
        FROM SNMPv2-SMI
    DisplayString
    		FROM SNMPv2-TC
    IpAddress
        FROM RFC1155-SMI;

zte OBJECT IDENTIFIER ::= { enterprises 3902 }

fwdpi MODULE-IDENTITY
    LAST-UPDATED "200504120000Z"  
    ORGANIZATION "ZTE Corporation"
    CONTACT-INFO
        ""

    DESCRIPTION
        "ZXROS DPI MIB"

    REVISION "200811040000Z"  
    DESCRIPTION
       "test for DPI"
	::= { zte 51 }	

--zyl OBJECT IDENTIFIER ::= { enterprises 4912 }

zxrDPI OBJECT IDENTIFIER ::= { fwdpi 1 }

------------------------------------------------------------------------------
dpiSystemControl OBJECT IDENTIFIER ::= { zxrDPI 1 }

       dpiSlotNumber OBJECT-TYPE
              SYNTAX  INTEGER(1..12)
              MAX-ACCESS  read-write
              STATUS  current
              DESCRIPTION
                      "An 32 bit unsigned integer description of the selected slot for DPI board."
              ::= { dpiSystemControl 1 }
              
       dpiRestartFunc OBJECT-TYPE
              SYNTAX  INTEGER{enable(1)}
              MAX-ACCESS  read-write
              STATUS  current
              DESCRIPTION
                      "Using for restarting the DPI system."
              ::= { dpiSystemControl 2  }
              
              
              
           
--------------------------------------------------------------------------------
dpiConfigMode OBJECT IDENTIFIER ::= { zxrDPI 2 }

 --  bind mng-server-ip
     dpiBindMngServiceIp OBJECT IDENTIFIER ::= { dpiConfigMode 2 }  
     
      dpiMngServerSlot  OBJECT-TYPE
      			 SYNTAX  INTEGER(1..12)
      			 MAX-ACCESS  read-write
              STATUS  current
              DESCRIPTION
                      "the slot for DPI board"
              ::= { dpiBindMngServiceIp 1  }
      
      dpiMngIp OBJECT-TYPE
      			 SYNTAX  IpAddress
      			 MAX-ACCESS  read-write
              STATUS  current
              DESCRIPTION
                      "the mng-ip for DPI board"
              ::= { dpiBindMngServiceIp 2  }
              
      dpiServerIp OBJECT-TYPE
      			 SYNTAX  IpAddress
      			 MAX-ACCESS  read-write
              STATUS  current
              DESCRIPTION
                      "the server-ip for DPI board"
              ::= { dpiBindMngServiceIp 3  } 
              
      dpiMngServerOK    OBJECT-TYPE
        SYNTAX   INTEGER{enable(1)}
        MAX-ACCESS  read-write
        STATUS  current
        DESCRIPTION
            "the commit of command."
        ::= { dpiBindMngServiceIp 4 }

-------------------------------------------------------------------------------              
dpiSignatureEntry OBJECT IDENTIFIER ::= { dpiConfigMode 3 }

--Signature-Entry X 
         dpiCurrentSignatureEntry OBJECT-TYPE
      			 SYNTAX  INTEGER(1..12287)
      			 MAX-ACCESS  read-write
              STATUS  current
              DESCRIPTION
                      "the current SignatureEntry mode"
              ::= { dpiSignatureEntry 1  }

--show signature-entry 
        dpiShowSignatureEntry OBJECT IDENTIFIER ::= { dpiSignatureEntry 2 }

			dpiSignatureEntryTable  OBJECT-TYPE
        SYNTAX  SEQUENCE OF DpiSignatureTableEntry
        MAX-ACCESS  not-accessible
        STATUS  current
        DESCRIPTION
            "Dpi SignatureEntry Table"
        ::= { dpiShowSignatureEntry 1 }
        
      dpiSignatureTableEntry  OBJECT-TYPE
        SYNTAX  DpiSignatureTableEntry
        MAX-ACCESS  not-accessible
        STATUS  current
        DESCRIPTION
            "Dpi Signaturetable entry"
        INDEX{dpiSignatureEntryID}
        ::= { dpiSignatureEntryTable 1 }
        
       DpiSignatureTableEntry ::= 
     			SEQUENCE {
         		dpiSignatureEntryID
             INTEGER,
         		dpiSignatureEntryContent
             DisplayString
          }
          
          
       dpiSignatureEntryID  OBJECT-TYPE
        SYNTAX   INTEGER(1..12287)
        MAX-ACCESS  read-only
        STATUS  current
        DESCRIPTION
            "the number of dpi Signature Entry"
        ::= { dpiSignatureTableEntry 1 }

			dpiSignatureEntryContent  OBJECT-TYPE
        SYNTAX   DisplayString
        MAX-ACCESS  read-only
        STATUS  current
        DESCRIPTION
            "A string description of the Key Content."
        ::= { dpiSignatureTableEntry 2 }    
        
        
 --set content
       dpiSetContent  OBJECT-TYPE 
       SYNTAX   DisplayString
        MAX-ACCESS  read-write
        STATUS  current
        DESCRIPTION
            "A string description of the Key Content."
        ::= { dpiSignatureEntry 3 }



-------------------------------------------------------------------------------
dpiSignatureSymbol OBJECT IDENTIFIER ::= { dpiConfigMode 4 }
 
-- signature-symbol X
     dpiCurrentSignatureSymbol   OBJECT-TYPE
      			 SYNTAX  INTEGER(1..6143)
      			 MAX-ACCESS  read-write
              STATUS  current
              DESCRIPTION
                      "the current SignatureSymbol mode"
              ::= { dpiSignatureSymbol 1  }

--show signature-symbol  
      dpiShowSignatureSymbol OBJECT IDENTIFIER ::= { dpiSignatureSymbol 2 }

dpiSignatureSymbolTable  OBJECT-TYPE
        SYNTAX  SEQUENCE OF DpiSignatureSymbolTableEntry
        MAX-ACCESS  not-accessible
        STATUS  current
        DESCRIPTION
            "Dpi SignatureSymbol Table"
        ::= { dpiShowSignatureSymbol 1 }
        
      dpiSignatureSymbolTableEntry  OBJECT-TYPE
        SYNTAX  DpiSignatureSymbolTableEntry
        MAX-ACCESS  not-accessible
        STATUS  current
        DESCRIPTION
            "Dpi SignatureSymbol-table entry"
        INDEX{dpiSignatureSymbolID}
        ::= { dpiSignatureSymbolTable 1 }
        
       DpiSignatureSymbolTableEntry ::= 
     			SEQUENCE {
     				dpiSignatureSymbolID  INTEGER,
     				dpiSignatureSymbolEntryID   DisplayString,
     				dpiSignatureSymbolHitNumLimit    INTEGER      }
          
      dpiSignatureSymbolID  OBJECT-TYPE
        SYNTAX   INTEGER(1..6143)
        MAX-ACCESS  read-only
        STATUS  current
        DESCRIPTION
            "the number of dpi Signature Symbol Entry"
        ::= { dpiSignatureSymbolTableEntry 1 }
        
        
      dpiSignatureSymbolEntryID  OBJECT-TYPE
        SYNTAX   DisplayString
        MAX-ACCESS  read-only
        STATUS  current
        DESCRIPTION
            "the number of dpi Signature Entry"
        ::= { dpiSignatureSymbolTableEntry 2 }

			dpiSignatureSymbolHitNumLimit  OBJECT-TYPE
        SYNTAX   INTEGER(1..16)
        MAX-ACCESS  read-only
        STATUS  current
        DESCRIPTION
            "A string description of the Key."
        ::= { dpiSignatureSymbolTableEntry 3 }    
                
       
 --add signature-entry
        dpiAddSignatureEntry  OBJECT-TYPE
        SYNTAX  INTEGER(1..12287)
        MAX-ACCESS  read-write
        STATUS  current
        DESCRIPTION
            "the SignatureEntry ID which you want to add into the current Symbol"
        ::= { dpiSignatureSymbol 3 }
 
 
 --no add signature-entry
        dpiNoAddSignatureEntry  OBJECT-TYPE
        SYNTAX  INTEGER(1..12287)
        MAX-ACCESS  read-write
        STATUS  current
        DESCRIPTION
            "the SignatureEntry ID which you want to remove from the current Symbol"
        ::= { dpiSignatureSymbol 4 }      
        
 --set hit-num-limit
      dpiSetHitNumLimit    OBJECT-TYPE
        SYNTAX  INTEGER(1..16)
        MAX-ACCESS  read-write
        STATUS  current
        DESCRIPTION
            "the hit-num-limit of the current Symbol"
        ::= { dpiSignatureSymbol 5 }
         
          
 
-------------------------------------------------------------------------------
dpiFlowPool OBJECT IDENTIFIER ::= { dpiConfigMode 5 }

--Flow-pool X
        dpiCurrentFlowPool   OBJECT-TYPE
      			 SYNTAX  INTEGER(1..8191)
      			 MAX-ACCESS  read-write
              STATUS  current
              DESCRIPTION
                      "the current flow-pool mode"
              ::= { dpiFlowPool 1  }

        
        
--show flow-pool 
        dpiShowFlowPool OBJECT IDENTIFIER ::= { dpiFlowPool 2 }

			dpiStreamLimitTable  OBJECT-TYPE
        SYNTAX  SEQUENCE OF DpiStreamLimitTableEntry
        MAX-ACCESS  not-accessible
        STATUS  current
        DESCRIPTION
            "Dpi stream-rate-limit Table"
        ::= { dpiShowFlowPool 1 }
        
      dpiStreamLimitTableEntry  OBJECT-TYPE
        SYNTAX  DpiStreamLimitTableEntry
        MAX-ACCESS  not-accessible
        STATUS  current
        DESCRIPTION
            "Dpi Stream-rate-Limit Table entry"
        INDEX{dpiStreamLimitID,dpiStreamLimitType}
        ::= { dpiStreamLimitTable 1 }
        
       DpiStreamLimitTableEntry ::= 
     			SEQUENCE {
         		dpiStreamLimitID
             INTEGER,
            dpiStreamLimitType
             INTEGER,
            dpiStreamRate
            	INTEGER,
         		dpiStreamCbs
             Integer32,
            dpiStreamEbs
            	Integer32
          }
          
        dpiStreamLimitID  OBJECT-TYPE
        SYNTAX   INTEGER(2..8191)
        MAX-ACCESS  read-only
        STATUS  current
        DESCRIPTION
            "the ID of dpi Stream limit"
        ::= { dpiStreamLimitTableEntry 1 }  
          
          
        dpiStreamLimitType OBJECT-TYPE
        SYNTAX   INTEGER{down(1),up(2)}
        MAX-ACCESS  read-only
        STATUS  current
        DESCRIPTION
            "the type of dpi Stream limit"
        ::= { dpiStreamLimitTableEntry 2 }   
          
       dpiStreamRate  OBJECT-TYPE
        SYNTAX   INTEGER(10..100000)
        MAX-ACCESS  read-only
        STATUS  current
        DESCRIPTION
            "the rate of dpi DownStream limit"
        ::= { dpiStreamLimitTableEntry 3 } 

			dpiStreamCbs  OBJECT-TYPE
        SYNTAX   Integer32
        MAX-ACCESS  read-only
        STATUS  current
        DESCRIPTION
            "the cbs of the rate-limit."
        ::= { dpiStreamLimitTableEntry 4 }
        
      dpiStreamEbs  OBJECT-TYPE
        SYNTAX   Integer32
        MAX-ACCESS  read-only
        STATUS  current
        DESCRIPTION
            "the ebs of the rate-limit."
        ::= { dpiStreamLimitTableEntry 5 }

--  upstream-rate-limit  
      dpiUpStreamRateLimit OBJECT IDENTIFIER ::= { dpiFlowPool 3 }   
      
      dpiUpStreamRate  OBJECT-TYPE
        SYNTAX   INTEGER(10..100000)
        MAX-ACCESS  read-write
        STATUS  current
        DESCRIPTION
            "the rate of dpi Up Stream limit"
        ::= { dpiUpStreamRateLimit 1 } 

			dpiUpStreamCbs  OBJECT-TYPE
        SYNTAX   Integer32
        MAX-ACCESS  read-write
        STATUS  current
        DESCRIPTION
            "the cbs of the rate-limit."
        ::= { dpiUpStreamRateLimit 2 }
        
      dpiUpStreamEbs  OBJECT-TYPE
        SYNTAX   Integer32
        MAX-ACCESS  read-write
        STATUS  current
        DESCRIPTION
            "the ebs of the rate-limit."
        ::= { dpiUpStreamRateLimit 3 }    
        
       dpiUpStreamOK  OBJECT-TYPE
        SYNTAX   INTEGER{enable(1)}
        MAX-ACCESS  read-write
        STATUS  current
        DESCRIPTION
            "the commit of the up stream-rate-limit."
        ::= { dpiUpStreamRateLimit 4 }   
               
-- no upstream-rate-limit  
       dpiNoUpStreamRateLimit   OBJECT-TYPE
        SYNTAX   INTEGER{enable(1)}
        MAX-ACCESS  read-write
        STATUS  current
        DESCRIPTION
            "the commit of the No up stream-rate-limit."
        ::= { dpiFlowPool 4 }
        
--  downstream-rate-limit    
     dpiDownStreamRateLimit OBJECT IDENTIFIER ::= { dpiFlowPool 5 }   
      
      dpiDownStreamRate  OBJECT-TYPE
        SYNTAX   INTEGER(10..100000)
        MAX-ACCESS  read-write
        STATUS  current
        DESCRIPTION
            "the rate of dpi DownStream limit"
        ::= { dpiDownStreamRateLimit 1 } 

			dpiDownStreamCbs  OBJECT-TYPE
        SYNTAX   Integer32
        MAX-ACCESS  read-write
        STATUS  current
        DESCRIPTION
            "the cbs of the rate-limit."
        ::= { dpiDownStreamRateLimit 2 }
        
      dpiDownStreamEbs  OBJECT-TYPE
        SYNTAX   Integer32
        MAX-ACCESS  read-write
        STATUS  current
        DESCRIPTION
            "the ebs of the rate-limit."
        ::= { dpiDownStreamRateLimit 3 }    
        
       dpiDownStreamOK  OBJECT-TYPE
        SYNTAX   INTEGER{enable(1)}
        MAX-ACCESS  read-write
        STATUS  current
        DESCRIPTION
            "the commit of the down stream-rate-limit."
        ::= { dpiDownStreamRateLimit 4 }  
        
 -- no downstream-rate-limit      
     dpiNoDownStreamRateLimit   OBJECT-TYPE
        SYNTAX   INTEGER{enable(1)}
        MAX-ACCESS  read-write
        STATUS  current
        DESCRIPTION
            "the commit of the No down stream-rate-limit."
        ::= { dpiFlowPool 6 }

        
        
        
-------------------------------------------------------------------------------
dpiSubservice OBJECT IDENTIFIER ::= { dpiConfigMode 6 }

--Subservice X   
	dpiCurrentSubservice  OBJECT-TYPE
        SYNTAX   INTEGER(1..8191)
        MAX-ACCESS  read-write
        STATUS  current
        DESCRIPTION
            "the current ID of dpi Subservice"
        ::= { dpiSubservice 1 }

     
--show subservice X
   dpiShowSubservice   OBJECT IDENTIFIER ::= { dpiSubservice 2 }  
   
dpiSubserviceTable  OBJECT-TYPE
        SYNTAX  SEQUENCE OF DpiSubserviceEntry
        MAX-ACCESS  not-accessible
        STATUS  current
        DESCRIPTION
            "Dpi Subservice Table"
        ::= { dpiShowSubservice 1 }
        
      dpiSubserviceEntry  OBJECT-TYPE
        SYNTAX  DpiSubserviceEntry
        MAX-ACCESS  not-accessible
        STATUS  current
        DESCRIPTION
            "Dpi SubserviceTable entry"
        INDEX{dpiSubserviceID}
        ::= { dpiSubserviceTable 1 }
        
       DpiSubserviceEntry ::= 
     			SEQUENCE {
         		dpiSubserviceID
             INTEGER,
         		dpiSubserviceSymbolNum
             INTEGER,
            dpiSubserviceFlowpoolID
            	INTEGER,
            dpiSubserviceAction
              INTEGER,
            dpiSubserviceAgingTime
            	INTEGER,
            dpiSubserviceSymbolList
              DisplayString
            
          }
          
          
       dpiSubserviceID  OBJECT-TYPE
        SYNTAX   INTEGER(1..8191)
        MAX-ACCESS  read-only
        STATUS  current
        DESCRIPTION
            "the ID of dpi Subservice"
        ::= { dpiSubserviceEntry 1 }

			dpiSubserviceSymbolNum  OBJECT-TYPE
        SYNTAX   INTEGER(1..6143)
        MAX-ACCESS  read-only
        STATUS  current
        DESCRIPTION
            "the number of the bound Symbol"
        ::= { dpiSubserviceEntry 2 }
        
      dpiSubserviceFlowpoolID  OBJECT-TYPE
        SYNTAX   INTEGER(2..8191)
        MAX-ACCESS  read-only
        STATUS  current
        DESCRIPTION
            "the ID of the bound Flow-pool"
        ::= { dpiSubserviceEntry 3 }
        
      dpiSubserviceAction  OBJECT-TYPE
        SYNTAX   INTEGER{permit(1),deny(0)}
        MAX-ACCESS  read-only
        STATUS  current
        DESCRIPTION
            "the status of the subservice"
        ::= { dpiSubserviceEntry 4 }
        
      dpiSubserviceAgingTime  OBJECT-TYPE
        SYNTAX   INTEGER(1..60)
        MAX-ACCESS  read-only
        STATUS  current
        DESCRIPTION
            "the time of the aging"
        ::= { dpiSubserviceEntry 5 }
        
      dpiSubserviceSymbolList  OBJECT-TYPE
        SYNTAX   DisplayString
        MAX-ACCESS  read-only
        STATUS  current
        DESCRIPTION
            "the Symbol List."
        ::= { dpiSubserviceEntry 6 }    
        
 -- add signature-symbol 
      dpiAddSignatureSymbol OBJECT IDENTIFIER ::= { dpiSubservice 3 }
      
      dpiAddSignatureSymbolId   OBJECT-TYPE
         SYNTAX   DisplayString
        MAX-ACCESS  read-write
        STATUS  current
        DESCRIPTION
            "the related symbol IDs."
        ::= { dpiAddSignatureSymbol 1 } 
        
        dpiAddSignatureSymbolRelationName   OBJECT-TYPE
         SYNTAX   DisplayString
        MAX-ACCESS  read-write
        STATUS  current
        DESCRIPTION
            "the relation Name."
        ::= { dpiAddSignatureSymbol 2 }   
        
      dpiAddSignatureSymbolOK   OBJECT-TYPE
        SYNTAX   INTEGER{enable(1)}
        MAX-ACCESS  read-write
        STATUS  current
        DESCRIPTION
            "the commit of the add signature-symbol."
        ::= { dpiAddSignatureSymbol 3 }  
        
-- no add signature-symbol
      dpiNoAddSignatureSymbol   OBJECT-TYPE
        SYNTAX   DisplayString
        MAX-ACCESS  read-write
        STATUS  current
        DESCRIPTION
            "the commit of the no add signature-symbol."
        ::= { dpiSubservice 4 }  
        
--add protocol
      dpiAddProtocol    OBJECT-TYPE
        SYNTAX   DisplayString
        MAX-ACCESS  read-write
        STATUS  current
        DESCRIPTION
            "the commit of the add protocol."
        ::= { dpiSubservice 5 }  
        
-- no add protocol
       dpiNoAddProtocol  OBJECT-TYPE
        SYNTAX   DisplayString
        MAX-ACCESS  read-write
        STATUS  current
        DESCRIPTION
            "the commit of the no add protocol."
        ::= { dpiSubservice 6 }
 
-- bind  flow-pool
       dpiBindFlowPool  OBJECT-TYPE
        SYNTAX   INTEGER(2..8191)
        MAX-ACCESS  read-write
        STATUS  current
        DESCRIPTION
            "the commit of the bind flow-pool."
        ::= { dpiSubservice 7 }    
        
-- no bind flow-pool 
       dpiNoBindFlowPool  OBJECT-TYPE
        SYNTAX   INTEGER(2..8191)
        MAX-ACCESS  read-write
        STATUS  current
        DESCRIPTION
            "the commit of the no bind flow-pool."
        ::= { dpiSubservice 8 } 
        
-- action 
      dpiSetAction   OBJECT-TYPE
        SYNTAX   INTEGER{permit(0),deny(1)}
        MAX-ACCESS  read-write
        STATUS  current
        DESCRIPTION
            "the status of the subservice"
        ::= { dpiSubservice 9 }   
        
-- aging time    
     dpiSetAgingTime     OBJECT-TYPE
        SYNTAX   INTEGER(1..60)
        MAX-ACCESS  read-write
        STATUS  current
        DESCRIPTION
            "the time of the aging"
        ::= { dpiSubservice 10 }

        
--------------------------------------------------------------------------------
dpiService OBJECT IDENTIFIER ::= { dpiConfigMode 7 }

-- Service X
   dpiCurrentService  OBJECT-TYPE
        SYNTAX   INTEGER(1..2047)
        MAX-ACCESS  read-write
        STATUS  current
        DESCRIPTION
            "the current ID of dpi service"
        ::= { dpiService 1 }
 
--Show Service X  
      dpiShowService   OBJECT IDENTIFIER ::= { dpiService 2 } 
      
       dpiServiceTable  OBJECT-TYPE
        SYNTAX  SEQUENCE OF DpiServiceEntry
        MAX-ACCESS  not-accessible
        STATUS  current
        DESCRIPTION
            "Dpi Service Table"
        ::= { dpiShowService 1 }
        
      dpiServiceEntry  OBJECT-TYPE
        SYNTAX  DpiServiceEntry
        MAX-ACCESS  not-accessible
        STATUS  current
        DESCRIPTION
            "Dpi Service entry"
        INDEX{dpiServiceID}
        ::= { dpiServiceTable 1 }
        
       DpiServiceEntry ::= 
     			SEQUENCE {
     				dpiServiceID  INTEGER,
     				dpiServiceFlowPoolID   INTEGER,
     				dpiServiceConnectionLimit INTEGER,
     				dpiServiceSubserviceNum  INTEGER,
     				dpiServiceSubserviceList DisplayString
          }
          
      dpiServiceID  OBJECT-TYPE
        SYNTAX   INTEGER(1..2047)
        MAX-ACCESS  read-only
        STATUS  current
        DESCRIPTION
            "the ID of dpi Service"
        ::= { dpiServiceEntry 1 }
        
     dpiServiceFlowPoolID  OBJECT-TYPE
        SYNTAX   INTEGER(2..8191)
        MAX-ACCESS  read-only
        STATUS  current
        DESCRIPTION
            "the ID of dpi Service bound Flow-pool"
        ::= { dpiServiceEntry 2 }
        
     dpiServiceConnectionLimit  OBJECT-TYPE
        SYNTAX   INTEGER(0..1310719)
        MAX-ACCESS  read-only
        STATUS  current
        DESCRIPTION
            "the max number of the limited connections"
        ::= { dpiServiceEntry 3 }
        
      dpiServiceSubserviceNum  OBJECT-TYPE
        SYNTAX   INTEGER(1..8191)
        MAX-ACCESS  read-only
        STATUS  current
        DESCRIPTION
            "the number of dpi Subservice in Service"
        ::= { dpiServiceEntry 4 }
        
     dpiServiceSubserviceList  OBJECT-TYPE
        SYNTAX   DisplayString
        MAX-ACCESS  read-only
        STATUS  current
        DESCRIPTION
            "the SubService List."
        ::= { dpiServiceEntry 5 }  
                                     
                                     
--add subservice
     dpiAddSubservice OBJECT-TYPE
        SYNTAX   INTEGER(1..8191)
        MAX-ACCESS  read-write
        STATUS  current
        DESCRIPTION
            "the commit of add subservice"
        ::= { dpiService 3 } 
        
-- no add subservice
     dpiNoAddSubservice OBJECT-TYPE
        SYNTAX   INTEGER(1..8191)
        MAX-ACCESS  read-write
        STATUS  current
        DESCRIPTION
            "the commit of no add subservice"
        ::= { dpiService 4 }
        
-- import subservice
     dpiImportSubservice    OBJECT IDENTIFIER ::= { dpiService 5 }
     
     dpiImportDestSubservice    OBJECT-TYPE
        SYNTAX   INTEGER(1..8191)
        MAX-ACCESS  read-write
        STATUS  current
        DESCRIPTION
            "the dest of import subservice"
        ::= { dpiImportSubservice 1 }   
        
      dpiImportSrcSubservice    OBJECT-TYPE
        SYNTAX   INTEGER(1..8191)
        MAX-ACCESS  read-write
        STATUS  current
        DESCRIPTION
            "the source of import subservice"
        ::= { dpiImportSubservice 2 } 
        
       dpiImportSubserviceOK    OBJECT-TYPE
        SYNTAX   INTEGER{enable(1)}
        MAX-ACCESS  read-write
        STATUS  current
        DESCRIPTION
            "the commit of import subservice"
        ::= { dpiImportSubservice 3 }  
        
       dpiNoImportSubservice    OBJECT-TYPE
        SYNTAX   INTEGER{enable(1)}
        MAX-ACCESS  read-write
        STATUS  current
        DESCRIPTION
            "the cancel of import subservice"
        ::= { dpiImportSubservice 4 }

 -- bind flow-pool
        dpiServiceBindFlowPool   OBJECT-TYPE
        SYNTAX   INTEGER(2..8191)
        MAX-ACCESS  read-write
        STATUS  current
        DESCRIPTION
            "the ID of dpi Service bound Flow-pool"
        ::= { dpiService 6 }   
        
-- no bind flow-pool
       dpiServiceNoBindFlowPool   OBJECT-TYPE
        SYNTAX   INTEGER(2..8191)
        MAX-ACCESS  read-write
        STATUS  current
        DESCRIPTION
            "the ID of No Service bound Flow-pool"
        ::= { dpiService 7 }     
        
        
-- set connection-limit
--      dpiSetConnectionLimit  OBJECT-TYPE
--        SYNTAX   INTEGER(0..1310719)
--        MAX-ACCESS  read-only
--        STATUS  current
--        DESCRIPTION
--            "the max number of the limited connections"
--        ::= { dpiService 8 }

        
--------------------------------------------------------------------------------
dpiTemplate OBJECT IDENTIFIER ::= { dpiConfigMode 8 }

--dpi-template X
    dpiCurrentTemplate    OBJECT-TYPE
        SYNTAX   INTEGER(1..4095)
        MAX-ACCESS  read-write
        STATUS  current
        DESCRIPTION
            "the current ID of dpi-template"
        ::= { dpiTemplate 1 }

        
--bind slot
    dpiBindSlot    OBJECT-TYPE
        SYNTAX   INTEGER(1..12)
        MAX-ACCESS  read-write
        STATUS  current
        DESCRIPTION
            "the current slot of dpi-template"
        ::= { dpiTemplate 2 }  
        
--no bind slot 
    dpiNoBindSlot    OBJECT-TYPE
        SYNTAX   INTEGER(1..12)
        MAX-ACCESS  read-write
        STATUS  current
        DESCRIPTION
            "remove the current slot of dpi-template"
        ::= { dpiTemplate 3 }    
        
-- bind service
    dpiBindService    OBJECT-TYPE
        SYNTAX   INTEGER(1..2047)
        MAX-ACCESS  read-write
        STATUS  current
        DESCRIPTION
            "the bind-service ID of dpi-template"
        ::= { dpiTemplate 4 } 
        
-- no bind service
    dpiNoBindService    OBJECT-TYPE
        SYNTAX   INTEGER(1..2047)
        MAX-ACCESS  read-write
        STATUS  current
        DESCRIPTION
            "remove the bind-service ID of dpi-template"
        ::= { dpiTemplate 5 } 

--  bind sip-addr 
    dpiBindSipAddr     OBJECT IDENTIFIER ::= { dpiTemplate 6 }
   	  
   	dpiSipAddress   OBJECT-TYPE
        SYNTAX   IpAddress
        MAX-ACCESS  read-write
        STATUS  current
        DESCRIPTION
            "the bind-sip-addr address"
        ::= { dpiBindSipAddr 1 }
        
    dpiSipMask   OBJECT-TYPE
        SYNTAX   IpAddress
        MAX-ACCESS  read-write
        STATUS  current
        DESCRIPTION
            "the bind-sip-addr mask"
        ::= { dpiBindSipAddr 2 } 
        
    dpiSipServiceID     OBJECT-TYPE
        SYNTAX   INTEGER(1..2047)
        MAX-ACCESS  read-write
        STATUS  current
        DESCRIPTION
            "the bind-sip-addr Service Id"
        ::= { dpiBindSipAddr 3 } 
        
    dpiBindSipAddrOK   OBJECT-TYPE
        SYNTAX   INTEGER{enable(1)}
        MAX-ACCESS  read-write
        STATUS  current
        DESCRIPTION
            "the commit of bind-sip-addr"
        ::= { dpiBindSipAddr 4 }  
        
    dpiNoBindSipAddr   OBJECT-TYPE
        SYNTAX   INTEGER{enable(1)}
        MAX-ACCESS  read-write
        STATUS  current
        DESCRIPTION
            "the commit of no bind-sip-addr"
        ::= { dpiBindSipAddr 5 }   
        
    dpiShowIpService  OBJECT-TYPE
        SYNTAX   INTEGER(1..2047)
        MAX-ACCESS  read-only
        STATUS  current
        DESCRIPTION
            "show the current bind-sip-addr Service Id"
        ::= { dpiBindSipAddr 6 } 
        
 --  bind switchport
    dpiBindSwitchport     OBJECT IDENTIFIER ::= { dpiTemplate 7 }
        
    dpiBindSwitchportPort OBJECT-TYPE
        SYNTAX   DisplayString
        MAX-ACCESS  read-write
        STATUS  current
        DESCRIPTION
            "the local port id of bind-switchport"
        ::= { dpiBindSwitchport 2 }  
        
   dpiBindSwitchService OBJECT-TYPE
        SYNTAX   INTEGER(1..2047)
        MAX-ACCESS  read-write
        STATUS  current
        DESCRIPTION
            "the service id of bind-switchport"
        ::= { dpiBindSwitchport 3 }  
   
   dpiBindSwitchportOK     OBJECT-TYPE
        SYNTAX   INTEGER{enable(1)}
        MAX-ACCESS  read-write
        STATUS  current
        DESCRIPTION
            "the commit of bind-switchport"
        ::= { dpiBindSwitchport 4 }   
    
   dpiNoBindSwitchport   OBJECT-TYPE
        SYNTAX   INTEGER{enable(1)}
        MAX-ACCESS  read-write
        STATUS  current
        DESCRIPTION
            "the commit of no bind-switchport"
        ::= { dpiBindSwitchport 5 } 
  
   dpiShowPortService  OBJECT-TYPE
        SYNTAX   INTEGER(1..2047)
        MAX-ACCESS  read-only
        STATUS  current
        DESCRIPTION
            "show the current service id of bind-switchport"
        ::= { dpiBindSwitchport 6 }  
        
        
  -- show vlan-service
  --  dpiShowVlanService     OBJECT IDENTIFIER ::= { dpiTemplate 8 }  
    
  --  dpiShowVlanServiceVlan  OBJECT-TYPE
  --      SYNTAX   INTEGER(1..4094)
  --      MAX-ACCESS  read-write
  --      STATUS  current
  --      DESCRIPTION
  --          "the Vlan ID of show vlan-service"
  --     ::= { dpiShowVlanService 1 }
        
  -- dpiShowVlanServiceService  OBJECT-TYPE
  --      SYNTAX   INTEGER(1..2047)
  --      MAX-ACCESS  read-only
  --      STATUS  current
   --     DESCRIPTION
  --          "show the current service id of show Vlan-id"
  --      ::= { dpiShowVlanService 2 }   
        
 -- show support-protocol all
 --   dpiShowSupportProtocol    OBJECT-TYPE
 --       SYNTAX   DisplayString
 --       MAX-ACCESS  read-only
 --       STATUS  current
 --       DESCRIPTION
 --           "show the all protocol what the template supports"
 --       ::= { dpiTemplate 9 } 
        
 -- set active-connection-save-interval
     dpiSetActiceConnectionSaveInterval   OBJECT-TYPE
        SYNTAX   INTEGER(1..60)
        MAX-ACCESS  read-write
        STATUS  current
        DESCRIPTION
            "set active-connection-save-interval"
        ::= { dpiConfigMode 9 } 
        
-- clear connection-all
    dpiClearConnectionAll  OBJECT-TYPE
        SYNTAX   INTEGER{enable(1)}
        MAX-ACCESS  read-write
        STATUS  current
        DESCRIPTION
            "clear connection-all"
        ::= { dpiConfigMode 10 } 

-- show connection-by-ip
--    dpiShowConnectionByIp   OBJECT-TYPE
--        SYNTAX   DisplayString
--        MAX-ACCESS  read-only
 --       STATUS  current
--        DESCRIPTION
 --           "show connection-by-ip"
 --       ::= { dpiConfigMode 11 } 
--------------------------------------------------------------------------------
dpiMonitorLog OBJECT IDENTIFIER ::= { zxrDPI 3 }    

--   upload auto
   dpiUploadAuto   OBJECT IDENTIFIER ::= { dpiMonitorLog 1 }  
   
   dpiUploadAutoSlot  OBJECT-TYPE
        SYNTAX   INTEGER(1..12)
        MAX-ACCESS  read-write
        STATUS  current
        DESCRIPTION
            "the slot id of upload-auto"
        ::= { dpiUploadAuto 1 } 
        
    
   dpiUploadAutoEnable    OBJECT-TYPE
        SYNTAX   INTEGER{enable(1),disable(0)}
        MAX-ACCESS  read-write
        STATUS  current
        DESCRIPTION
            "the enable of upload-auto"
        ::= { dpiUploadAuto 2 }
        
   dpiUploadAutoOK      OBJECT-TYPE
        SYNTAX   INTEGER{enable(1)}
        MAX-ACCESS  read-write
        STATUS  current
        DESCRIPTION
            "the commit of upload-auto"
        ::= { dpiUploadAuto 3 }
        
 --  upload interval
      dpiUploadInterval   OBJECT IDENTIFIER ::= { dpiMonitorLog 2 }  
   
   dpiUploadIntervalSlot  OBJECT-TYPE
        SYNTAX   INTEGER(1..12)
        MAX-ACCESS  read-write
        STATUS  current
        DESCRIPTION
            "the slot id of upload-interval"
        ::= { dpiUploadInterval 1 } 
        
    
   dpiUploadTimeInterval    OBJECT-TYPE
        SYNTAX   INTEGER(2..60)
        MAX-ACCESS  read-write
        STATUS  current
        DESCRIPTION
            "the time-interval of upload-interval"
        ::= { dpiUploadInterval 2 }
        
   dpiUploadIntervalOK      OBJECT-TYPE
        SYNTAX   INTEGER{enable(1)}
        MAX-ACCESS  read-write
        STATUS  current
        DESCRIPTION
            "the commit of upload-interval"
        ::= { dpiUploadInterval 3 }   
        
 --  logo-file list-dir   
     dpiLogFileListDir   OBJECT IDENTIFIER ::= { dpiMonitorLog 3 }  
   
   dpiLogFileListDirSlot  OBJECT-TYPE
        SYNTAX   INTEGER(1..12)
        MAX-ACCESS  read-write
        STATUS  current
        DESCRIPTION
            "the slot id of Log-File-List-Dir"
        ::= { dpiLogFileListDir 1 } 
        
    
   dpiLogFileListDirFtpFile    OBJECT-TYPE
        SYNTAX   DisplayString
        MAX-ACCESS  read-write
        STATUS  current
        DESCRIPTION
            "the file on ftp"
        ::= { dpiLogFileListDir 2 }  
    
   dpiLogFileListDirLocalDir    OBJECT-TYPE
        SYNTAX   DisplayString
        MAX-ACCESS  read-write
        STATUS  current
        DESCRIPTION
            "the local directory"
        ::= { dpiLogFileListDir 3 }

        
   dpiLogFileListDirOK      OBJECT-TYPE
        SYNTAX   INTEGER{enable(1)}
        MAX-ACCESS  read-write
        STATUS  current
        DESCRIPTION
            "the commit of logo-file list-dir"
        ::= { dpiLogFileListDir 4 } 
   
  --logo-file delete-dir
     dpiLogFileDeleteDir   OBJECT IDENTIFIER ::= { dpiMonitorLog 4 }  
   
   dpiLogFileDeleteDirSlot  OBJECT-TYPE
        SYNTAX   INTEGER(1..12)
        MAX-ACCESS  read-write
        STATUS  current
        DESCRIPTION
            "the slot id of Log-File-Delete-Dir "
        ::= { dpiLogFileDeleteDir 1 } 
        
    
   dpiLogFileDeleteDirName    OBJECT-TYPE
        SYNTAX   DisplayString
        MAX-ACCESS  read-write
        STATUS  current
        DESCRIPTION
            "the directory name of Log-File-Delete-Dir"
        ::= { dpiLogFileDeleteDir 2 }
        
   dpiLogFileDeleteDirOK      OBJECT-TYPE
        SYNTAX   INTEGER{enable(1)}
        MAX-ACCESS  read-write
        STATUS  current
        DESCRIPTION
            "the commit of Log-File-Delete-Dir"
        ::= { dpiLogFileDeleteDir 3 }    
        
 -- logo-file delete-file    
    dpiLogFileDeleteFile   OBJECT IDENTIFIER ::= { dpiMonitorLog 5 }  
   
   dpiLogFileDeleteFileSlot  OBJECT-TYPE
        SYNTAX   INTEGER(1..12)
        MAX-ACCESS  read-write
        STATUS  current
        DESCRIPTION
            "the slot id of Log-File-Delete-File "
        ::= { dpiLogFileDeleteFile 1 } 
        
    
   dpiLogFileDeleteFileName    OBJECT-TYPE
        SYNTAX   DisplayString
        MAX-ACCESS  read-write
        STATUS  current
        DESCRIPTION
            "the directory name of Log-File-Delete-File"
        ::= { dpiLogFileDeleteFile 2 }
        
   dpiLogFileDeleteFileOK      OBJECT-TYPE
        SYNTAX   INTEGER{enable(1)}
        MAX-ACCESS  read-write
        STATUS  current
        DESCRIPTION
            "the commit of Log-File-Delete-File"
        ::= { dpiLogFileDeleteFile 3 }  
        
 --  update dpi-logo
 
   dpiUpdateDpiLog    OBJECT IDENTIFIER ::= { dpiMonitorLog 6 }
   
   dpiUpdateDpiLogSlot OBJECT-TYPE
        SYNTAX   INTEGER(1..12)
        MAX-ACCESS  read-write
        STATUS  current
        DESCRIPTION
            "the slot id of Update-Dpi-Log "
        ::= { dpiUpdateDpiLog 1 }  
           
        
   dpiLogServerFileName  OBJECT-TYPE
        SYNTAX   DisplayString
        MAX-ACCESS  read-write
        STATUS  current
        DESCRIPTION
            "the file name of Log-update"
        ::= { dpiUpdateDpiLog 3 }  
        
           
        
   dpiLogLocalFileName  OBJECT-TYPE
        SYNTAX   DisplayString
        MAX-ACCESS  read-write
        STATUS  current
        DESCRIPTION
            "the loacl file name of Log-update"
        ::= { dpiUpdateDpiLog 5 }

     
     
     dpiUpdateDpiLogOK       OBJECT-TYPE
        SYNTAX   INTEGER{enable(1)}
        MAX-ACCESS  read-write
        STATUS  current
        DESCRIPTION
            "the commit of Update Dpi Log"
        ::= { dpiUpdateDpiLog 6 }    
        
 --  upload today-logo
     dpiUploadTodayLog  OBJECT-TYPE
        SYNTAX   INTEGER(1..12)
        MAX-ACCESS  read-write
        STATUS  current
        DESCRIPTION
            "the slot id of Upload today log "
        ::= { dpiMonitorLog 7 }

 ------------------------------------------------------------ 
 -- commit   
    dpiCommit   OBJECT-TYPE
        SYNTAX   INTEGER{enable(1)}
        MAX-ACCESS  read-write
        STATUS  current
        DESCRIPTION
            "the commit of the DPI Config"
        ::= { zxrDPI 4 }   
        
--  update dpi-signature version
   dpiUpdateSignatureVersion   OBJECT-TYPE
        SYNTAX   INTEGER{enable(1)}
        MAX-ACCESS  read-write
        STATUS  current
        DESCRIPTION
            "update the DPI signature version"
        ::= { zxrDPI 5 }  
        
 ----------------------------------------------------------- 
 
 --  vlan bind dpi-template
   dpiVlanBindDpiTemplate OBJECT IDENTIFIER ::= { zxrDPI 6 }
   
   dpiVlanInterfaceName  OBJECT-TYPE
        SYNTAX   DisplayString
        MAX-ACCESS  read-write
        STATUS  current
        DESCRIPTION
            "enter the Interface Name"
        ::= { dpiVlanBindDpiTemplate 1 }    
        
    dpiBindDpiTemplate  OBJECT-TYPE
        SYNTAX   INTEGER(1..4095)
        MAX-ACCESS  read-write
        STATUS  current
        DESCRIPTION
            "bind the Dpi-template ID"
        ::= { dpiVlanBindDpiTemplate 2 }  

 --show all signature-entry
     dpiShowAllSignatureEntryTable     OBJECT-TYPE
        SYNTAX         SEQUENCE OF DpiShowAllSignatureEntry 
        MAX-ACCESS     not-accessible
        STATUS         current
        DESCRIPTION
            "A Signature-Entry table."
    ::= { zxrDPI 7 }   
    
    dpiShowAllSignatureEntry    OBJECT-TYPE
        SYNTAX          DpiShowAllSignatureEntry 
        MAX-ACCESS      not-accessible
        STATUS          current
        DESCRIPTION
            "A list of  entries of Signature-Entry."
        INDEX  { dpiAllSignatureEntryID }
    ::= { dpiShowAllSignatureEntryTable 1 }
    
    DpiShowAllSignatureEntry ::= SEQUENCE 
    {
       	dpiAllSignatureEntryID INTEGER,
        dpiAllSignatureEntryContent DisplayString
    }
        
    dpiAllSignatureEntryID   OBJECT-TYPE
         SYNTAX   INTEGER(1..12287)
        MAX-ACCESS  read-only
        STATUS  current
        DESCRIPTION
            "the id of dpi Signature Entry"
    ::= { dpiShowAllSignatureEntry 1}   
    
    dpiAllSignatureEntryContent    OBJECT-TYPE
        SYNTAX   DisplayString
        MAX-ACCESS  read-only
        STATUS  current
        DESCRIPTION
            "A string description of the Key Content."
        ::= { dpiShowAllSignatureEntry 2 } 
        
 --show all signature-symbol 
     dpiShowAllSignatureSymbolTable     OBJECT-TYPE
        SYNTAX         SEQUENCE OF DpiShowAllSignatureSymbolEntry 
        MAX-ACCESS     not-accessible
        STATUS         current
        DESCRIPTION
            "A Signature-Symbol table."
    ::= { zxrDPI 8 }   
    
    dpiShowAllSignatureSymbolEntry    OBJECT-TYPE
        SYNTAX          DpiShowAllSignatureSymbolEntry 
        MAX-ACCESS      not-accessible
        STATUS          current
        DESCRIPTION
            "A list of  entries of Signature-Symbol."
        INDEX  { dpiAllSignatureSymbolID }
    ::= { dpiShowAllSignatureSymbolTable 1 }
    
    DpiShowAllSignatureSymbolEntry ::= SEQUENCE 
    {
       dpiAllSignatureSymbolID  INTEGER,
       dpiAllSignatureSymbolEntryList   DisplayString,
       dpiAllSignatureSymbolHitNumLimit    INTEGER,
       dpiAllSignatureSymbolProtocol       INTEGER   
      }
    
    dpiAllSignatureSymbolID   OBJECT-TYPE
        SYNTAX   INTEGER(1..6143)
        MAX-ACCESS  read-only
        STATUS  current
        DESCRIPTION
            "the id of dpi Signature Symbol"
        ::= { dpiShowAllSignatureSymbolEntry 1 }   
        
    dpiAllSignatureSymbolEntryList   OBJECT-TYPE
        SYNTAX       DisplayString
        MAX-ACCESS read-only
        STATUS current
        DESCRIPTION
            "The id-bitmap of the signature-entry included by signature-symbol ,display 16 entries at most. "
              
    ::= { dpiShowAllSignatureSymbolEntry 2 }
                                               
    dpiAllSignatureSymbolHitNumLimit  OBJECT-TYPE
        SYNTAX   INTEGER(1..16)
        MAX-ACCESS  read-only
        STATUS  current
        DESCRIPTION
            "A string description of the Key."
        ::= { dpiShowAllSignatureSymbolEntry 3 }   
        
      dpiAllSignatureSymbolProtocol  OBJECT-TYPE
        SYNTAX   INTEGER{normal(1),inherit(2)}
        MAX-ACCESS  read-only
        STATUS  current
        DESCRIPTION
            "the protocol of the symbol: normal=1,inherit=2"
        ::= { dpiShowAllSignatureSymbolEntry 4 }

        
 --show all  flow-pool
      dpiShowAllFlowPoolTable     OBJECT-TYPE
        SYNTAX         SEQUENCE OF DpiShowAllFlowPoolEntry 
        MAX-ACCESS     not-accessible
        STATUS         current
        DESCRIPTION
            "A Flow-Pool table."
    ::= { zxrDPI 9 }   
    
    dpiShowAllFlowPoolEntry    OBJECT-TYPE
        SYNTAX          DpiShowAllFlowPoolEntry 
        MAX-ACCESS      not-accessible
        STATUS          current
        DESCRIPTION
            "A list of  entries of flow-pool."
        INDEX  { dpiAllFlowPoolID }
    ::= { dpiShowAllFlowPoolTable 1 }
    
    DpiShowAllFlowPoolEntry ::= SEQUENCE 
    {
       	dpiAllFlowPoolID INTEGER,
        dpiAllUpStreamRate  INTEGER,
       dpiAllUpStreamCbs    Integer32,
       dpiAllUpStreamEbs    Integer32,
       dpiAllDownStreamRate  INTEGER,
       dpiAllDownStreamCbs    Integer32,
       dpiAllDownStreamEbs    Integer32


    }
    
     dpiAllFlowPoolID  OBJECT-TYPE
        SYNTAX   INTEGER(2..8191)
        MAX-ACCESS  read-only
        STATUS  current
        DESCRIPTION
            "the ID of dpi Stream limit"
        ::= { dpiShowAllFlowPoolEntry 1 }  
            
          
       dpiAllUpStreamRate  OBJECT-TYPE
        SYNTAX   INTEGER(10..100000)
        MAX-ACCESS  read-only
        STATUS  current
        DESCRIPTION
            "the rate of dpi Stream limit"
        ::= { dpiShowAllFlowPoolEntry 2 } 

			dpiAllUpStreamCbs  OBJECT-TYPE
        SYNTAX   Integer32
        MAX-ACCESS  read-only
        STATUS  current
        DESCRIPTION
            "the cbs of the rate-limit."
        ::= { dpiShowAllFlowPoolEntry 3 }
        
      dpiAllUpStreamEbs  OBJECT-TYPE
        SYNTAX   Integer32
        MAX-ACCESS  read-only
        STATUS  current
        DESCRIPTION
            "the ebs of the rate-limit."
        ::= { dpiShowAllFlowPoolEntry 4 }    
        
         dpiAllDownStreamRate  OBJECT-TYPE
        SYNTAX   INTEGER(10..100000)
        MAX-ACCESS  read-only
        STATUS  current
        DESCRIPTION
            "the rate of dpi Stream limit"
        ::= { dpiShowAllFlowPoolEntry 5 } 

			dpiAllDownStreamCbs  OBJECT-TYPE
        SYNTAX   Integer32
        MAX-ACCESS  read-only
        STATUS  current
        DESCRIPTION
            "the cbs of the rate-limit."
        ::= { dpiShowAllFlowPoolEntry 6 }
        
      dpiAllDownStreamEbs  OBJECT-TYPE
        SYNTAX   Integer32
        MAX-ACCESS  read-only
        STATUS  current
        DESCRIPTION
            "the ebs of the rate-limit."
        ::= { dpiShowAllFlowPoolEntry 7 }

 
 --show all subservice
     dpiShowAllSubserviceTable     OBJECT-TYPE
        SYNTAX         SEQUENCE OF DpiShowAllSubserviceEntry 
        MAX-ACCESS     not-accessible
        STATUS         current
        DESCRIPTION
            "A subservice table."
    ::= { zxrDPI 10 }   
    
    dpiShowAllSubserviceEntry    OBJECT-TYPE
        SYNTAX          DpiShowAllSubserviceEntry 
        MAX-ACCESS      not-accessible
        STATUS          current
        DESCRIPTION
            "A list of  entries of subservice."
        INDEX  { dpiAllSubserviceID }
    ::= { dpiShowAllSubserviceTable 1 }
    
    DpiShowAllSubserviceEntry ::= SEQUENCE 
    {
       	dpiAllSubserviceID INTEGER,
 --     dpiAllSubserviceSymbolNum INTEGER,
        dpiAllSubserviceFlowpoolID INTEGER,
        dpiAllSubserviceAction   INTEGER,
        dpiAllSubserviceAgingTime INTEGER,
        dpiAllSubserviceSymbolList DisplayString,
        dpiAllSubserviceProtocol  DisplayString
    }
       
   dpiAllSubserviceID  OBJECT-TYPE
        SYNTAX   INTEGER(1..8191)
        MAX-ACCESS  read-only
        STATUS  current
        DESCRIPTION
            "the ID of dpi Subservice"
        ::= { dpiShowAllSubserviceEntry 1 }

 --			dpiAllSubserviceSymbolNum  OBJECT-TYPE
 --       SYNTAX   INTEGER(1..6143)
 --       MAX-ACCESS  read-only
 --       STATUS  current
 --       DESCRIPTION
 --           "the number of the bound Symbol"
 --       ::= { dpiShowAllSubserviceEntry 2 }
        
      dpiAllSubserviceFlowpoolID  OBJECT-TYPE
        SYNTAX   INTEGER(2..8191)
        MAX-ACCESS  read-only
        STATUS  current
        DESCRIPTION
            "the ID of the bound Flow-pool"
        ::= { dpiShowAllSubserviceEntry 3 }
        
      dpiAllSubserviceAction  OBJECT-TYPE
        SYNTAX   INTEGER{permit(1),deny(0)}
        MAX-ACCESS  read-only
        STATUS  current
        DESCRIPTION
            "the status of the subservice"
        ::= { dpiShowAllSubserviceEntry 4 }
        
      dpiAllSubserviceAgingTime  OBJECT-TYPE
        SYNTAX   INTEGER(1..60)
        MAX-ACCESS  read-only
        STATUS  current
        DESCRIPTION
            "the time of the aging"
        ::= { dpiShowAllSubserviceEntry 5 }
        
      dpiAllSubserviceSymbolList  OBJECT-TYPE
        SYNTAX   DisplayString
        MAX-ACCESS  read-only
        STATUS  current
        DESCRIPTION
            "the string of symbols included by Subservice."
        ::= { dpiShowAllSubserviceEntry 6 }   
        
      dpiAllSubserviceProtocol  OBJECT-TYPE
      SYNTAX   DisplayString
        MAX-ACCESS  read-only
        STATUS  current
        DESCRIPTION
            "All the protocol supported by Subservice."
        ::= { dpiShowAllSubserviceEntry 7 } 
        
 --show all service   
       dpiShowAllServiceTable     OBJECT-TYPE
        SYNTAX         SEQUENCE OF DpiShowAllServiceEntry 
        MAX-ACCESS     not-accessible
        STATUS         current
        DESCRIPTION
            "A Service table."
    ::= { zxrDPI 11 }   
    
    dpiShowAllServiceEntry    OBJECT-TYPE
        SYNTAX          DpiShowAllServiceEntry 
        MAX-ACCESS      not-accessible
        STATUS          current
        DESCRIPTION
            "A list of  entries of Service."
        INDEX  { dpiAllServiceID }
    ::= { dpiShowAllServiceTable 1 }
    
    DpiShowAllServiceEntry ::= SEQUENCE 
    {
       		dpiAllServiceID  INTEGER,
     		dpiAllServiceFlowPoolID   INTEGER,
 --    		dpiAllServiceConnectionLimit INTEGER,
     		dpiAllServiceSubserviceNum  INTEGER,
     		dpiAllServiceSubserviceList OCTET STRING
    }
     
    dpiAllServiceID  OBJECT-TYPE
        SYNTAX   INTEGER(1..2047)
        MAX-ACCESS  read-only
        STATUS  current
        DESCRIPTION
            "the ID of dpi Service"
        ::= { dpiShowAllServiceEntry 1 }
        
     dpiAllServiceFlowPoolID  OBJECT-TYPE
        SYNTAX   INTEGER(2..8191)
        MAX-ACCESS  read-only
        STATUS  current
        DESCRIPTION
            "the ID of dpi Service bound Flow-pool"
        ::= { dpiShowAllServiceEntry 2 }
        
 --    dpiAllServiceConnectionLimit  OBJECT-TYPE
 --       SYNTAX   INTEGER(0..1310719)
 --       MAX-ACCESS  read-only
 --       STATUS  current
 --       DESCRIPTION
 --           "the max number of the limited connections"
 --       ::= { dpiShowAllServiceEntry 3 }
        
      dpiAllServiceSubserviceNum  OBJECT-TYPE
        SYNTAX   INTEGER(1..8191)
        MAX-ACCESS  read-only
        STATUS  current
        DESCRIPTION
            "the number of dpi Subservice in Service"
        ::= { dpiShowAllServiceEntry 4 }
        
     dpiAllServiceSubserviceList  OBJECT-TYPE
        SYNTAX   OCTET STRING(SIZE(0..1049))
        MAX-ACCESS  read-only
        STATUS  current
        DESCRIPTION
            "the bitmap of subservice included by service."
        ::= { dpiShowAllServiceEntry 5 }  
        
 --show all template 
      dpiShowAllTemplateTable     OBJECT-TYPE
        SYNTAX         SEQUENCE OF DpiShowAllTemplateEntry 
        MAX-ACCESS     not-accessible
        STATUS         current
        DESCRIPTION
            "A Template table."
    ::= { zxrDPI 12 }   
    
    dpiShowAllTemplateEntry    OBJECT-TYPE
        SYNTAX          DpiShowAllTemplateEntry 
        MAX-ACCESS      not-accessible
        STATUS          current
        DESCRIPTION
            "A list of  entries of Template."
        INDEX  { dpiAllTemplateID }
    ::= { dpiShowAllTemplateTable 1 }
    
    DpiShowAllTemplateEntry ::= SEQUENCE 
    {
       		dpiAllTemplateID  INTEGER,
     		dpiAllTemplateCfgCmd   DisplayString
     }
   
   dpiAllTemplateID   OBJECT-TYPE
        SYNTAX   INTEGER(1..4095)
        MAX-ACCESS  read-only
        STATUS  current
        DESCRIPTION
            "the ID of dpi template"
        ::= { dpiShowAllTemplateEntry 1 }
    
   dpiAllTemplateCfgCmd      OBJECT-TYPE
        SYNTAX   DisplayString
        MAX-ACCESS  read-only
        STATUS  current
        DESCRIPTION
            "the configure commands of dpi template"
        ::= { dpiShowAllTemplateEntry 2 }

 --show mng ip
   dpiShowAllMnpIpTable     OBJECT-TYPE
        SYNTAX         SEQUENCE OF DpiShowAllMngIpEntry  
        MAX-ACCESS     not-accessible
        STATUS         current
        DESCRIPTION
            "the mng-ip table."
    ::= { zxrDPI 13 } 
 
     dpiShowAllMngIpEntry    OBJECT-TYPE
        SYNTAX          DpiShowAllMngIpEntry 
        MAX-ACCESS      not-accessible
        STATUS          current
        DESCRIPTION
            "A list of  entries of Mng-ip."
        INDEX  { dpiAllSlotID }
    ::= { dpiShowAllMnpIpTable 1 }   
    
     DpiShowAllMngIpEntry ::= SEQUENCE 
    {
       		dpiAllSlotID  INTEGER,
     		dpiAllMngIp   IpAddress,
     		dpiAllServerIp IpAddress, 
     		dpiAllMngIpIsUsed INTEGER,
     		dpiAllLogSaveInterval INTEGER,
     		dpiAllLogAutoUpload    INTEGER,
     		dpiAllLogUploadInterval  INTEGER
     		
     }
     
     dpiAllSlotID   OBJECT-TYPE
        SYNTAX   INTEGER(1..12)
        MAX-ACCESS  read-only
        STATUS  current
        DESCRIPTION
            "the ID of dpi slot"
        ::= { dpiShowAllMngIpEntry 1 }  
        
     dpiAllMngIp   OBJECT-TYPE
        SYNTAX   IpAddress
        MAX-ACCESS  read-only
        STATUS  current
        DESCRIPTION
            "the Mng-Ip"
        ::= { dpiShowAllMngIpEntry 2 }

     dpiAllServerIp   OBJECT-TYPE
        SYNTAX   IpAddress
        MAX-ACCESS  read-only
        STATUS  current
        DESCRIPTION
            "the Server-Ip"
        ::= { dpiShowAllMngIpEntry 3 } 

     dpiAllMngIpIsUsed   OBJECT-TYPE
        SYNTAX   INTEGER{used(1),notUsed(0)}
        MAX-ACCESS  read-only
        STATUS  current
        DESCRIPTION
            "the state of mng-ip"
        ::= { dpiShowAllMngIpEntry 4 }  
        
     dpiAllLogSaveInterval   OBJECT-TYPE
        SYNTAX   INTEGER
        MAX-ACCESS  read-only
        STATUS  current
        DESCRIPTION
            "the interval-time of saving dpi-log"
        ::= { dpiShowAllMngIpEntry 5 } 
                                        
      dpiAllLogAutoUpload   OBJECT-TYPE
        SYNTAX   INTEGER{enable(1),disable(0)}
        MAX-ACCESS  read-only
        STATUS  current
        DESCRIPTION
            "the state of auto-uploading dpi-log"
        ::= { dpiShowAllMngIpEntry 6 }    
        
      dpiAllLogUploadInterval   OBJECT-TYPE
        SYNTAX   INTEGER
        MAX-ACCESS  read-only
        STATUS  current
        DESCRIPTION
            "the interval-time of auto-uploading dpi-log"
        ::= { dpiShowAllMngIpEntry 7 } 

        
 -- show vlan binding
    dpiShowAllVlanDpiTable     OBJECT-TYPE
        SYNTAX         SEQUENCE OF DpiShowAllVlanDpiEntry  
        MAX-ACCESS     not-accessible
        STATUS         current
        DESCRIPTION
            "the vlan-dpi binding table."
    ::= { zxrDPI 14 }    
     
     dpiShowAllVlanDpiEntry    OBJECT-TYPE
        SYNTAX          DpiShowAllVlanDpiEntry 
        MAX-ACCESS      not-accessible
        STATUS          current
        DESCRIPTION
            "A list of  entries of vlan-dpi."
        INDEX  { dpiAllVlanID }
    ::= { dpiShowAllVlanDpiTable 1 } 
    
     DpiShowAllVlanDpiEntry ::= SEQUENCE 
    {
       		dpiAllVlanID  INTEGER,
     		dpiAllVlanBindTemplateID   INTEGER,
     		dpiAllVlanBindSlotID INTEGER, 
     		dpiAllVlanBindServiceID INTEGER,
     		dpiAllVlanBindIsUsed   INTEGER
     		 
     }

    dpiAllVlanID   OBJECT-TYPE
        SYNTAX   INTEGER
        MAX-ACCESS  read-only
        STATUS  current
        DESCRIPTION
            "the ID of Vlan"
        ::= { dpiShowAllVlanDpiEntry 1 }   
        
    dpiAllVlanBindTemplateID   OBJECT-TYPE
        SYNTAX   INTEGER
        MAX-ACCESS  read-only
        STATUS  current
        DESCRIPTION
            "the ID of Vlan-binding template"
        ::= { dpiShowAllVlanDpiEntry 2 } 
        
    dpiAllVlanBindSlotID   OBJECT-TYPE
        SYNTAX   INTEGER
        MAX-ACCESS  read-only
        STATUS  current
        DESCRIPTION
            "the ID of Vlan-binding dpi-slot "
        ::= { dpiShowAllVlanDpiEntry 3 } 
        
    dpiAllVlanBindServiceID   OBJECT-TYPE
        SYNTAX   INTEGER
        MAX-ACCESS  read-only
        STATUS  current
        DESCRIPTION
            "the ID of Vlan-binding service "
        ::= { dpiShowAllVlanDpiEntry 4 } 
        
        
     dpiAllVlanBindIsUsed   OBJECT-TYPE
        SYNTAX  INTEGER{used(1),notUsed(0)}
        MAX-ACCESS  read-only
        STATUS  current
        DESCRIPTION
            "the state of Vlan-binding "
        ::= { dpiShowAllVlanDpiEntry 5 }    
  

END
