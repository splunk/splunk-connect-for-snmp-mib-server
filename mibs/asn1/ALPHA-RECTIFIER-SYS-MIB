ALPHA-RECTIFIER-SYS-MIB DEFINITIONS ::= BEGIN

	--==========================================================================
	--
	-- Alpha Technologies Ltd.
	-- Copyright 2014
	--                      
	--==========================================================================

	IMPORTS
		MODULE-IDENTITY, OBJECT-TYPE
			FROM SNMPv2-SMI  
		ScaledNumber, simple
			FROM ALPHA-RESOURCE-MIB
	   	MODULE-COMPLIANCE, OBJECT-GROUP
      	 	FROM SNMPv2-CONF;  
                           
	rectifierSystem MODULE-IDENTITY
		LAST-UPDATED "201507280000Z"
		ORGANIZATION "Alpha Technologies Ltd."
		CONTACT-INFO
		  	 "Alpha Technologies Ltd.
			  7700 Riverfront Gate
			  Burnaby, BC  V5J 5M4
			  Canada

			  Tel: 1-604-436-5900
			  Fax: 1-604-436-1233"
		DESCRIPTION
		  	"This MIB defines the notification block(s) available in system controllers."

		REVISION    "201507280000Z"  -- July 28, 2015
		DESCRIPTION
			"
			Updated to follow MIB structure conformance rules.  Tested with 
			SimpleWeb: http://www.simpleweb.org      
			Passed highest level of compliance.  (level 6)
			"

		REVISION    "201507230000Z"  -- July 23, 2015
		DESCRIPTION
			"Fixed MIB syntax warnings."

		REVISION    "201506230000Z"  -- June 23, 2015
		DESCRIPTION
			"General revision."        

	::= { simple 1 }

                         
    -- Tectual convention
	
   rectSysTotalOutputCurrent OBJECT-TYPE
       SYNTAX      ScaledNumber
       MAX-ACCESS  read-only
       STATUS      current
       DESCRIPTION
               "
               Total accumulated output current of all the rectifiers associated with the current system.
               "
       ::= { rectifierSystem 1 }       
       
   rectSysTotalOutputPower OBJECT-TYPE
       SYNTAX      ScaledNumber
       MAX-ACCESS  read-only
       STATUS      current
       DESCRIPTION
               "Total output current of all system rectifiers."
       ::= { rectifierSystem 2 }
       
   rectSysTotalCapacityInstalledAmps OBJECT-TYPE
       SYNTAX      ScaledNumber
       MAX-ACCESS  read-only
       STATUS      current
       DESCRIPTION
               "A rectifier output current multiplied by the number of rectifiers installed."
       ::= { rectifierSystem 3 }

   rectSysTotalCapacityInstalledPower OBJECT-TYPE
       SYNTAX      ScaledNumber
       MAX-ACCESS  read-only
       STATUS      current
       DESCRIPTION
               "A rectifier output power multiplied by the number of rectifiers installed."
       ::= { rectifierSystem 4 }

   rectSysAverageRectifierOutputVoltage OBJECT-TYPE
       SYNTAX      ScaledNumber
       MAX-ACCESS  read-only
       STATUS      current
       DESCRIPTION
               "Average rectifier output voltage."
       ::= { rectifierSystem 5 }
  
   rectSysAverageRectifierACInputVoltage OBJECT-TYPE
       SYNTAX      ScaledNumber
       MAX-ACCESS  read-only
       STATUS      current
       DESCRIPTION
               "Average rectifier input voltage."
       ::= { rectifierSystem 6 }
  
   rectSysAveragePhase1Voltage OBJECT-TYPE
       SYNTAX      ScaledNumber
       MAX-ACCESS  read-only
       STATUS      current
       DESCRIPTION
               "Average output voltage of rectifiers in Phase 1."
       ::= { rectifierSystem 7 }

   rectSysAveragePhase2Voltage OBJECT-TYPE
       SYNTAX      ScaledNumber
       MAX-ACCESS  read-only
       STATUS      current
       DESCRIPTION
               "Average output voltage of rectifiers in Phase 2."
       ::= { rectifierSystem 8 }

   rectSysAveragePhase3Voltage OBJECT-TYPE
       SYNTAX      ScaledNumber
       MAX-ACCESS  read-only
       STATUS      current
       DESCRIPTION
               "Average output voltage of rectifiers in Phase 3."
       ::= { rectifierSystem 9 }               
       
   rectSysSystemVoltage OBJECT-TYPE
       SYNTAX      ScaledNumber
       MAX-ACCESS  read-only
       STATUS      current
       DESCRIPTION
               "System voltage."
       ::= { rectifierSystem 10 }

   rectSysTotalLoadCurrent OBJECT-TYPE
       SYNTAX      ScaledNumber
       MAX-ACCESS  read-only
       STATUS      current
       DESCRIPTION
               "Total load current."
       ::= { rectifierSystem 11 }
       
   rectSysBatteryVoltage OBJECT-TYPE
       SYNTAX      ScaledNumber
       MAX-ACCESS  read-only
       STATUS      current
       DESCRIPTION
               "Battery voltage."
       ::= { rectifierSystem 12 }
  
   rectSysBatteryCurrent OBJECT-TYPE
       SYNTAX      ScaledNumber
       MAX-ACCESS  read-only
       STATUS      current
       DESCRIPTION
               "Battery current."
       ::= { rectifierSystem 13 }
                                  
   rectSysBatteryTemperature OBJECT-TYPE
       SYNTAX      ScaledNumber
       MAX-ACCESS  read-only
       STATUS      current
       DESCRIPTION
               "Battery temperature."
       ::= { rectifierSystem 14 }

   rectSysSystemNumber OBJECT-TYPE
       SYNTAX      ScaledNumber
       MAX-ACCESS  read-only
       STATUS      current
       DESCRIPTION
               "Snmp ID# assigned to the system."
       ::= { rectifierSystem 15 }
                                      
                                      
                                      
	-- Conformance                                      
                                      
	conformance OBJECT IDENTIFIER ::= { rectifierSystem 100 }
	
	compliances OBJECT IDENTIFIER ::= { conformance 1 }
	
	compliance MODULE-COMPLIANCE
	      STATUS  current
	      DESCRIPTION
	          "The compliance statement for systems supporting
	          the alpha MIB."
	      MODULE -- this module
	          MANDATORY-GROUPS {
				rectifierGroup
	          }               
	   ::= { compliances 1 }
	
	rectifierGroups OBJECT IDENTIFIER ::= { conformance 2 }
         
	rectifierGroup OBJECT-GROUP
	    OBJECTS {      
	    	rectSysTotalOutputCurrent,
	    	rectSysTotalOutputPower, 
	    	rectSysTotalCapacityInstalledAmps,  
	    	rectSysTotalCapacityInstalledPower, 	
	    	rectSysAverageRectifierOutputVoltage,
	    	rectSysAverageRectifierACInputVoltage,
	    	rectSysAveragePhase1Voltage,
	    	rectSysAveragePhase2Voltage,
	    	rectSysAveragePhase3Voltage,
	    	rectSysSystemVoltage,
	    	rectSysTotalLoadCurrent,
	    	rectSysBatteryVoltage,
	    	rectSysBatteryCurrent,
	    	rectSysBatteryTemperature,
	    	rectSysSystemNumber
		}
		STATUS   current
		DESCRIPTION
		     "Alpha Rectifier System data list group."
		::= { rectifierGroups 1 }
           
           
END
