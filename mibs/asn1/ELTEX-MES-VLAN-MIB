ELTEX-MES-VLAN-MIB DEFINITIONS ::= BEGIN

-- -----------------------------------------------------------------------------
-- MIB NAME : Eltex MES VLAN
-- FILE NAME: eltVlan.mib
-- DATE     : 2013/11/18
-- VERSION  : 1.00
-- -----------------------------------------------------------------------------

IMPORTS
    rnd                                         FROM RADLAN-MIB
    DisplayString, TruthValue, RowStatus,
    MacAddress                                  FROM SNMPv2-TC
    VlanIndex, dot1qVlanIndex, PortList         FROM Q-BRIDGE-MIB
    ifIndex                                     FROM IF-MIB
    dot1dBasePort                               FROM BRIDGE-MIB
    SnmpAdminString                             FROM SNMP-FRAMEWORK-MIB
    MODULE-IDENTITY, OBJECT-TYPE, IpAddress     FROM SNMPv2-SMI
    InetAddressType                             FROM INET-ADDRESS-MIB
    eltMes                                      FROM ELTEX-MES
    vlanMulticastTvEntry                        FROM RADLAN-vlan-MIB;

eltMesVlan MODULE-IDENTITY
              LAST-UPDATED "201311180000Z"
              ORGANIZATION "Eltex Ltd."
              CONTACT-INFO
                      "www.eltex.nsk.ru"
              DESCRIPTION
                      "The private MIB module definition for IP Multicast support in Eltex devices."
              REVISION "201311180000Z"
              DESCRIPTION
                       "Editorial changes to support new MIB compilers."
               REVISION "201311180000Z"
              DESCRIPTION
                      "Initial version of this MIB."
          ::= { eltMes 5 }

EltVlanMode ::= TEXTUAL-CONVENTION
    STATUS      current
    DESCRIPTION
       "Indicates global VLAN QinQ operation mode.
       "
    REFERENCE
       "TR-101"
    SYNTAX      INTEGER {
                        basic(1),
                        tr101(2)
                }


eltVlanMulticastTvTable OBJECT-TYPE
    SYNTAX      SEQUENCE OF EltVlanMulticastTvEntry
    MAX-ACCESS  not-accessible
    STATUS      current
    DESCRIPTION
        "Multicast vlan used for this port"
    ::= { eltMesVlan 1 }

eltVlanMulticastTvEntry OBJECT-TYPE
    SYNTAX      EltVlanMulticastTvEntry
    MAX-ACCESS  not-accessible
    STATUS      current
    DESCRIPTION
        "Entry of multicast tag"
    AUGMENTS { vlanMulticastTvEntry }
    ::= { eltVlanMulticastTvTable 1 }

EltVlanMulticastTvEntry ::= SEQUENCE {
        eltVlanMulticastTvVIDIsTagged  TruthValue
}

eltVlanMulticastTvVIDIsTagged OBJECT-TYPE
    SYNTAX      TruthValue
    MAX-ACCESS  read-write
    STATUS      current
    DESCRIPTION
         "Specify whether the port is tagged in TV vlan or not."
    ::= { eltVlanMulticastTvEntry  1 }


eltVlanMode OBJECT-TYPE
    SYNTAX      EltVlanMode
    MAX-ACCESS  read-write
    STATUS      current
    DESCRIPTION
        "Global VLAN QinQ operation mode"
    ::= { eltMesVlan 2 }

eltdot1qPortVlanCurrentTable OBJECT-TYPE
    SYNTAX      SEQUENCE OF Eltdot1qPortVlanCurrentEntry
    MAX-ACCESS  not-accessible
    STATUS      current
    DESCRIPTION
        "A table containing current vlan port membership information."
    ::= { eltMesVlan 3 }

eltdot1qPortVlanCurrentEntry OBJECT-TYPE
    SYNTAX      Eltdot1qPortVlanCurrentEntry
    MAX-ACCESS  not-accessible
    STATUS      current
    DESCRIPTION
        "Current vlan membership information per port"
    INDEX   {ifIndex}
    ::= { eltdot1qPortVlanCurrentTable 1 }

Eltdot1qPortVlanCurrentEntry ::=SEQUENCE {

    eltdot1qPortVlanCurrentEgressList1to1024              OCTET STRING,
    eltdot1qPortVlanCurrentEgressList1025to2048           OCTET STRING,
    eltdot1qPortVlanCurrentEgressList2049to3072           OCTET STRING,
    eltdot1qPortVlanCurrentEgressList3073to4094           OCTET STRING
}

eltdot1qPortVlanCurrentEgressList1to1024 OBJECT-TYPE
   SYNTAX      OCTET STRING(SIZE(0..128))
   MAX-ACCESS  read-only
   STATUS      current
   DESCRIPTION
     "The port egress vlan current list."
   ::= { eltdot1qPortVlanCurrentEntry 1 }

eltdot1qPortVlanCurrentEgressList1025to2048 OBJECT-TYPE
   SYNTAX      OCTET STRING(SIZE(0..128))
   MAX-ACCESS  read-only
   STATUS      current
   DESCRIPTION
     "The port egress vlan current list."
   ::= { eltdot1qPortVlanCurrentEntry 2 }

eltdot1qPortVlanCurrentEgressList2049to3072 OBJECT-TYPE
   SYNTAX      OCTET STRING(SIZE(0..128))
   MAX-ACCESS  read-only
   STATUS      current
   DESCRIPTION
     "The port egress vlan current list."
   ::= { eltdot1qPortVlanCurrentEntry 3 }

eltdot1qPortVlanCurrentEgressList3073to4094 OBJECT-TYPE
   SYNTAX      OCTET STRING(SIZE(0..128))
   MAX-ACCESS  read-only
   STATUS      current
   DESCRIPTION
     "The port egress vlan current list."
   ::= { eltdot1qPortVlanCurrentEntry 4}

END
