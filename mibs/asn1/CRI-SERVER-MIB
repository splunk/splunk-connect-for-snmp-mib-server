--
-- ident	"@(#)xfire.my	1.46	97/02/14 SMI"
--
-- Copyright (c) 1996 by Sun Microsystems, Inc.
-- All rights reserved.
--

CRI-SERVER-MIB DEFINITIONS ::= BEGIN

IMPORTS
	enterprises			
		FROM RFC1155-SMI
    	OBJECT-TYPE				
		FROM RFC-1212
	TRAP-TYPE 			
		FROM RFC-1215;

	sun			OBJECT IDENTIFIER ::= { enterprises 34 }

	--
	-- DESCRIPTION	
	-- "The MIB module to describe objects for Sun Server 
	-- class machines. This MIB is organized into 2 major
	-- sub-trees. One sub-tree is intended for general
	-- objects that should apply to all server class machines.
	-- And another sub-tree describing objects that are
	-- specific to the Starfire server machine. 
	-- 
	-- This organization is in accordance to the MIB layout
	-- of other major computer corporations in describing
	-- computer systems."
	
	products	OBJECT IDENTIFIER ::= { sun 2 }
	
	-- display string
	DisplayString ::= OCTET STRING

	-- a truth value
	Boolean ::= INTEGER { true(1), false(2) }

	-- a YesNo value
	YesNo ::= INTEGER { yes(1), no(2) }

	general OBJECT IDENTIFIER ::= { products 1 }
	
	------------------------------------------------------------------
	-- Platform group
	------------------------------------------------------------------

	platform OBJECT IDENTIFIER ::= { general 1 }

	platformType OBJECT-TYPE
		SYNTAX 		INTEGER {
					ue10000(1)
				}
		ACCESS		read-only
		STATUS		mandatory
		DESCRIPTION	"The platform type. Currently, only one
				platform is defined: Starfire.  There is no
				plan to backport to CS6400 yet."
		::= { platform 1 }

	platformName OBJECT-TYPE
		SYNTAX		DisplayString
		ACCESS		read-only
		STATUS		mandatory
		DESCRIPTION	"The name assigned to a physical machine."
		::= { platform 2 }

	platformAmbientTemp OBJECT-TYPE
		SYNTAX		INTEGER
		ACCESS		read-only
		STATUS		mandatory
		DESCRIPTION	"The current ambient temperature of the 
				platform. The temperature will be in Celsius."
		::= { platform 3 }
	
	platformReset OBJECT-TYPE
		SYNTAX		INTEGER {
					reset (1)
					}
		ACCESS		read-write
		STATUS		mandatory
		DESCRIPTION	"This member resets the platform."
		::= { platform 4 }

	platformInterconnectClockFreq OBJECT-TYPE 
		SYNTAX		INTEGER 
		ACCESS		read-only
		STATUS		mandatory
		DESCRIPTION	"This member is the current interconnect
				frequency of the platform. The unit is in Hz."
		::= { platform 5 }

	platformProcClockFreq OBJECT-TYPE
		SYNTAX		INTEGER
		ACCESS		read-only
		STATUS		mandatory
		DESCRIPTION	"This member is the current processor clock 
				frequency of the platform. The unit is in Hz."
		::= { platform 6 }

	platformJtagClockFreq OBJECT-TYPE
		SYNTAX		INTEGER
		ACCESS		read-only
		STATUS		mandatory
		DESCRIPTION	"This member is the current JTAG clock 
				frequency of the platform. The unit is in Hz.
				Note: this member is only measurable in
				the rev-3 control board. If this unit is
				not available (rev-1 or rev-2 control board),
				the returning value is set to 0 Hz."
		::= { platform 7 }

	platformTargetInterconnectClockFreq OBJECT-TYPE
		SYNTAX		INTEGER (40000000..120000000)
		ACCESS		read-write
		STATUS		mandatory
		DESCRIPTION	"This member is the targeted interconnect clock
				frequency. The unit is in Hz and the valid 
				range is between 40,000,000 Hz and
				120,000,000 Hz.
				
				The platformTargetInterconnectClockFreq, 
				platformTargetProcClockMultiple and 
				platformTargetJtagClockFreq must be 
				established prior to system operation.
				They are used as the guideline to 
				set up the interconnect, processor and JTAG 
				clock frequency of the platform. 
				These value are maintained in SSP persistent 
				store."
		::= { platform 8 }

	platformTargetProcClockMultiple OBJECT-TYPE
		SYNTAX		INTEGER {
					two-to-one (1),
					three-to-one (2),
					three-to-two (3)
				}
		ACCESS		read-write
		STATUS		mandatory
		DESCRIPTION	"This member is the targeted processor clock
				frequency expressed in terms of a specific
				factor of the system clock. Possible options
				are factor of 2 or 3. See 
				platformTargetInterconnectClockFreq for more
				detail.
				A possible Blackbird processor would use the 
				3:2 ratio."
		::= { platform 9 }

	platformTargetJtagClockFreq OBJECT-TYPE
		SYNTAX		INTEGER (2000000..12000000)
		ACCESS		read-only
		STATUS		mandatory
		DESCRIPTION	"This member is the targeted JTAG clock
				frequency. The unit is in Hz.
				See platformTargetSystemClockFreq for more 
				detail."
		::= { platform 10 }

	platformMasterConBrd OBJECT-TYPE
		SYNTAX		INTEGER (0..1)
		ACCESS		read-only
		STATUS		mandatory
		DESCRIPTION	"This member is the master control board
				number."
		::=	{ platform 11 }

	platformSysClkConBrd OBJECT-TYPE
		SYNTAX		INTEGER (0..1)
		ACCESS		read-only
		STATUS		mandatory
		DESCRIPTION	"This member is the control board providing
				system clock to the platform."
		::=	{ platform 12 }

	------------------------------------------------------------------
	-- Configuration group
	-- This group describes domain and physical configuration.
	------------------------------------------------------------------
	
	conf OBJECT IDENTIFIER ::= { general 2 }

	confNumDomain OBJECT-TYPE	
		SYNTAX		INTEGER 
		ACCESS		read-only
		STATUS		mandatory
		DESCRIPTION	"The number of domain in the platform.
				Domains are created with command, domain_create.
				Domains are removed with command, 
				domain_remove."
		::= { conf 1 }

	confNumSysBrd OBJECT-TYPE
		SYNTAX		INTEGER
		ACCESS		read-only
		STATUS		mandatory
		DESCRIPTION	"The number of system board in the platform.
				The max # system board in a Starfire system is 
				16."
		::= { conf 2 }

	confNumProc OBJECT-TYPE
		SYNTAX		INTEGER
		ACCESS		read-only
		STATUS		mandatory
		DESCRIPTION	"The number of processor in a system board.
				The max # processors in a Starfire system is 
				64."
		::= { conf 3 }

	confNumConBrd OBJECT-TYPE
		SYNTAX		INTEGER
		ACCESS		read-only
		STATUS		mandatory
		DESCRIPTION	"The number of control board in the system.
				The max # control board in a Starfire system 
				is 2."
		::= { conf 4 }

	confNumCenterplane OBJECT-TYPE
		SYNTAX		INTEGER
		ACCESS		read-only
		STATUS		mandatory
		DESCRIPTION	"The number of centerplane in the system.
				The max # centerplane half board in a Starfire
				system is 2."
		::= { conf 5 }

	confNumSuppBrd OBJECT-TYPE
		SYNTAX		INTEGER
		ACCESS		read-only
		STATUS		mandatory
		DESCRIPTION	"The number of centerplane support board 
				in the system. The max # of centerplane 
				support board in a Starfire system is 2."
		::= { conf 6 }

	confNumIoCab OBJECT-TYPE
		SYNTAX		INTEGER
		ACCESS		read-only
		STATUS		mandatory
		DESCRIPTION	"The number of IO cabinet connected to the 
				 system. The max # of IO cabinets that can 
				 be connected to a Starfire system is 3."
		::= { conf 7 }

	confNumFanTray OBJECT-TYPE
		SYNTAX		INTEGER
		ACCESS		read-only
		STATUS		mandatory
		DESCRIPTION	"The number of fan tray in the system. The 
				max # of fan trays that can be installed in 
				a Starfire system is 16."
		::= { conf 8 }

	confNumBulkPower OBJECT-TYPE
		SYNTAX		INTEGER
		ACCESS		read-only
		STATUS		mandatory
		DESCRIPTION	"The number of bulk power supply in the system.
				The max # of bulk power supply in a Starfire 
				system is 8."
		::= { conf 9 }

	confNumSysBrdPower OBJECT-TYPE
		SYNTAX		INTEGER
		ACCESS		read-only
		STATUS		mandatory
		DESCRIPTION	"The number of system board power supply in 
				the system. The max # of system board 
				power supply for a Starfire system is 16. In
				Starfire, system board power supply is not
				a separate entity. It is integrated in
				a system board."
		::= { conf 10 }

	confSysBrdList OBJECT-TYPE
		SYNTAX		DisplayString
		ACCESS		read-only
		STATUS		mandatory
		DESCRIPTION	"A string identifying the system boards
				that are present in the system. The format
				of the string is: xx-xx-.. where xx is the
				system board number and the delimiter is a
				dash."
		::= { conf 11 }

	confProcList OBJECT-TYPE
		SYNTAX		DisplayString
		ACCESS		read-only
		STATUS		mandatory
		DESCRIPTION	"A string identifying the processors that are 
				present in the system. The format of the 
				string is: bb.pp-bb.pp-... where bb is the
				system board number and pp is the processor
				number within a system board, the delimiter 
				is a dash."
		::= { conf 12 }

	confConBrdList OBJECT-TYPE
		SYNTAX		DisplayString
		ACCESS		read-only
		STATUS		mandatory
		DESCRIPTION	"A string identifying the control boards
				that are present in the system. The format
				of the string is: xx-xx-.. where xx is the
				control board number and dash is the
				delimiter."
		::= { conf 13 }

	confCenterplaneList OBJECT-TYPE
		SYNTAX		DisplayString
		ACCESS		read-only
		STATUS		mandatory
		DESCRIPTION	"A string identifying the centerplanes
				that are present in the system. The format
				of the string is: xx-xx-.. where xx is the
				centerplane number and dash is the 
				delimiter."
		::= { conf 14 }

	confSuppBrdList OBJECT-TYPE
		SYNTAX		DisplayString
		ACCESS		read-only
		STATUS		mandatory
		DESCRIPTION	"A string identifying the centerplane support 
				boards that are present in the system. The
				format of the string is: xx-xx-... where xx
				is the centerplane support board number and
				dash is the delimiter."
		::= { conf 15 }

	confIoCabList OBJECT-TYPE
		SYNTAX		DisplayString
		ACCESS		read-only
		STATUS		mandatory
		DESCRIPTION	"A string identifying the IO cabinets that are 
				connected to the system. The format of the
				string is: xx-xx-... where xx is the I/O
				cabinet number and dash is the delimiter."
		::= { conf 16 }

	confFanTrayList OBJECT-TYPE
		SYNTAX		DisplayString
		ACCESS		read-only
		STATUS		mandatory
		DESCRIPTION	"A string identifying the fan trays that 
				are present in the system. the format of the
				string is: xx-xx-... where xx is the fan
				tray number and dash is the delimiter."
		::= { conf 17 }

	confBulkPowerList OBJECT-TYPE
		SYNTAX		DisplayString
		ACCESS		read-only
		STATUS		mandatory
		DESCRIPTION	"A string identifying the bulk power
				supplies that are present in the system. The
				format of the string is: x-x where x is 
				the bulk power supply number and dash is 
				the delimiter.  Bulk power supplies are
				numbered 0 to 7."
		::= { conf 18 }

	confSysBrdPowerList OBJECT-TYPE
		SYNTAX		DisplayString
		ACCESS		read-only
		STATUS		mandatory
		DESCRIPTION	"A string identifying the system board
				power supplies that are present in the system.
				The format of the string: xx-xx-... where
				xx is the system board power supply number
				and dash is the delimiter."
		::= { conf 19 }

	confMaxProcPerSysBrd OBJECT-TYPE
		SYNTAX		INTEGER
		ACCESS		read-only
		STATUS		mandatory
		DESCRIPTION	"The maximum number of processor in a system
				board. There is a max of 4 processors in
				a Starfire system board."
		::= { conf 20 }

	confMaxFanPerTray OBJECT-TYPE
		SYNTAX		INTEGER
		ACCESS		read-only
		STATUS		mandatory
		DESCRIPTION	"The maximum number of fan in a fan tray. There
				is a max of 2 fan in a Starfire fan tray."
		::= { conf 21 }

	confMaxLEDPerFanTray OBJECT-TYPE
		SYNTAX		INTEGER
		ACCESS		read-only
		STATUS		mandatory
		DESCRIPTION	"The maximum number of LED in a fan tray. There
				is a max of 2 LEDs in a Starfire fan tray."
		::= { conf 22 }

	confMaxLEDPerBulkPower OBJECT-TYPE
		SYNTAX		INTEGER
		ACCESS		read-only
		STATUS		mandatory
		DESCRIPTION	"The maximum number of LED in a bulk power
				supply. There is a max of 2 LEDs in a Starfire
				bulk power supply."
		::= { conf 23 }
	
	confMaxLEDPerSysBrd OBJECT-TYPE
		SYNTAX		INTEGER
		ACCESS		read-only
		STATUS		mandatory
		DESCRIPTION	"The maximum number of LED in a system board."
		::= { conf 24 }

	confMemAddrMap OBJECT-TYPE
		SYNTAX		OCTET STRING(SIZE(16))
		ACCESS		read-write
		STATUS		mandatory
		DESCRIPTION	"Starfire supports Shared Memory Domains. This
				requires the memory boards in the machine to
				have unique address. Because of this global
				requirement, Starfire hpost assigns the
				memory addresses, as well as for attaching
				boards. DR detach operation also assigns
				memory addresses. The method used to ensure
				unique addresses is to assign addresses
				based on slot number. To allow for 2 way
				inter-board interleaving, these addresses
				are slot number*8G.

				The map is a 16-byte array representing the 16
				slots. The lower 7 bits of each byte
				represents the unique address assign to that
				slot. The high bit is significant on a
				write-operation only, when set the
				corresponding slot of the map will be changed
				with the address represented by the lower
				7 bits. On a read operation the returning data
				represents the current memory map and the high
				bit of each byte is always 0. On a write
				operation the byte with the high bit set will
				be modified.

				The SNMP agent will perform a consistency check
				before committing a write operation.
				Consistency check simply makes sure no two slots
				will contain the same address if the write is
				performed. If consistency check fails, the write
				operation will return an error.
				"
		::= { conf 25 }

	------------------------------------------------------------------
	-- Domain table
	-- Domain information is kept in the SSP.
	------------------------------------------------------------------
	
	domainTable OBJECT-TYPE
		SYNTAX		SEQUENCE OF DomainEntry
		ACCESS		not-accessible
		STATUS		mandatory
		DESCRIPTION	"The domain table. The number of entries in
				the table is given by conf.confNumDomain."
		::= { general 3 }
	
	domainEntry OBJECT-TYPE
		SYNTAX		DomainEntry
		ACCESS		not-accessible
		STATUS		mandatory
		DESCRIPTION	"A domain table entry." 
		INDEX		{ domainIndex }
		::= { domainTable 1 }
	
	DomainEntry ::=
		SEQUENCE {
			domainIndex		INTEGER,
			domainName 		DisplayString,
			domainNumSysBrd		INTEGER,
			domainSysBrdList	DisplayString,
			domainOSVersion		DisplayString,
			domainProcList		DisplayString,
			domainBootProc		INTEGER,
			domainInterruptVector	INTEGER,
			domainSysBrdConfig	DisplayString,
			domainProcConfig	DisplayString,
			domainABusConfig	DisplayString,
			domainDBusConfig	DisplayString
		}

	domainIndex OBJECT-TYPE
		SYNTAX		INTEGER
		ACCESS		read-only
		STATUS		mandatory
		DESCRIPTION	"A number assigned to a domain."
		::= { domainEntry 1 }
	
	domainName OBJECT-TYPE
		SYNTAX		DisplayString
		ACCESS		read-only
		STATUS		mandatory
		DESCRIPTION	"Domain name in ASCII format."
		::= { domainEntry 2 }
	
	domainNumSysBrd OBJECT-TYPE
		SYNTAX		INTEGER (1..16)
		ACCESS		read-only
		STATUS		mandatory
		DESCRIPTION	"The number of system board assigned to this 
				domain."
		::= { domainEntry 3 }
	
	domainSysBrdList OBJECT-TYPE
		SYNTAX		DisplayString
		ACCESS		read-only
		STATUS		mandatory
		DESCRIPTION	"A list of system board entries belonging to 
				this domain. The number of boards is given by 
				domainNumSysBrd. The format of the string
				is: xx-xx where xx is the system board
				number and dash is the delimiter."
		::= { domainEntry 4 }
	
	domainOSVersion OBJECT-TYPE
		SYNTAX		DisplayString
		ACCESS		read-only
		STATUS		mandatory
		DESCRIPTION	"The OS version for this domain."
		::= { domainEntry 5 }
	
	domainProcList OBJECT-TYPE
		SYNTAX		DisplayString
		ACCESS		read-only
		STATUS		mandatory
		DESCRIPTION	"A list of processors belonging to this domain.
				The format of the string is in: 
				ss.bb-ss.bb-... where ss is the system board
				number, bb is the processor number within
				a system board, and dash is the delimiter."
		::= { domainEntry 6 }
	
	domainBootProc OBJECT-TYPE
		SYNTAX		INTEGER
		ACCESS		read-write
		STATUS		mandatory
		DESCRIPTION	"The boot processor number of this domain. If the value
					is -1, that means the domain is not configured/booted."
		::= { domainEntry 7 }

	domainInterruptVector OBJECT-TYPE
		SYNTAX		INTEGER
		ACCESS		read-write
		STATUS		mandatory
		DESCRIPTION	"Interrupts to the host processor via JTAG
				requires 2 pieces of information: the UPA ID
				of the target CPU and the interrupt number
				assigned to the bootbus interrupt by the host.
				The target UPA ID identifies the particular 
				bootbus and the proc ID (0 or 1) to be written
				into the bootbus interrupt register. The 
				interrupt number is the value to be
				written into word 0 of the mondo vector 
				of the target CPU. This number is computed
				by the host kernel.
				
				This object is a 13 bit value and is treated
				as an integer (32 bit) for easy manipulation."
		::= { domainEntry 8 }

	domainSysBrdConfig OBJECT-TYPE
		SYNTAX		DisplayString
		ACCESS		read-only
		STATUS		mandatory
		DESCRIPTION	"A list of configured system board entries
				belonging to this domain. The format of the
				string is: xx-xx where xx is the system board
				number and dash is the delimiter."
		::= { domainEntry 9 }

	domainProcConfig OBJECT-TYPE
		SYNTAX		DisplayString
		ACCESS		read-only
		STATUS		mandatory
		DESCRIPTION	"POST scans both blacklist and redlist files 
				to determine which components should not be 
				used to configure a domain. The content of 
				the blacklist and redlist files along with 
				the final result of a POST run is kept in a
				data structure, P2OBP, in the boot 
				processor's BBSRAM. The SNMP agent is
				responsible to retrieve the data structure 
				and extracts the necessary information to 
				produce the result.

				domainProcConfig describes the processors 
				configuration. Its format is a DisplayString 
				(character string) in the format of 
				xx.yyS-xx.yyS-...  where xx is a system 
				board number [0..15], yy is a processor 
				number within a system board [0..3], 
				S is a single character status code, 
				and (dash) '-' is for delimiting multiple 
				components. Valid status code include:
				F - Tested and Failed
				M - Missing
				R - Redlisted
				B - Blacklisted
				c - Crunched
				U - Good but not configured 
				G - Good
				A - Architecturally missing"
		::= { domainEntry 10 }
			
	domainABusConfig OBJECT-TYPE
		SYNTAX		DisplayString
		ACCESS		read-only
		STATUS		mandatory
		DESCRIPTION	"domainAbusConfig describes the address bus 
				configuration. Its format is a DisplayString 
				in the format of xxS-xxS-... where xx is an 
				address bus [0..3] and S is a status code 
				(see domainProcConfig)."
		::= { domainEntry 11 }
			
	domainDBusConfig OBJECT-TYPE
		SYNTAX		DisplayString
		ACCESS		read-only
		STATUS		mandatory
		DESCRIPTION	"domainDbusConfig describes the data bus 
				configuration. Its format is a DisplayString 
				in the format of xxS-xxS where xx is a data 
				bus [0..1] and S is a status code 
				(see domainProcConfig)."
		::= { domainEntry 12 }
			
	------------------------------------------------------------------
	-- General system board table
	-- Each system board entry contains generic objects that are
	-- applicable to all server platforms. 
	------------------------------------------------------------------
	
	sysBrdGenTable OBJECT-TYPE
		SYNTAX		SEQUENCE OF SysBrdGenEntry
		ACCESS		not-accessible
		STATUS		mandatory
		DESCRIPTION	"System board table. The number host of
				entries in the table is represented by 
				Conf.ConfNumSysBrd."
		::= { general 4 }
	
	sysBrdGenEntry OBJECT-TYPE
		SYNTAX		SysBrdGenEntry
		ACCESS		not-accessible
		STATUS		mandatory
		DESCRIPTION	"A system board table entry." 
		INDEX		{ sysBrdGenIndex }
		::= { sysBrdGenTable 1 }
	
	SysBrdGenEntry ::= SEQUENCE {
			sysBrdGenIndex		INTEGER,
			sysBrdGenNum		INTEGER,
			sysBrdGenPower		INTEGER,
			sysBrdGenNumProc	INTEGER,
			sysBrdGenProcList	DisplayString,
			sysBrdGenReset		INTEGER,
			sysBrdGenPowerControl	INTEGER
		}
	
	sysBrdGenIndex OBJECT-TYPE
		SYNTAX		INTEGER
		ACCESS		read-only
		STATUS		mandatory
		DESCRIPTION	"An index into this table."
		::= { sysBrdGenEntry 1 }
	
	sysBrdGenNum OBJECT-TYPE
		SYNTAX		INTEGER
		ACCESS		read-only
		STATUS		mandatory
		DESCRIPTION	"A unique number assigned to a system board.
				Index begins with 1." 
		::= { sysBrdGenEntry 2 }
	
	sysBrdGenPower OBJECT-TYPE
		SYNTAX		INTEGER {
					on (1),
					off (2)
				}
		ACCESS		read-only
		STATUS		mandatory
		DESCRIPTION	"Power status of the system board. To control
				power to a system board, modify the 
				sysBrdGenPowerControl."
		::= { sysBrdGenEntry 3 }
	
	sysBrdGenNumProc OBJECT-TYPE
		SYNTAX		INTEGER
		ACCESS		read-only
		STATUS		mandatory
		DESCRIPTION	"Number of processor that are present in this
				system board."
		::= { sysBrdGenEntry 4 }
	
	sysBrdGenProcList OBJECT-TYPE
		SYNTAX		DisplayString
		ACCESS		read-only
		STATUS		mandatory
		DESCRIPTION	"A string containing the processors list that 
				are present in this system board. The format
				of the string is: xx-xx where xx is the
				processor number within a system board, and
				dash is the delimiter."
		::= { sysBrdGenEntry 5 }
	
	sysBrdGenReset OBJECT-TYPE
		SYNTAX		INTEGER {
					reset (1)
					}
		ACCESS		read-write
		STATUS		mandatory
		DESCRIPTION	"This member resets the system board."
		::= { sysBrdGenEntry 6 }

	sysBrdGenPowerControl OBJECT-TYPE
		SYNTAX		INTEGER {
					on (1),
					off (2)
				}
		ACCESS		read-write
		STATUS		mandatory
		DESCRIPTION	"On reading it returns the power status of this 
				system board power supply. On writing, it 
				turns on/off this system board power supply."
		::= { sysBrdGenEntry 7 }
	
	------------------------------------------------------------------
	-- General processor state table
	-- This table describes the state of a processor.
	-- Each entry contains objects that are applicable to all server
	-- platforms.
	------------------------------------------------------------------
	
	procStateGenTable OBJECT-TYPE
		SYNTAX		SEQUENCE OF ProcStateGenEntry
		ACCESS		not-accessible
		STATUS		mandatory
		DESCRIPTION	"A table of processor entries."
		::= { general 5 }
	
	procStateGenEntry OBJECT-TYPE
		SYNTAX		ProcStateGenEntry
		ACCESS		not-accessible
		STATUS		mandatory
		DESCRIPTION	"A processor state table entry." 
		INDEX		{ procStateGenIndex }
		::= { procStateGenTable 1 }
	
	ProcStateGenEntry ::=
		SEQUENCE {
			procStateGenIndex 		INTEGER,
			procStateGenNum 		INTEGER,
			procStateGenHeartbeat 		Counter,
			procStateGenPgmSignature 	INTEGER,
			procStateGenPgmState 		INTEGER,
			procStateGenPgmSubState 	INTEGER,
			procStateGenTemp		INTEGER
		}
	
	procStateGenIndex OBJECT-TYPE
		SYNTAX		INTEGER
		ACCESS		read-only
		STATUS		mandatory
		DESCRIPTION	"An index into this table." 
		::= { procStateGenEntry 1 }
	
	procStateGenNum OBJECT-TYPE
		SYNTAX		INTEGER
		ACCESS		read-only
		STATUS		mandatory
		DESCRIPTION	"A unique number assigned to each CPU."
		::= { procStateGenEntry 2 }
	
	procStateGenHeartbeat OBJECT-TYPE
--		SYNTAX		INTEGER (0..'ffffffff'h)
		SYNTAX		Counter
		ACCESS		read-only
		STATUS		mandatory
		DESCRIPTION	"A counter being updated by the kernel.
				This serves an as indicator that the 
				kernel is alive and well."
		::= { procStateGenEntry 3 }
	
	procStateGenPgmSignature OBJECT-TYPE
		SYNTAX		INTEGER {
					post (1),
					download-helper (2),
					obp (3),
					os (4),
					unknown (5)
					}
		ACCESS		read-only
		STATUS		mandatory
		DESCRIPTION	"This value represents the current program 
				running on a processor. Only 4 programs
				are identified: POST, Download_helper, 
				OBP, and the kernel."
		::= { procStateGenEntry 4 }
	
	procStateGenPgmState OBJECT-TYPE
		SYNTAX		INTEGER {
					run (1),
					exit (2),
					prerun (3),
					arbstop (4),
					reset (5),
					poweroff (6),
					detached (7),
					callback (8),
					watchdog (9),
					watchdog-sync (10),
					offline (11),
					booting (12),
					unknown (13),
					xir (14),
					xir-sync (15),
					sir (16),
					sir-sync (17),
					redmode (18),
					redmode-sync (19),
					quiesced (20),
					quiesce-in-progress (21),
					resume-in-progress (22),
					none (23)
					}
		ACCESS		read-only
		STATUS		mandatory
		DESCRIPTION	"This value represents the current state of 
				the program running on a processor.

#define SIGBST_NONE     0       /* no state */
#define SIGBST_RUN      1       /* running */
#define SIGBST_EXIT     2       /* finished */
#define SIGBST_PRERUN   3       /* pre-exec */
#define SIGBST_ARBSTOP  4       /* transient arbstop state */
#define SIGBST_RESET    5       /* reset */
#define SIGBST_POWEROFF 6       /* no power */
#define SIGBST_DETACHED 7       /* spinning in OBP after DR DETACH */
#define SIGBST_CALLBACK 8       /* kernel calling back into OBP */
#define SIGBST_WATCHDOG 9       /* OBP running after watchdog */
#define SIGBST_WATCHDOG_SYNC    10 /* OBP sync after watchdog reset */
#define SIGBST_OFFLINE  11      /* cpu offline */
#define SIGBST_BOOTING  12      /* booting */
#define SIGBST_UNKNOWN  13      /* unknown */
#define SIGBST_XIR      14      /* OBP running after XIR */
#define SIGBST_XIR_SYNC 15      /* OBP trying sync in XIR */
#define SIGBST_SIR      16      /* OBP running after SIR */
#define SIGBST_SIR_SYNC 17      /* OBP trying sync in SIR */
#define SIGBST_REDMODE  18      /* OBP running after REDMODE */
#define SIGBST_REDMODE_SYNC     19      /* OBP trying sync in REDMODE */
#define SIGBST_QUIESCED         20      /* system quiesced */
#define SIGBST_QUIESCE_INPROGRESS 21    /* system quiesce in-progress */
#define SIGBST_RESUME_INPROGRESS 22     /* system resume in-progress */

				"
		::= { procStateGenEntry 5 }
	
	procStateGenPgmSubState OBJECT-TYPE
		SYNTAX		INTEGER {
					exit-halt (1),
					exit-environ (2),
					exit-reboot (3),
					exit-panic1 (4),
					exit-panic2 (5),
					exit-hung (6),
					exit-watch (7),
					exit-panic-reboot (8),
					exit-watchdog-reboot (9),
					exit-soft-init-reset (10),
					exit-extern-init-reset (11),
					exit-redmode-reboot (12),
					exit-obp-reset (13),
					exit-null (14),
					unknown (15)
					}
		ACCESS		read-only
		STATUS		mandatory
		DESCRIPTION	"This value represents a finer detail of the 
				current state of the program running on a 
				processor.

#define EXIT_NULL               0
#define EXIT_HALT               1
#define EXIT_ENVIRON            2
#define EXIT_REBOOT             3
#define EXIT_PANIC1             4
#define EXIT_PANIC2             5
#define EXIT_HUNG               6
#define EXIT_WATCH              7
#define EXIT_PANIC_REBOOT       8
#define EXIT_WATCHDOG_REBOOT    9
#define EXIT_SOFT_INIT_RESET    10   /* SIR */
#define EXIT_EXTERN_INIT_RESET  11   /* XIR */
#define EXIT_REDMODE_REBOOT     12   /* REDMODE */
#define EXIT_OBP_RESET          13   /* OBP RESET */

				"
		::= { procStateGenEntry 6 }
	
	procStateGenTemp OBJECT-TYPE
		SYNTAX		INTEGER
		ACCESS		read-only
		STATUS		mandatory
		DESCRIPTION	"The processor temperature."
		::= { procStateGenEntry 7 }
	
	------------------------------------------------------------------
	-- General processor communication table
	-- This table contains objects that are used for various way of 
	-- communicating between the SSP and the processor.
	-- This table is applicable to all server platforms.
	-- For each entry in ProcStateGenTable there is a corresponding
	-- entry in this table.
	------------------------------------------------------------------

	procCommGenTable OBJECT-TYPE
		SYNTAX		SEQUENCE OF ProcCommGenEntry
		ACCESS		not-accessible
		STATUS		mandatory
		DESCRIPTION	"A table of processor communication entries."
		::= { general 6 }
	
	procCommGenEntry OBJECT-TYPE
		SYNTAX		ProcCommGenEntry
		ACCESS		not-accessible
		STATUS		mandatory
		DESCRIPTION	"A processor communication table entry." 
		INDEX		{ procCommGenIndex }
		::= { procCommGenTable 1 }
	
	ProcCommGenEntry ::=
		SEQUENCE {
			procCommGenIndex 		INTEGER,
			procCommGenNum 			INTEGER,
			procCommGenSspMboxLen		INTEGER,
			procCommGenSspMboxFlag		INTEGER,
			procCommGenSspMboxCmd		INTEGER,
			procCommGenSspMboxData		OCTET STRING,
			procCommGenHostMboxLen		INTEGER,
			procCommGenHostMboxFlag		INTEGER,
			procCommGenHostMboxCmd		INTEGER,
			procCommGenHostMboxData		OCTET STRING,
			procCommGenObpMboxLen		INTEGER,
			procCommGenObpMboxFlag		INTEGER,
			procCommGenObpMboxCmd		INTEGER,
			procCommGenObpMboxData		OCTET STRING,
			procCommGenCvcInputData		OCTET STRING,
			procCommGenCvcOutputData	OCTET STRING
		}
	
	procCommGenIndex OBJECT-TYPE
		SYNTAX		INTEGER
		ACCESS		read-only
		STATUS		mandatory
		DESCRIPTION	"A unique number assigned to each CPU."
		::= { procCommGenEntry 1 }
	
	procCommGenNum OBJECT-TYPE
		SYNTAX		INTEGER
		ACCESS		read-only
		STATUS		mandatory
		DESCRIPTION	"A unique number assigned to each CPU."
		::= { procCommGenEntry 2 }
	
	procCommGenSspMboxLen OBJECT-TYPE
		SYNTAX		INTEGER
		ACCESS		read-write
		STATUS		mandatory
		DESCRIPTION	"The length of SSP-to-Host mailbox. This
				mailbox is used to instruct the host to
				perform a specific command."
		::= { procCommGenEntry 3 }
	
	procCommGenSspMboxFlag OBJECT-TYPE
		SYNTAX		INTEGER (0..64)
		ACCESS		read-write
		STATUS		mandatory
		DESCRIPTION	"The flag of SSP-to-Host mailbox."
		::= { procCommGenEntry 4 }
	
	procCommGenSspMboxCmd OBJECT-TYPE
		SYNTAX		INTEGER {
					command-success (1),
					goto-obp (2),
					goto-panic (3),
					environ (4)
					}
		ACCESS		read-write
		STATUS		mandatory
		DESCRIPTION	"The command of SSP-to-Host mailbox."
		::= { procCommGenEntry 5 }
	
	procCommGenSspMboxData OBJECT-TYPE
		SYNTAX		OCTET STRING(SIZE (64))
		ACCESS		read-write
		STATUS		mandatory
		DESCRIPTION	"The data in the SSP-to-Host mailbox."
		::= { procCommGenEntry 6 }
	
	procCommGenHostMboxLen OBJECT-TYPE
		SYNTAX		INTEGER
		ACCESS		read-write
		STATUS		mandatory
		DESCRIPTION	"The length of Host-to-SSP mailbox."
		::= { procCommGenEntry 7 }
	
	procCommGenHostMboxFlag OBJECT-TYPE
		SYNTAX		INTEGER (0..64)
		ACCESS		read-write
		STATUS		mandatory
		DESCRIPTION	"The flag of Host-to-SSP mailbox."
		::= { procCommGenEntry 8 }
	
	procCommGenHostMboxCmd OBJECT-TYPE
		SYNTAX		INTEGER {
					command-success (1),
					goto-obp (2),
					goto-panic (3),
					environ (4)
				}
		ACCESS		read-write
		STATUS		mandatory
		DESCRIPTION	"The command of Host-to-SSP mailbox."
		::= { procCommGenEntry 9 }
	
	procCommGenHostMboxData OBJECT-TYPE
		SYNTAX		OCTET STRING (SIZE (64))
		ACCESS		read-write
		STATUS		mandatory
		DESCRIPTION	"The data in the Host-to-SSP mailbox. This
				mailbox serves for communication between
				OBP running on the host and obp_helper 
				running on the SSP."
		::= { procCommGenEntry 10 }
	
	procCommGenObpMboxLen OBJECT-TYPE
		SYNTAX		INTEGER
		ACCESS		read-write
		STATUS		mandatory
		DESCRIPTION	"The length of Obp-to-SSP mailbox."
		::= { procCommGenEntry 11 }
	
	procCommGenObpMboxFlag OBJECT-TYPE
		SYNTAX		INTEGER (0..64)
		ACCESS		read-write
		STATUS		mandatory
		DESCRIPTION	"The flag of Obp-to-SSP mailbox."
		::= { procCommGenEntry 12 }
	
	procCommGenObpMboxCmd OBJECT-TYPE
		SYNTAX		INTEGER {
					release-slave-cpu (1),
					time-of-day (2),
					get-eeprom-image (3),
					put-eeprom-image (4),
					invalidate-reboot-info (5),
					move-cpu0 (6),
					get-ap-database-loc (7),
					store-boot-path-info (8)
				}
		ACCESS		read-write
		STATUS		mandatory
		DESCRIPTION	"The command of Obp-to-SSP mailbox.

#define SSPC_MULTIPROC  0x0b0b0001  	/* Request to release slave CPUs */
#define SSPC_GETTOD 0x0b0b0002  	/* Get Unix time of day from SSP */
#define SSPC_GETEEPROM  0x0b0b0003  	/* Get EEPROM image from SSP */
#define SSPC_PUTEEPROM  0x0b0b0004  	/* Put EEPROM image to SSP */
#define SSPC_UPDREBOOT  0x0b0b0005  	/* Invalidate Reboot-info in eeprom */
#define SSPC_MOVECPU0   0x0b0b0006  	/* Move Cpu0 Command */
#define SSPC_GETAPDATABASELOC   0x0b0b0007  /* Get AP database location */
#define SSPC_SAVEBOOTPATH   0x0b0b0008  /* Store boot path info */
				"
		::= { procCommGenEntry 13 }
	
	procCommGenObpMboxData OBJECT-TYPE
		SYNTAX		OCTET STRING (SIZE (64))
		ACCESS		read-write
		STATUS		mandatory
		DESCRIPTION	"The data in the Obp-to-SSP mailbox."
		::= { procCommGenEntry 14 }
	
	procCommGenCvcInputData OBJECT-TYPE
		SYNTAX		OCTET STRING (SIZE (1024))
		ACCESS		read-write
		STATUS		mandatory
		DESCRIPTION	"The input buffer to cvc."
		::= { procCommGenEntry 15 }
	
	procCommGenCvcOutputData OBJECT-TYPE
		SYNTAX		OCTET STRING (SIZE (1024))
		ACCESS		read-write
		STATUS		mandatory
		DESCRIPTION	"The output buffer to cvc."
		::= { procCommGenEntry 16 }
	
	------------------------------------------------------------------
	-- General control board table
	-- This table contains objects that are applicable to all server
	-- platforms.
	------------------------------------------------------------------
	
	cbGenTable OBJECT-TYPE
		SYNTAX		SEQUENCE OF CbGenEntry
		ACCESS		not-accessible
		STATUS		mandatory
		DESCRIPTION	"A table of general control board entries."
		::= { general 7 }
	
	cbGenEntry OBJECT-TYPE
		SYNTAX		CbGenEntry
		ACCESS		not-accessible
		STATUS		mandatory
		DESCRIPTION	"A general control board table entry."
		INDEX		{ cbGenIndex }
		::= { cbGenTable 1 }
	
	CbGenEntry ::=
		SEQUENCE {
			cbGenIndex 		INTEGER,
			cbGenNum		INTEGER,
			cbGenPower		INTEGER,
			cbGenPowerControl	INTEGER
		}
	
	cbGenIndex OBJECT-TYPE
		SYNTAX		INTEGER
		ACCESS		read-only
		STATUS		mandatory
		DESCRIPTION	"An index into this table."
		::= { cbGenEntry 1 }
	
	cbGenNum OBJECT-TYPE
		SYNTAX		INTEGER
		ACCESS		read-only
		STATUS		mandatory
		DESCRIPTION	"A unique number assigned to a control board."
		::= { cbGenEntry 2 }
	
	cbGenPower OBJECT-TYPE
		SYNTAX		INTEGER {
					on (1),
					off (2)
				}
		ACCESS		read-only
		STATUS		mandatory
		DESCRIPTION	"Power status of the control board."
		::= { cbGenEntry 3 }

	cbGenPowerControl OBJECT-TYPE
		SYNTAX		INTEGER {
					off (1)
				}
		ACCESS		read-write
		STATUS		mandatory
		DESCRIPTION	"On writing, it turns off this control board
				power supply.  By default, control board is
				powered on automatically upon insertion to the
				cabinet or when house keeping power is applied.
				On reading, it always returns off."
		::= { cbGenEntry 4 }
	
	------------------------------------------------------------------
	-- General I/O cabinet table
	-- This table contains objects that are applicable to all server
	-- platforms
	------------------------------------------------------------------
	
	ioCabGenTable OBJECT-TYPE
		SYNTAX		SEQUENCE OF IoCabGenEntry
		ACCESS		not-accessible
		STATUS		mandatory
		DESCRIPTION	"A table of general IO cabinet entries."
		::= { general 8 }
	
	ioCabGenEntry OBJECT-TYPE
		SYNTAX		IoCabGenEntry
		ACCESS		not-accessible
		STATUS		mandatory
		DESCRIPTION	"A general I/O cabinet table entry."
		INDEX		{ ioCabGenIndex }
		::= { ioCabGenTable 1 }
	
	IoCabGenEntry ::=
		SEQUENCE {
			ioCabGenIndex 		INTEGER,
			ioCabGenNum 		INTEGER,
			ioCabGenPower		INTEGER	
		}
	
	ioCabGenIndex OBJECT-TYPE
		SYNTAX		INTEGER
		ACCESS		read-only
		STATUS		mandatory
		DESCRIPTION	"An index into this table."
		::= { ioCabGenEntry 1 }

	ioCabGenNum OBJECT-TYPE
		SYNTAX		INTEGER
		ACCESS		read-only
		STATUS		mandatory
		DESCRIPTION	"A unique number assigned to an I/O Cabinet."
		::= { ioCabGenEntry 2 }

	ioCabGenPower OBJECT-TYPE
		SYNTAX		INTEGER {
					on (1),
					off (2)
					}
		ACCESS		read-write
		STATUS		mandatory
		DESCRIPTION	"A value identifying the current power state 
				of an IO cabinet and also for powering on
				and off the I/O cabinet."
		::= { ioCabGenEntry 3 }
	
	------------------------------------------------------------------
	-- General fan tray table
	-- This table contains objects that are applicable to all server
	-- platforms.
	------------------------------------------------------------------
	
	fanTrayGenTable OBJECT-TYPE
		SYNTAX		SEQUENCE OF FanTrayGenEntry
		ACCESS		not-accessible
		STATUS		mandatory
		DESCRIPTION	"A table of fan tray entries."
		::= { general 10 }
	
	fanTrayGenEntry OBJECT-TYPE
		SYNTAX		FanTrayGenEntry
		ACCESS		not-accessible
		STATUS		mandatory
		DESCRIPTION	"A fan tray table entry." 
		INDEX		{ fanTrayGenIndex }
		::= { fanTrayGenTable 1 }
	
	FanTrayGenEntry ::=
		SEQUENCE {
			fanTrayGenIndex 	INTEGER,
			fanTrayGenNum 		INTEGER,
			fanTrayGenPower		INTEGER
		}
	
	fanTrayGenIndex OBJECT-TYPE
		SYNTAX		INTEGER
		ACCESS		read-only
		STATUS		mandatory
		DESCRIPTION	"An index into this table." 
		::= { fanTrayGenEntry 1 }
	
	fanTrayGenNum OBJECT-TYPE
		SYNTAX		INTEGER
		ACCESS		read-only
		STATUS		mandatory
		DESCRIPTION	"A unique number assigned to a fan tray."
		::= { fanTrayGenEntry 2 }
	
	fanTrayGenPower OBJECT-TYPE
		SYNTAX		INTEGER {
					on (1),
					off (2)
				}
		ACCESS		read-write
		STATUS		mandatory
		DESCRIPTION	"On reading this object, it returns the
				power status of this fan tray. On writing
				it turns on/off the fan tray power."
		::= { fanTrayGenEntry 3 }
	
	------------------------------------------------------------------
	-- General fan table
	-- Each fan tray contains one or more fans.
	-- This table describe individual fan.
	-- This table contains objects that are applicable to all server
	-- platforms.
	-- Two indices are used to uniquely identify a fan: fan tray slot
	-- index and fan index within the tray.
	------------------------------------------------------------------
	
	fanGenTable OBJECT-TYPE
		SYNTAX		SEQUENCE OF FanGenEntry
		ACCESS		not-accessible
		STATUS		mandatory
		DESCRIPTION	"A table of fan entries. Each fan tray has
				certain number of fans. The number is 
				represented by ConfMaxFanPerTray."
		::= { general 11 }
	
	fanGenEntry OBJECT-TYPE
		SYNTAX		FanGenEntry
		ACCESS		not-accessible
		STATUS		mandatory
		DESCRIPTION	"A fan tray entry containing information 
				about a fan tray. Each fan entry is 
				uniquely identified by 2 fields: fan tray 
				number and fan number."
		INDEX		{ fanGenIndex }
		::= { fanGenTable 1 }
	
	FanGenEntry ::=
		SEQUENCE {
			fanGenIndex		INTEGER,
			fanGenTraySlotNum	INTEGER,
			fanGenNum		INTEGER,
			fanGenStatus		INTEGER,
			fanGenSpeed		INTEGER,
			fanGenPowerControl	INTEGER
		}
	
	fanGenIndex OBJECT-TYPE
		SYNTAX		INTEGER
		ACCESS		read-only
		STATUS		mandatory
		DESCRIPTION	"An index into this table."
		::= { fanGenEntry 1 }
	
	fanGenTraySlotNum OBJECT-TYPE
		SYNTAX		INTEGER
		ACCESS		read-only
		STATUS		mandatory
		DESCRIPTION	"A unique number assigned to a fan tray slot."
		::= { fanGenEntry 2 }
	
	fanGenNum OBJECT-TYPE
		SYNTAX		INTEGER
		ACCESS		read-only
		STATUS		mandatory
		DESCRIPTION	"A unique number assigned to a fan inside this 
				tray."
		::= { fanGenEntry 3 }
	
	fanGenStatus OBJECT-TYPE
		SYNTAX		INTEGER {
					on (1),
					off (2),
					fail (3)
				}
		ACCESS		read-write
		STATUS		mandatory
		DESCRIPTION	"On reading it returns the power status
				of this fan. On writing it allows an 
				application to turn on/off this fan. "
		::= { fanGenEntry 4 }
	
	fanGenSpeed OBJECT-TYPE
		SYNTAX		INTEGER {
					nominal (1),
					fast (2)
				}
		ACCESS		read-write
		STATUS		mandatory
		DESCRIPTION	"On reading it returns the speed of this fan 
				inside a fan tray. On writing, it allows one
				to change the speed of this fan. Nominal is
				the medium speed the fan will support, and
				fast is the highest fastest speed the fan will support."
		::= { fanGenEntry 5 }
	
	fanGenPowerControl OBJECT-TYPE
		SYNTAX		INTEGER {
					on  (1),
					off (2)
				}
		ACCESS		read-write
		STATUS		mandatory
		DESCRIPTION	"The MIB object that is used to either power
				on or off this fan.  The power status of this fan
				should be read from the fanGenStatus MIB object.
				On writing, the fan is either turned on or off."
		::= { fanGenEntry 6 }

	------------------------------------------------------------------
	-- General centerplane support board table
	-- This table contains objects that are applicable to all server
	-- platforms.
	------------------------------------------------------------------
	
	suppBrdGenTable OBJECT-TYPE
		SYNTAX		SEQUENCE OF SuppBrdGenEntry
		ACCESS		not-accessible
		STATUS		mandatory
		DESCRIPTION	"A table of support board entries."
		::= { general 13 }
	
	suppBrdGenEntry OBJECT-TYPE
		SYNTAX		SuppBrdGenEntry
		ACCESS		not-accessible
		STATUS		mandatory
		DESCRIPTION	"A support board table entry." 
		INDEX		{ suppBrdGenIndex }
		::= { suppBrdGenTable 1 }
	
	SuppBrdGenEntry ::=
		SEQUENCE {
			suppBrdGenIndex 	INTEGER,
			suppBrdGenNum 		INTEGER,
			suppBrdGenPower		INTEGER,
			suppBrdGenPowerControl	INTEGER
		}
	
	suppBrdGenIndex OBJECT-TYPE
		SYNTAX		INTEGER
		ACCESS		read-only
		STATUS		mandatory
		DESCRIPTION	"A unique number assigned to this support 
				board."
		::= { suppBrdGenEntry 1 }
	
	suppBrdGenNum OBJECT-TYPE
		SYNTAX		INTEGER
		ACCESS		read-only
		STATUS		mandatory
		DESCRIPTION	"A unique number assigned to this support 
				board."
		::= { suppBrdGenEntry 2 }
	
	suppBrdGenPower OBJECT-TYPE
		SYNTAX		INTEGER {
					on (1),
					off (2)
				}
		ACCESS		read-only
		STATUS		mandatory
		DESCRIPTION	"Power status of the support board."
		::= { suppBrdGenEntry 3 }

	suppBrdGenPowerControl OBJECT-TYPE
		SYNTAX		INTEGER {
					on (1),
					off (2)
				}
		ACCESS		read-write
		STATUS		mandatory
		DESCRIPTION	"On reading it returns the power status of this 
				support board power suuply. On writing, it 
				turns on/off this support board power supply."
		::= { suppBrdGenEntry 4 }
	
	------------------------------------------------------------------
	-- General bulk power supply table
	-- This table contains objects that are applicable to all server
	-- platforms.
	------------------------------------------------------------------
	
	bulkPowerGenTable OBJECT-TYPE
		SYNTAX		SEQUENCE OF BulkPowerGenEntry
		ACCESS		not-accessible
		STATUS		mandatory
		DESCRIPTION	"A table of bulk power supply entries."
		::= { general 14 }
	
	bulkPowerGenEntry OBJECT-TYPE
		SYNTAX		BulkPowerGenEntry
		ACCESS		not-accessible
		STATUS		mandatory
		DESCRIPTION	"A bulk power supply table entry."
		INDEX		{ bulkPowerGenIndex }
		::= { bulkPowerGenTable 1 }
	
	BulkPowerGenEntry ::=
		SEQUENCE {
			bulkPowerGenIndex 	INTEGER,
			bulkPowerGenNum 	INTEGER,
			bulkPowerGenControl	INTEGER,
			bulkPowerGenStatus	INTEGER
		}
	
	bulkPowerGenIndex OBJECT-TYPE
		SYNTAX		INTEGER
		ACCESS		read-only
		STATUS		mandatory
		DESCRIPTION	"An index into this table."
		::= { bulkPowerGenEntry 1 }
	
	bulkPowerGenNum OBJECT-TYPE
		SYNTAX		INTEGER
		ACCESS		read-only
		STATUS		mandatory
		DESCRIPTION	"A unique number assigned to this bulk power 
				supply."
		::= { bulkPowerGenEntry 2 }
	
	bulkPowerGenControl OBJECT-TYPE
		SYNTAX		INTEGER {
					off (1)
				}
		ACCESS		read-write
		STATUS		mandatory
		DESCRIPTION	"The MIB object that is used to power off this
				bulk power supply.  On writing, it powers off
				this bulk power supply."
		::= { bulkPowerGenEntry 3 }

	bulkPowerGenStatus OBJECT-TYPE
		SYNTAX		INTEGER {
					ok (1),
					fail (2)
				}
		ACCESS		read-only
		STATUS		mandatory
		DESCRIPTION	"Power status of the bulk power supply.
				A status of ok implies the unit is on and 
				supplying enough voltage/current.  A status
				of fail implies the unit is on but not
				supplying enough voltage/current or the unit is off."
		::= { bulkPowerGenEntry 4 }
	
	------------------------------------------------------------------
	-- The following describes MIB objects that are specific to 
	-- the Starfire server machine.
	------------------------------------------------------------------
	
	
	ue10000 OBJECT IDENTIFIER ::= { products 2 }
	
	------------------------------------------------------------------
	-- Starfire system board table
	-- Each system board entry contains objects that are
	-- specific to Starfire server platform only.
	------------------------------------------------------------------
	
	sysBrdStarfireTable OBJECT-TYPE
		SYNTAX		SEQUENCE OF SysBrdStarfireEntry
		ACCESS		not-accessible
		STATUS		mandatory
		DESCRIPTION	"System board table. The number host of
				entries in the table is represented by 
				Conf.ConfNumSysBrd."
		::= { ue10000 1 }
	
	sysBrdStarfireEntry OBJECT-TYPE
		SYNTAX		SysBrdStarfireEntry
		ACCESS		not-accessible
		STATUS		mandatory
		DESCRIPTION	"A system board table entry." 
		INDEX		{ sysBrdStarfireIndex }
		::= { sysBrdStarfireTable 1 }
	
	SysBrdStarfireEntry ::= SEQUENCE {
			sysBrdStarfireIndex		INTEGER,
			sysBrdStarfireNum		INTEGER,
			sysBrdStarfireCIC0Temp		INTEGER,
			sysBrdStarfireCIC1Temp		INTEGER,
			sysBrdStarfireMCTemp		INTEGER,
			sysBrdStarfireXDB2Temp		INTEGER,
			sysBrdStarfireXDB3Temp		INTEGER,
			sysBrdStarfirePROC0Temp		INTEGER,
			sysBrdStarfirePROC1Temp		INTEGER,
			sysBrdStarfirePROC2Temp		INTEGER,
			sysBrdStarfirePROC3Temp		INTEGER,
			sysBrdStarfire3p3VDCTemp	INTEGER,
			sysBrdStarfireVDCCoreTemp	INTEGER,
			sysBrdStarfire5VDCTemp		INTEGER,
			sysBrdStarfire3p3VDC		INTEGER,
			sysBrdStarfire5VDCHK		INTEGER,
			sysBrdStarfire5VDC		INTEGER,
			sysBrdStarfireVDCCore		INTEGER,
			sysBrdStarfire3p3VDCHK		INTEGER
		}
	
	sysBrdStarfireIndex OBJECT-TYPE
		SYNTAX		INTEGER
		ACCESS		read-only
		STATUS		mandatory
		DESCRIPTION	"An index into this table." 
		::= { sysBrdStarfireEntry 1 }
	
	sysBrdStarfireNum OBJECT-TYPE
		SYNTAX		INTEGER
		ACCESS		read-only
		STATUS		mandatory
		DESCRIPTION	"A unique number assigned to a system board." 
		::= { sysBrdStarfireEntry 2 }
	
	sysBrdStarfireCIC0Temp OBJECT-TYPE
		SYNTAX		INTEGER
		ACCESS		read-only
		STATUS		mandatory
		DESCRIPTION	"The temperature of the CIC0 ASIC on this 
				Starfire system board."
		::= { sysBrdStarfireEntry 3 }
	
	sysBrdStarfireCIC1Temp OBJECT-TYPE
		SYNTAX		INTEGER
		ACCESS		read-only
		STATUS		mandatory
		DESCRIPTION	"The temperature of the CIC1 ASIC on this 
				Starfire system board."
		::= { sysBrdStarfireEntry 4 }
	
	sysBrdStarfireMCTemp OBJECT-TYPE
		SYNTAX		INTEGER
		ACCESS		read-only
		STATUS		mandatory
		DESCRIPTION	"The temperature of the MC ASIC on this 
				Starfire system board."
		::= { sysBrdStarfireEntry 5 }
	
	sysBrdStarfireXDB2Temp OBJECT-TYPE
		SYNTAX		INTEGER
		ACCESS		read-only
		STATUS		mandatory
		DESCRIPTION	"The temperature of the XDB2 ASIC on this 
				Starfire system board."
		::= { sysBrdStarfireEntry 6 }
	
	sysBrdStarfireXDB3Temp OBJECT-TYPE
		SYNTAX		INTEGER
		ACCESS		read-only
		STATUS		mandatory
		DESCRIPTION	"The temperature of the XDB3 ASIC on this 
				Starfire system board."
		::= { sysBrdStarfireEntry 7 }
	
	sysBrdStarfirePROC0Temp OBJECT-TYPE
		SYNTAX		INTEGER
		ACCESS		read-only
		STATUS		mandatory
		DESCRIPTION	"The temperature of the PROC0 ASIC on this 
				Starfire system board."
		::= { sysBrdStarfireEntry 8 }
	
	sysBrdStarfirePROC1Temp OBJECT-TYPE
		SYNTAX		INTEGER
		ACCESS		read-only
		STATUS		mandatory
		DESCRIPTION	"The temperature of the PROC1 ASIC on this 
				Starfire system board."
		::= { sysBrdStarfireEntry 9 }
	
	sysBrdStarfirePROC2Temp OBJECT-TYPE
		SYNTAX		INTEGER
		ACCESS		read-only
		STATUS		mandatory
		DESCRIPTION	"The temperature of the PROC2 ASIC on this 
				Starfire system board."
		::= { sysBrdStarfireEntry 10 }
	
	sysBrdStarfirePROC3Temp OBJECT-TYPE
		SYNTAX		INTEGER
		ACCESS		read-only
		STATUS		mandatory
		DESCRIPTION	"The temperature of the PROC3 ASIC on this 
				Starfire system board."
		::= { sysBrdStarfireEntry 11 }
	
	sysBrdStarfire3p3VDCTemp OBJECT-TYPE
		SYNTAX		INTEGER
		ACCESS		read-only
		STATUS		mandatory
		DESCRIPTION	"The temperature of the PS2 3.3V DC on this 
				Starfire system board."
		::= { sysBrdStarfireEntry 12 }
	
	sysBrdStarfireVDCCoreTemp OBJECT-TYPE
		SYNTAX		INTEGER
		ACCESS		read-only
		STATUS		mandatory
		DESCRIPTION	"The temperature of the PS3 VDD Core on this 
				Starfire system board."
		::= { sysBrdStarfireEntry 13 }
	
	sysBrdStarfire5VDCTemp OBJECT-TYPE
		SYNTAX		INTEGER
		ACCESS		read-only
		STATUS		mandatory
		DESCRIPTION	"The temperature of the PS5 5V DC on this 
				Starfire system board."
		::= { sysBrdStarfireEntry 14 }
	
	sysBrdStarfire3p3VDC OBJECT-TYPE
		SYNTAX		INTEGER
		ACCESS		read-only
		STATUS		mandatory
		DESCRIPTION	"The VDD voltage reading of this Starfire 
				system board, which is equivalent to 3.3VDC."
		::= { sysBrdStarfireEntry 15 }
	
	sysBrdStarfire5VDCHK OBJECT-TYPE
		SYNTAX		INTEGER
		ACCESS		read-only
		STATUS		mandatory
		DESCRIPTION	"The 5V DC housekeeping voltage reading of 
				this Starfire system board."
		::= { sysBrdStarfireEntry 16 }
	
	sysBrdStarfire5VDC OBJECT-TYPE
		SYNTAX		INTEGER
		ACCESS		read-only
		STATUS		mandatory
		DESCRIPTION	"The 5V DC voltage reading of this Starfire 
				system board."
		::= { sysBrdStarfireEntry 17 }
	
	sysBrdStarfireVDCCore OBJECT-TYPE
		SYNTAX		INTEGER
		ACCESS		read-only
		STATUS		mandatory
		DESCRIPTION	"The VDD Core voltage reading of this Starfire 
				system board."
		::= { sysBrdStarfireEntry 18 }
	
	sysBrdStarfire3p3VDCHK OBJECT-TYPE
		SYNTAX		INTEGER
		ACCESS		read-only
		STATUS		mandatory
		DESCRIPTION	"The 3.3V DC voltage reading of this Starfire 
				system board."
		::= { sysBrdStarfireEntry 19 }
	
	
	------------------------------------------------------------------
	-- Starfire control board table
	-- Each control board entry contains objects that are specific to 
	-- Starfire server platform only.
	------------------------------------------------------------------
	
	cbStarfireTable OBJECT-TYPE
		SYNTAX		SEQUENCE OF CbStarfireEntry
		ACCESS		not-accessible
		STATUS		mandatory
		DESCRIPTION	"A table of control board entries."
		::= { ue10000 2 }
	
	cbStarfireEntry OBJECT-TYPE
		SYNTAX		CbStarfireEntry
		ACCESS		not-accessible
		STATUS		mandatory
		DESCRIPTION	"A control board table entry."
		INDEX		{ cbStarfireIndex }
		::= { cbStarfireTable 1 }
	
	CbStarfireEntry ::=
		SEQUENCE {
			cbStarfireIndex 		INTEGER,
			cbStarfireNum 			INTEGER,
			cbStarfireHostName		DisplayString,
			cbStarfire5VDCTemp		INTEGER,
			cbStarfire5VDCPerTemp		INTEGER,
			cbStarfire5VDCFanTemp		INTEGER,
			cbStarfireSen0Temp		INTEGER,
			cbStarfireSen1Temp		INTEGER,
			cbStarfireSen2Temp		INTEGER,
			cbStarfire5VDC			INTEGER,
			cbStarfire5VDCHK		INTEGER,
			cbStarfire3p3VDCHK		INTEGER,
			cbStarfire5VDCPer		INTEGER,
			cbStarfire5VDCFan		INTEGER
		}
	
	cbStarfireIndex OBJECT-TYPE
		SYNTAX		INTEGER
		ACCESS		read-only
		STATUS		mandatory
		DESCRIPTION	"An index into this table." 
		::= { cbStarfireEntry 1 }

	cbStarfireNum OBJECT-TYPE
		SYNTAX		INTEGER
		ACCESS		read-only
		STATUS		mandatory
		DESCRIPTION	"A unique number assigned to a control board."
		::= { cbStarfireEntry 2 }

	cbStarfireHostName OBJECT-TYPE
		SYNTAX		DisplayString
		ACCESS		read-only
		STATUS		mandatory
		DESCRIPTION	"Host name assigned to this control board."
		::= { cbStarfireEntry 3 }

	cbStarfire5VDCTemp OBJECT-TYPE
		SYNTAX		INTEGER
		ACCESS		read-only
		STATUS		mandatory
		DESCRIPTION	"The temperature of PS1."
		::= { cbStarfireEntry 4 }

	cbStarfire5VDCPerTemp OBJECT-TYPE
		SYNTAX		INTEGER
		ACCESS		read-only
		STATUS		mandatory
		DESCRIPTION	"The temperature of PS2. "
		::= { cbStarfireEntry 5 }

	cbStarfire5VDCFanTemp OBJECT-TYPE
		SYNTAX		INTEGER
		ACCESS		read-only
		STATUS		mandatory
		DESCRIPTION	"The temperature of PS3."
		::= { cbStarfireEntry 6 }

	cbStarfireSen0Temp OBJECT-TYPE
		SYNTAX		INTEGER
		ACCESS		read-only
		STATUS		mandatory
		DESCRIPTION	"The temperature of the 1st temperature
				sensor."
		::= { cbStarfireEntry 7 }

	cbStarfireSen1Temp OBJECT-TYPE
		SYNTAX		INTEGER
		ACCESS		read-only
		STATUS		mandatory
		DESCRIPTION	"The temperature of the 2nd temperature
				sensor."
		::= { cbStarfireEntry 8 }

	cbStarfireSen2Temp OBJECT-TYPE
		SYNTAX		INTEGER
		ACCESS		read-only
		STATUS		mandatory
		DESCRIPTION	"The temperature of the 3rd temperature
				sensor."
		::= { cbStarfireEntry 9 }

	cbStarfire5VDC OBJECT-TYPE
		SYNTAX		INTEGER
		ACCESS		read-only
		STATUS		mandatory
		DESCRIPTION	"The voltage reading of 5V DC."
		::= { cbStarfireEntry 10 }

	cbStarfire5VDCHK OBJECT-TYPE
		SYNTAX		INTEGER
		ACCESS		read-only
		STATUS		mandatory
		DESCRIPTION	"The voltage reading of housekeeping 5V DC."
		::= { cbStarfireEntry 11 }

	cbStarfire3p3VDCHK OBJECT-TYPE
		SYNTAX		INTEGER
		ACCESS		read-only
		STATUS		mandatory
		DESCRIPTION	"The voltage reading of housekeeping 3.3V DC." 
		::= { cbStarfireEntry 12 }

	cbStarfire5VDCPer OBJECT-TYPE
		SYNTAX		INTEGER
		ACCESS		read-only
		STATUS		mandatory
		DESCRIPTION	"The voltage reading of VccPer."
		::= { cbStarfireEntry 13 }

	cbStarfire5VDCFan OBJECT-TYPE
		SYNTAX		INTEGER
		ACCESS		read-only
		STATUS		mandatory
		DESCRIPTION	"The voltage reading of VccFan."
		::= { cbStarfireEntry 14 }

	
	------------------------------------------------------------------
	-- Starfire centerplane table
	-- Each centerplane entry contains objects that are specific to 
	-- Starfire server platform only.
	------------------------------------------------------------------
	
	centerplaneStarfireTable OBJECT-TYPE
		SYNTAX		SEQUENCE OF CenterplaneStarfireEntry
		ACCESS		not-accessible
		STATUS		mandatory
		DESCRIPTION	"A table of centerplane entries."
		::= { ue10000 3 }
	
	centerplaneStarfireEntry OBJECT-TYPE
		SYNTAX		CenterplaneStarfireEntry
		ACCESS		not-accessible
		STATUS		mandatory
		DESCRIPTION	"A centerplane table entry."
		INDEX		{ centerplaneStarfireIndex }
		::= { centerplaneStarfireTable 1 }
	
	CenterplaneStarfireEntry ::=
		SEQUENCE {
			centerplaneStarfireIndex	INTEGER,
			centerplaneStarfireNum		INTEGER,
			centerplaneStarfireTemp0	INTEGER,
			centerplaneStarfireTemp1	INTEGER,
			centerplaneStarfireTemp2	INTEGER,
			centerplaneStarfireTemp3	INTEGER,
			centerplaneStarfireTemp4	INTEGER,
			centerplaneStarfireTemp5	INTEGER,
			centerplaneStarfireTemp6	INTEGER,
			centerplaneStarfireTemp7	INTEGER,
			centerplaneStarfireTemp8	INTEGER,
			centerplaneStarfireTemp9	INTEGER
		}
	
	centerplaneStarfireIndex OBJECT-TYPE
		SYNTAX		INTEGER
		ACCESS		read-only
		STATUS		mandatory
		DESCRIPTION	"An index into this table."
		::= { centerplaneStarfireEntry 1 }
	
	centerplaneStarfireNum OBJECT-TYPE
		SYNTAX		INTEGER
		ACCESS		read-only
		STATUS		mandatory
		DESCRIPTION	"A unique number assigned to this centerplane."
		::= { centerplaneStarfireEntry 2 }
	
	centerplaneStarfireTemp0 OBJECT-TYPE
		SYNTAX		INTEGER
		ACCESS		read-only
		STATUS		mandatory
		DESCRIPTION	"The 1st temp point of this Starfire centerplane."
		::= { centerplaneStarfireEntry 3 }
	
	centerplaneStarfireTemp1 OBJECT-TYPE
		SYNTAX		INTEGER
		ACCESS		read-only
		STATUS		mandatory
		DESCRIPTION	"The 2nd temp point of this Starfire centerplane."
		::= { centerplaneStarfireEntry 4 }
	
	centerplaneStarfireTemp2 OBJECT-TYPE
		SYNTAX		INTEGER
		ACCESS		read-only
		STATUS		mandatory
		DESCRIPTION	"The 3rd temp point of this Starfire centerplane."
		::= { centerplaneStarfireEntry 5 }
	
	centerplaneStarfireTemp3 OBJECT-TYPE
		SYNTAX		INTEGER
		ACCESS		read-only
		STATUS		mandatory
		DESCRIPTION	"The 4th temp point of this Starfire centerplane."
		::= { centerplaneStarfireEntry 6 }
	
	centerplaneStarfireTemp4 OBJECT-TYPE
		SYNTAX		INTEGER
		ACCESS		read-only
		STATUS		mandatory
		DESCRIPTION	"The 5th temp point of this Starfire centerplane."
		::= { centerplaneStarfireEntry 7 }
	
	centerplaneStarfireTemp5 OBJECT-TYPE
		SYNTAX		INTEGER
		ACCESS		read-only
		STATUS		mandatory
		DESCRIPTION	"The 6th temp point of this Starfire centerplane."
		::= { centerplaneStarfireEntry 8 }
	
	centerplaneStarfireTemp6 OBJECT-TYPE
		SYNTAX		INTEGER
		ACCESS		read-only
		STATUS		mandatory
		DESCRIPTION	"The 7th temp point of this Starfire centerplane."
		::= { centerplaneStarfireEntry 9 }
	
	centerplaneStarfireTemp7 OBJECT-TYPE
		SYNTAX		INTEGER
		ACCESS		read-only
		STATUS		mandatory
		DESCRIPTION	"The 8th temp point of this Starfire centerplane."
		::= { centerplaneStarfireEntry 10 }
	
	centerplaneStarfireTemp8 OBJECT-TYPE
		SYNTAX		INTEGER
		ACCESS		read-only
		STATUS		mandatory
		DESCRIPTION	"The 9th temp point of this Starfire centerplane."
		::= { centerplaneStarfireEntry 11 }
	
	centerplaneStarfireTemp9 OBJECT-TYPE
		SYNTAX		INTEGER
		ACCESS		read-only
		STATUS		mandatory
		DESCRIPTION	"The 10th temp point of this Starfire centerplane."
		::= { centerplaneStarfireEntry 12 }
	
	
	------------------------------------------------------------------
	-- Starfire support board table
	-- Each support board entry contains objects that are specific to 
	-- Starfire server platform only.
	------------------------------------------------------------------
	
	suppBrdStarfireTable OBJECT-TYPE
		SYNTAX		SEQUENCE OF SuppBrdStarfireEntry
		ACCESS		not-accessible
		STATUS		mandatory
		DESCRIPTION	"A table of support board entries."
		::= { ue10000 4 }
	
	suppBrdStarfireEntry OBJECT-TYPE
		SYNTAX		SuppBrdStarfireEntry
		ACCESS		not-accessible
		STATUS		mandatory
		DESCRIPTION	"A support board table entry."
		INDEX		{ suppBrdStarfireIndex }
		::= { suppBrdStarfireTable 1 }
	
	SuppBrdStarfireEntry ::=
		SEQUENCE {
			suppBrdStarfireIndex	INTEGER,
			suppBrdStarfireNum	INTEGER,
			suppBrdStarfire3p3VDC1Temp	INTEGER,
			suppBrdStarfire3p3VDC2Temp	INTEGER,
			suppBrdStarfire5VDCHK	INTEGER,
			suppBrdStarfire3p3VDCHK	INTEGER,
			suppBrdStarfire3p3VDC	INTEGER
		}
	
	suppBrdStarfireIndex OBJECT-TYPE
		SYNTAX		INTEGER
		ACCESS		read-only
		STATUS		mandatory
		DESCRIPTION	"An index into this table."
		::= { suppBrdStarfireEntry 1 }
	
	suppBrdStarfireNum OBJECT-TYPE
		SYNTAX		INTEGER
		ACCESS		read-only
		STATUS		mandatory
		DESCRIPTION	"A unique number assigned to this support board."
		::= { suppBrdStarfireEntry 2 }
	
	suppBrdStarfire3p3VDC1Temp OBJECT-TYPE
		SYNTAX		INTEGER
		ACCESS		read-only
		STATUS		mandatory
		DESCRIPTION	"The PS1 temp point of this Starfire support board."
		::= { suppBrdStarfireEntry 3 }
	
	suppBrdStarfire3p3VDC2Temp OBJECT-TYPE
		SYNTAX		INTEGER
		ACCESS		read-only
		STATUS		mandatory
		DESCRIPTION	"The PS2 temp point of this Starfire support board."
		::= { suppBrdStarfireEntry 4 }
	
	suppBrdStarfire5VDCHK OBJECT-TYPE
		SYNTAX		INTEGER
		ACCESS		read-only
		STATUS		mandatory
		DESCRIPTION	"The 5V DC voltage in this Starfire 
				support board."
		::= { suppBrdStarfireEntry 5 }
	
	suppBrdStarfire3p3VDCHK OBJECT-TYPE
		SYNTAX		INTEGER
		ACCESS		read-only
		STATUS		mandatory
		DESCRIPTION	"The 3.3V DC housekeeping voltage in this 
				Starfire support board."
		::= { suppBrdStarfireEntry 6 }

	suppBrdStarfire3p3VDC	OBJECT-TYPE
		SYNTAX		INTEGER
		ACCESS		read-only
		STATUS		mandatory
		DESCRIPTION	"The CP 3.3V DC housekeeping voltage in this 
				Starfire support board."
		::= { suppBrdStarfireEntry 7 }


	------------------------------------------------------------------
	-- The following describes MIB objects that are intended for the 
	-- SSP application management.
	------------------------------------------------------------------
	
	ssp OBJECT IDENTIFIER ::= { products 3 }
	
	------------------------------------------------------------------
	-- SSP platform-type application
	------------------------------------------------------------------
	
	sspPlatformApp OBJECT IDENTIFIER ::= { ssp 1 }

	sspPlatformAppEddControl OBJECT-TYPE
		SYNTAX 		INTEGER {
					start (1),
					stop (2),
					reconfig (3),
					unknown (4)
				}
		ACCESS		read-write
		STATUS		mandatory
		DESCRIPTION	"The object identifies the action intended 
				for the EDD. Changing this object will cause 
				the agent to send a eddControl trap.
				Reading this object returns the last action
				requested for the EDD. The SNMP agent does
				not maintain persistent information for this
				object. It will be initialized to unknown
				value." 
		::= { sspPlatformApp 1 }

	sspPlatformAppEddState OBJECT-TYPE
		SYNTAX		INTEGER {
					started-monitoring (1),
					stopped-monitoring (2),
					unknown (3)
				}
		ACCESS		read-write
		STATUS		mandatory
		DESCRIPTION	"The object identifies the current state
				of the Event Detector Daemon. Changing this
				object will cause the agent to send a
				eddState trap. Reading this object returns
				the last changed state of the EDD. The SNMP
				agent does not maintain persistent
				information for this object. It will be
				initialized to unknown."
		::= { sspPlatformApp 2 }

	
	-- well-known traps

	
	domainChange TRAP-TYPE
		ENTERPRISE	sun
		VARIABLES	{ platformName,
				confNumDomain,
				domainName,
				domainNumSysBrd,
				domainSysBrdList,
				domainOSVersion,
				platformType,
				platformName }
		DESCRIPTION	"This trap indicates the domain table has
				changed. The first two variables (platformName
				and confNumDomain) will always have an instance
				value of 0.  The remaining variables
				(domainName, domainNumSysBrd, domainSysBrdList,
				domainOSVersion, platformType, platformName )
				will have an instance value of 0 to
				confNumDomain - 1.  An instance of these
				remaining variables describe a domain.
				All variables for this trap are mandatory."
		::= 0

	eddControl TRAP-TYPE
		ENTERPRISE	sun
		VARIABLES 	{ platformName,
				  sspPlatformAppEddControl }
		DESCRIPTION	"This trap indicates the action EDD should
				be taken. All variables for this trap are
				mandatory." 
		::= 1

	eddState TRAP-TYPE
		ENTERPRISE	sun
		VARIABLES 	{ platformName,
				  sspPlatformAppEddState }
		DESCRIPTION	"This trap indicates the new state of the
				EDD. All variables for this trap are
				mandatory."
		::= 2

	sysBrdTempNorm TRAP-TYPE
		ENTERPRISE	sun
		VARIABLES 	{ platformName,
				  sysBrdStarfireNum,
				  sysBrdStarfireCIC0Temp,
				  sysBrdStarfireCIC1Temp,
				  sysBrdStarfireMCTemp,
				  sysBrdStarfireXDB2Temp,
				  sysBrdStarfireXDB3Temp,
				  sysBrdStarfirePROC0Temp,
				  sysBrdStarfirePROC1Temp,
				  sysBrdStarfirePROC2Temp,
				  sysBrdStarfirePROC3Temp,
				  sysBrdStarfire3p3VDCTemp,
				  sysBrdStarfireVDCCoreTemp,
				  sysBrdStarfire5VDCTemp }
		DESCRIPTION	"This trap indicates a System Board transition
				from over temperature reading to normal. The
				platform name and board number will always be
				provided with this trap. Whereas, only those
				temperature readings that crossed the
				threshold will be included."
		::= 3

	sysBrdTempHigh TRAP-TYPE
		ENTERPRISE	sun
		VARIABLES 	{ platformName,
				  sysBrdStarfireNum,
				  sysBrdStarfireCIC0Temp,
				  sysBrdStarfireCIC1Temp,
				  sysBrdStarfireMCTemp,
				  sysBrdStarfireXDB2Temp,
				  sysBrdStarfireXDB3Temp,
				  sysBrdStarfirePROC0Temp,
				  sysBrdStarfirePROC1Temp,
				  sysBrdStarfirePROC2Temp,
				  sysBrdStarfirePROC3Temp,
				  sysBrdStarfire3p3VDCTemp,
				  sysBrdStarfireVDCCoreTemp,
				  sysBrdStarfire5VDCTemp }
		DESCRIPTION	"This trap indicates a System Board high
				temperature reading. The platform name and
				board number variables will always be
				provided with this trap. Whereas, only those
				temperature readings that crossed the
				threshold will be included."
		::= 4

	sysBrdTempWarn TRAP-TYPE
		ENTERPRISE	sun
		VARIABLES 	{ platformName,
				  sysBrdStarfireNum,
				  sysBrdStarfireCIC0Temp,
				  sysBrdStarfireCIC1Temp,
				  sysBrdStarfireMCTemp,
				  sysBrdStarfireXDB2Temp,
				  sysBrdStarfireXDB3Temp,
				  sysBrdStarfirePROC0Temp,
				  sysBrdStarfirePROC1Temp,
				  sysBrdStarfirePROC2Temp,
				  sysBrdStarfirePROC3Temp,
				  sysBrdStarfire3p3VDCTemp,
				  sysBrdStarfireVDCCoreTemp,
				  sysBrdStarfire5VDCTemp }
		DESCRIPTION	"This trap indicates a System Board warning
				temperature reading. The platform name and
				board number variables will always be
				provided with this trap. Whereas, only those
				temperature readings that crossed the
				threshold will be included."
		::= 5

	sysBrdTempMax TRAP-TYPE
		ENTERPRISE	sun
		VARIABLES 	{ platformName,
				  sysBrdStarfireNum,
				  sysBrdStarfireCIC0Temp,
				  sysBrdStarfireCIC1Temp,
				  sysBrdStarfireMCTemp,
				  sysBrdStarfireXDB2Temp,
				  sysBrdStarfireXDB3Temp,
				  sysBrdStarfirePROC0Temp,
				  sysBrdStarfirePROC1Temp,
				  sysBrdStarfirePROC2Temp,
				  sysBrdStarfirePROC3Temp,
				  sysBrdStarfire3p3VDCTemp,
				  sysBrdStarfireVDCCoreTemp,
				  sysBrdStarfire5VDCTemp }
		DESCRIPTION	"This trap indicates a System Board max
				temperature reading. The platform name and
				board number variables will always be
				provided with this trap. Whereas, only those
				temperature readings that crossed the
				threshold will be included."
		::= 6

	sysBrdTemp911 TRAP-TYPE
		ENTERPRISE	sun
		VARIABLES 	{ platformName,
				  sysBrdStarfireNum,
				  sysBrdStarfireCIC0Temp,
				  sysBrdStarfireCIC1Temp,
				  sysBrdStarfireMCTemp,
				  sysBrdStarfireXDB2Temp,
				  sysBrdStarfireXDB3Temp,
				  sysBrdStarfirePROC0Temp,
				  sysBrdStarfirePROC1Temp,
				  sysBrdStarfirePROC2Temp,
				  sysBrdStarfirePROC3Temp,
				  sysBrdStarfire3p3VDCTemp,
				  sysBrdStarfireVDCCoreTemp,
				  sysBrdStarfire5VDCTemp }
		DESCRIPTION	"This trap indicates a System Board 911
				temperature reading. The platform name and
				board number variables will always be
				provided with this trap. Whereas, only those
				temperature readings that crossed the
				threshold will be included."
		::= 7

	sysBrdTempBad TRAP-TYPE
		ENTERPRISE	sun
		VARIABLES 	{ platformName,
				  sysBrdStarfireNum,
				  sysBrdStarfireCIC0Temp,
				  sysBrdStarfireCIC1Temp,
				  sysBrdStarfireMCTemp,
				  sysBrdStarfireXDB2Temp,
				  sysBrdStarfireXDB3Temp,
				  sysBrdStarfirePROC0Temp,
				  sysBrdStarfirePROC1Temp,
				  sysBrdStarfirePROC2Temp,
				  sysBrdStarfirePROC3Temp,
				  sysBrdStarfire3p3VDCTemp,
				  sysBrdStarfireVDCCoreTemp,
				  sysBrdStarfire5VDCTemp }
		DESCRIPTION	"This trap indicates a System Board bad
				temperature reading. This means that at least
				half the temperature sensors on the board
				report invalid temperature readings. For
				ASIC temperature errors, it is possible that
				the ASICs are not thermally calibrated. The
				platform name and board number variables
				will always be provided with this trap.
				Whereas, only those temperature readings
				that crossed the threshold will be included."
		::= 8

	sysBrdTempChange TRAP-TYPE
		ENTERPRISE	sun
		VARIABLES 	{ platformName,
				  sysBrdStarfireNum,
				  sysBrdStarfireCIC0Temp,
				  sysBrdStarfireCIC1Temp,
				  sysBrdStarfireMCTemp,
				  sysBrdStarfireXDB2Temp,
				  sysBrdStarfireXDB3Temp,
				  sysBrdStarfirePROC0Temp,
				  sysBrdStarfirePROC1Temp,
				  sysBrdStarfirePROC2Temp,
				  sysBrdStarfirePROC3Temp,
				  sysBrdStarfire3p3VDCTemp,
				  sysBrdStarfireVDCCoreTemp,
				  sysBrdStarfire5VDCTemp }
		DESCRIPTION	"This trap indicates that a System Board
				temperature reading has changed within a
				specified delta. The platform name
				and board number variables will always be
				provided with this trap.  Whereas, only
				those temperature readings that changed
				will be included."
		::= 9

	cbTempNorm TRAP-TYPE
		ENTERPRISE	sun
		VARIABLES 	{ platformName,
				  cbStarfireNum,
				  cbStarfire5VDCTemp,
				  cbStarfire5VDCPerTemp,
				  cbStarfire5VDCFanTemp,
				  cbStarfireSen0Temp,
				  cbStarfireSen1Temp,
				  cbStarfireSen2Temp }
		DESCRIPTION	"This trap indicates a Control Board
				transition to normal temperature reading.
				The platform name and board number variables
				will always be provided with this trap.
				Whereas, only those temperature readings
				that crossed the threshold will be included."
		::= 10

	cbTempHigh TRAP-TYPE
		ENTERPRISE	sun
		VARIABLES 	{ platformName,
				  cbStarfireNum,
				  cbStarfire5VDCTemp,
				  cbStarfire5VDCPerTemp,
				  cbStarfire5VDCFanTemp,
				  cbStarfireSen0Temp,
				  cbStarfireSen1Temp,
				  cbStarfireSen2Temp }
		DESCRIPTION	"This trap indicates a Control Board high
				temperature reading. The platform name and
				board number variables will always be
				provided with this trap. Whereas, only those
				temperature readings that crossed the
				threshold will be included."
		::= 11

	cbTempWarn TRAP-TYPE
		ENTERPRISE	sun
		VARIABLES 	{ platformName,
				  cbStarfireNum,
				  cbStarfire5VDCTemp,
				  cbStarfire5VDCPerTemp,
				  cbStarfire5VDCFanTemp,
				  cbStarfireSen0Temp,
				  cbStarfireSen1Temp,
				  cbStarfireSen2Temp }
		DESCRIPTION	"This trap indicates a Control Board warning
				temperature reading. The platform name and
				board number variables will always be
				provided with this trap. Whereas, only those
				temperature readings that crossed the
				threshold will be included."
		::= 12

	cbTempMax TRAP-TYPE
		ENTERPRISE	sun
		VARIABLES 	{ platformName,
				  cbStarfireNum,
				  cbStarfire5VDCTemp,
				  cbStarfire5VDCPerTemp,
				  cbStarfire5VDCFanTemp,
				  cbStarfireSen0Temp,
				  cbStarfireSen1Temp,
				  cbStarfireSen2Temp }
		DESCRIPTION	"This trap indicates a Control Board max
				temperature reading. The platform name and
				board number variables will always be
				provided with this trap. Whereas, only those
				temperature readings that crossed the
				threshold will be included."
		::= 13

	cbTemp911 TRAP-TYPE
		ENTERPRISE	sun
		VARIABLES 	{ platformName,
				  cbStarfireNum,
				  cbStarfire5VDCTemp,
				  cbStarfire5VDCPerTemp,
				  cbStarfire5VDCFanTemp,
				  cbStarfireSen0Temp,
				  cbStarfireSen1Temp,
				  cbStarfireSen2Temp }
		DESCRIPTION	"This trap indicates a Control Board 911
				temperature reading. The platform name and
				board number variables will always be
				provided with this trap. Whereas, only those
				temperature readings that crossed the
				threshold will be included."
		::= 14

	cbTempBad TRAP-TYPE
		ENTERPRISE	sun
		VARIABLES 	{ platformName,
				  cbStarfireNum,
				  cbStarfire5VDCTemp,
				  cbStarfire5VDCPerTemp,
				  cbStarfire5VDCFanTemp,
				  cbStarfireSen0Temp,
				  cbStarfireSen1Temp,
				  cbStarfireSen2Temp }
		DESCRIPTION	"This trap indicates a Control Board bad
				temperature reading. This means that at least
				half the temperature sensors on the board
				report invalid temperature readings. For
				ASIC temperature errors, it is possible that
				the ASICs are not thermally calibrated. The
				platform name and board number variables will
				always be provided with this trap. Whereas,
				only those temperature readings that crossed
				the threshold will be included."
		::= 15

	cbTempChange TRAP-TYPE
		ENTERPRISE	sun
		VARIABLES 	{ platformName,
				  cbStarfireNum,
				  cbStarfire5VDCTemp,
				  cbStarfire5VDCPerTemp,
				  cbStarfire5VDCFanTemp,
				  cbStarfireSen0Temp,
				  cbStarfireSen1Temp,
				  cbStarfireSen2Temp }
		DESCRIPTION	"This trap indicates that a Control Board
				temperature reading has changed within a
				specified delta. The platform name and board
				number variables will always be provided
				with this trap. Whereas, only those
				temperature readings that crossed
				the threshold will be included."
		::= 16

	centerplaneTempNorm TRAP-TYPE
		ENTERPRISE	sun
		VARIABLES 	{ platformName,
				  centerplaneStarfireNum,
				  centerplaneStarfireTemp0,
				  centerplaneStarfireTemp1,
				  centerplaneStarfireTemp2,
				  centerplaneStarfireTemp3,
				  centerplaneStarfireTemp4,
				  centerplaneStarfireTemp5,
				  centerplaneStarfireTemp6,
				  centerplaneStarfireTemp7,
				  centerplaneStarfireTemp8,
				  centerplaneStarfireTemp9
				}
		DESCRIPTION	"This trap indicates a Centerplane
				transition to normal temperature reading.
				The platform name and board number variables
				will always be provided with this trap.
				Whereas, only those temperature readings
				that crossed the threshold will be included."
		::= 17

	centerplaneTempHigh TRAP-TYPE
		ENTERPRISE	sun
		VARIABLES 	{ platformName,
				  centerplaneStarfireNum,
				  centerplaneStarfireTemp0,
				  centerplaneStarfireTemp1,
				  centerplaneStarfireTemp2,
				  centerplaneStarfireTemp3,
				  centerplaneStarfireTemp4,
				  centerplaneStarfireTemp5,
				  centerplaneStarfireTemp6,
				  centerplaneStarfireTemp7,
				  centerplaneStarfireTemp8,
				  centerplaneStarfireTemp9
				}
		DESCRIPTION	"This trap indicates a Centerplane high
				temperature reading. The platform name and
				board number variables will always be
				provided with this trap. Whereas, only those
				temperature readings that crossed the
				threshold will be included."
		::= 18

	centerplaneTempWarn TRAP-TYPE
		ENTERPRISE	sun
		VARIABLES 	{ platformName,
				  centerplaneStarfireNum,
				  centerplaneStarfireTemp0,
				  centerplaneStarfireTemp1,
				  centerplaneStarfireTemp2,
				  centerplaneStarfireTemp3,
				  centerplaneStarfireTemp4,
				  centerplaneStarfireTemp5,
				  centerplaneStarfireTemp6,
				  centerplaneStarfireTemp7,
				  centerplaneStarfireTemp8,
				  centerplaneStarfireTemp9
				}
		DESCRIPTION	"This trap indicates a Centerplane
				warning temperature reading. The platform name
				and board number variables will always be
				provided with this trap. Whereas, only those
				temperature readings that crossed the
				threshold will be included."
		::= 19

	centerplaneTempMax TRAP-TYPE
		ENTERPRISE	sun
		VARIABLES 	{ platformName,
				  centerplaneStarfireNum,
				  centerplaneStarfireTemp0,
				  centerplaneStarfireTemp1,
				  centerplaneStarfireTemp2,
				  centerplaneStarfireTemp3,
				  centerplaneStarfireTemp4,
				  centerplaneStarfireTemp5,
				  centerplaneStarfireTemp6,
				  centerplaneStarfireTemp7,
				  centerplaneStarfireTemp8,
				  centerplaneStarfireTemp9
				}
		DESCRIPTION	"This trap indicates a Centerplane max
				temperature reading. The platform name and
				board number variables will always be
				provided with this trap. Whereas, only those
				temperature readings that crossed the
				threshold will be included."
		::= 20

	centerplaneTemp911 TRAP-TYPE
		ENTERPRISE	sun
		VARIABLES 	{ platformName,
				  centerplaneStarfireNum,
				  centerplaneStarfireTemp0,
				  centerplaneStarfireTemp1,
				  centerplaneStarfireTemp2,
				  centerplaneStarfireTemp3,
				  centerplaneStarfireTemp4,
				  centerplaneStarfireTemp5,
				  centerplaneStarfireTemp6,
				  centerplaneStarfireTemp7,
				  centerplaneStarfireTemp8,
				  centerplaneStarfireTemp9
				}
		DESCRIPTION	"This trap indicates a Centerplane 911
				temperature reading. The platform name and
				board number variables will always be
				provided with this trap. Whereas, only those
				temperature readings that crossed the
				threshold will be included."
		::= 21

	centerplaneTempBad TRAP-TYPE
		ENTERPRISE	sun
		VARIABLES 	{ platformName,
				  centerplaneStarfireNum,
				  centerplaneStarfireTemp0,
				  centerplaneStarfireTemp1,
				  centerplaneStarfireTemp2,
				  centerplaneStarfireTemp3,
				  centerplaneStarfireTemp4,
				  centerplaneStarfireTemp5,
				  centerplaneStarfireTemp6,
				  centerplaneStarfireTemp7,
				  centerplaneStarfireTemp8,
				  centerplaneStarfireTemp9
				}
		DESCRIPTION	"This trap indicates a Centerplane bad
				temperature reading. This means that at least
				half the temperature sensors on the board
				report invalid temperature readings. For
				ASIC temperature errors, it is possible that
				the ASICs are not thermally calibrated. The
				platform name and board number variables will
				always be provided with this trap. Whereas,
				only those temperature readings that crossed
				the threshold will be included."
		::= 22

	centerplaneTempChange TRAP-TYPE
		ENTERPRISE	sun
		VARIABLES 	{ platformName,
				  centerplaneStarfireNum,
				  centerplaneStarfireTemp0,
				  centerplaneStarfireTemp1,
				  centerplaneStarfireTemp2,
				  centerplaneStarfireTemp3,
				  centerplaneStarfireTemp4,
				  centerplaneStarfireTemp5,
				  centerplaneStarfireTemp6,
				  centerplaneStarfireTemp7,
				  centerplaneStarfireTemp8,
				  centerplaneStarfireTemp9
				}
		DESCRIPTION	"This trap indicates that a Centerplane
				temperature reading has changed within a
				specified delta. The platform name and
				board number variables will always be
				provided with this trap. Whereas,
				only those temperature readings that crossed
				the threshold will be included."
		::= 23

	cbeConnected TRAP-TYPE
		ENTERPRISE	sun
		VARIABLES	{ platformName,
				  platformMasterConBrd,
				  platformSysClkConBrd
				}
		DESCRIPTION	"This trap indicates that the control board
				server (cbs) is connected to the control 
				board executive (cbe) and is ready for
				control board operation. All variables are
				mandatory for this trap."
		::= 24

	cbeDisconnected TRAP-TYPE
		ENTERPRISE	sun
		VARIABLES	{ platformName,
				  platformMasterConBrd,
				  platformSysClkConBrd
				}
		DESCRIPTION	"This trap indicates that the control board
				server (cbs) has lost connection with the
				control board executive (cbe). All variables
				are mandatory for this trap."
		::= 25

	suppBrdTempNorm TRAP-TYPE
		ENTERPRISE	sun
		VARIABLES	{ platformName,
				  suppBrdStarfireNum,
				  suppBrdStarfire3p3VDC1Temp,
				  suppBrdStarfire3p3VDC2Temp
				}
		DESCRIPTION	"This trap indicates a Centerplane Support Board
				transition from over temperature reading to
				normal. The platform name and
				board number variables will always be
				provided with this trap. Whereas, only those
				temperature readings that crossed the
				threshold will be included."
		::= 26

	suppBrdTempHigh TRAP-TYPE
		ENTERPRISE	sun
		VARIABLES	{ platformName,
				  suppBrdStarfireNum,
				  suppBrdStarfire3p3VDC1Temp,
				  suppBrdStarfire3p3VDC2Temp
				}
		DESCRIPTION	"This trap indicates a Centerplane Support Board
				high temperature reading. The platform name and
				board number variables will always be
				provided with this trap. Whereas, only those
				temperature readings that crossed the
				threshold will be included."
		::= 27

	suppBrdTempWarn TRAP-TYPE
		ENTERPRISE	sun
		VARIABLES	{ platformName,
				  suppBrdStarfireNum,
				  suppBrdStarfire3p3VDC1Temp,
				  suppBrdStarfire3p3VDC2Temp
				}
		DESCRIPTION	"This trap indicates a Centerplane Support Board
				warning temperature reading. The platform name
				and board number variables will always be
				provided with this trap. Whereas, only those
				temperature readings that crossed the
				threshold will be included."
		::= 28

	suppBrdTempMax TRAP-TYPE
		ENTERPRISE	sun
		VARIABLES	{ platformName,
				  suppBrdStarfireNum,
				  suppBrdStarfire3p3VDC1Temp,
				  suppBrdStarfire3p3VDC2Temp
				}
		DESCRIPTION	"This trap indicates a Centerplane Support Board
				max temperature reading. The platform name and
				board number variables will always be
				provided with this trap. Whereas, only those
				temperature readings that crossed the
				threshold will be included."
		::= 29

	suppBrdTemp911 TRAP-TYPE
		ENTERPRISE	sun
		VARIABLES	{ platformName,
				  suppBrdStarfireNum,
				  suppBrdStarfire3p3VDC1Temp,
				  suppBrdStarfire3p3VDC2Temp
				}
		DESCRIPTION	"This trap indicates a Centerplane Support Board
				911 temperature reading. The platform name and
				board number variables will always be
				provided with this trap. Whereas, only those
				temperature readings that crossed the
				threshold will be included."
		::= 30

	suppBrdTempBad TRAP-TYPE
		ENTERPRISE	sun
		VARIABLES	{ platformName,
				  suppBrdStarfireNum,
				  suppBrdStarfire3p3VDC1Temp,
				  suppBrdStarfire3p3VDC2Temp
				}
		DESCRIPTION	"This trap indicates a Centerplane Support Board
				bad temperature reading. This means that half
				the temperature sensors on the board do not
				report valid temperature readings. For
				ASIC temperature errors, it is possible that
				the ASICs are not thermally calibrated. 
				The platform name and board number variables
				will always be provided with this trap.
				Whereas, only those temperature readings
				that crossed the threshold will be included."
		::= 31

	suppBrdTempChange TRAP-TYPE
		ENTERPRISE	sun
		VARIABLES	{ platformName,
				  suppBrdStarfireNum,
				  suppBrdStarfire3p3VDC1Temp,
				  suppBrdStarfire3p3VDC2Temp
				}
		DESCRIPTION	"This trap indicates that a Centerplane
				Support Board temperature reading has changed
				within a specified delta. The platform
				name and board number variables will always be
				provided with this trap. Whereas, only those
				temperature readings that crossed the
				threshold will be included."
		::= 32

	sysBrdVoltNorm TRAP-TYPE
		ENTERPRISE	sun
		VARIABLES 	{ platformName,
				  sysBrdStarfireNum,
				  sysBrdStarfire3p3VDC,
				  sysBrdStarfire5VDCHK,
				  sysBrdStarfire5VDC,
				  sysBrdStarfireVDCCore,
				  sysBrdStarfire3p3VDCHK
				}
		DESCRIPTION	"This trap indicates a System Board transition
				from low or high power reading to normal. The
				platform name and board number variables will
				always be provided with this trap. Whereas,
				only those voltage readings that crossed the
				threshold will be included."
		::= 33

	sysBrdVoltMax TRAP-TYPE
		ENTERPRISE	sun
		VARIABLES 	{ platformName,
				  sysBrdStarfireNum,
				  sysBrdStarfire3p3VDC,
				  sysBrdStarfire5VDCHK,
				  sysBrdStarfire5VDC,
				  sysBrdStarfireVDCCore,
				  sysBrdStarfire3p3VDCHK
				}
		DESCRIPTION	"This trap indicates a System Board max
				voltage reading. The platform name and
				board number variables will always be
				provided with this trap. Whereas, only those
				voltage readings that crossed the
				threshold will be included."
		::= 34

	sysBrdVoltMin TRAP-TYPE
		ENTERPRISE	sun
		VARIABLES 	{ platformName,
				  sysBrdStarfireNum,
				  sysBrdStarfire3p3VDC,
				  sysBrdStarfire5VDCHK,
				  sysBrdStarfire5VDC,
				  sysBrdStarfireVDCCore,
				  sysBrdStarfire3p3VDCHK
				}
		DESCRIPTION	"This trap indicates a System Board min
				voltage reading. The platform name and
				board number variables will always be
				provided with this trap. Whereas, only those
				voltage readings that crossed the
				threshold will be included."
		::= 35

	sysBrdVoltBad TRAP-TYPE
		ENTERPRISE	sun
		VARIABLES 	{ platformName,
				  sysBrdStarfireNum,
				  sysBrdStarfire3p3VDC,
				  sysBrdStarfire5VDCHK,
				  sysBrdStarfire5VDC,
				  sysBrdStarfireVDCCore,
				  sysBrdStarfire3p3VDCHK
				}
		DESCRIPTION	"This trap indicates a System Board bad
				voltage reading. This means that at least
				half the voltage sensors on the board
				report invalid voltage readings. The platform
				name and board number variables will always be
				provided with this trap. Whereas, only those
				voltage readings that crossed the
				threshold will be included."
		::= 36

	sysBrdVoltChange TRAP-TYPE
		ENTERPRISE	sun
		VARIABLES 	{ platformName,
				  sysBrdStarfireNum,
				  sysBrdStarfire3p3VDC,
				  sysBrdStarfire5VDCHK,
				  sysBrdStarfire5VDC,
				  sysBrdStarfireVDCCore,
				  sysBrdStarfire3p3VDCHK
				}
		DESCRIPTION	"This trap indicates a System Board
				voltage reading has changed within a
				specified delta. The platform name and
				board number variables will always be
				provided with this trap. Whereas, only those
				voltage readings that crossed the
				threshold will be included."
		::= 37

	cbVoltNorm TRAP-TYPE
		ENTERPRISE	sun
		VARIABLES 	{ platformName,
				  cbStarfireNum,
				  cbStarfire5VDC,
				  cbStarfire5VDCHK,
				  cbStarfire3p3VDCHK,
				  cbStarfire5VDCPer,
				  cbStarfire5VDCFan
				}
		DESCRIPTION	"This trap indicates a Control Board
				transition to normal voltage reading. The
				platform name and board number variables
				will always be provided with this trap.
				Whereas, only those voltage readings that
				crossed the threshold will be included."
		::= 38

	cbVoltMax TRAP-TYPE
		ENTERPRISE	sun
		VARIABLES 	{ platformName,
				  cbStarfireNum,
				  cbStarfire5VDC,
				  cbStarfire5VDCHK,
				  cbStarfire3p3VDCHK,
				  cbStarfire5VDCPer,
				  cbStarfire5VDCFan
				}
		DESCRIPTION	"This trap indicates a Control Board max
				voltage reading. The platform name and
				board number variables will always be
				provided with this trap. Whereas, only those
				voltage readings that crossed the
				threshold will be included."
		::= 39

	cbVoltMin TRAP-TYPE
		ENTERPRISE	sun
		VARIABLES 	{ platformName,
				  cbStarfireNum,
				  cbStarfire5VDC,
				  cbStarfire5VDCHK,
				  cbStarfire3p3VDCHK,
				  cbStarfire5VDCPer,
				  cbStarfire5VDCFan
				}
		DESCRIPTION	"This trap indicates a Control Board min
				voltage reading. The platform name and
				board number variables will always be
				provided with this trap. Whereas, only those
				voltage readings that crossed the
				threshold will be included."
		::= 40

	cbVoltBad TRAP-TYPE
		ENTERPRISE	sun
		VARIABLES 	{ platformName,
				  cbStarfireNum,
				  cbStarfire5VDC,
				  cbStarfire5VDCHK,
				  cbStarfire3p3VDCHK,
				  cbStarfire5VDCPer,
				  cbStarfire5VDCFan
				}
		DESCRIPTION	"This trap indicates a Control Board bad
				voltage reading. This means that at least
				half the voltage sensors on the board
				report invalid voltage readings. The platform	
				name and board number variables will always be
				provided with this trap. Whereas, only those
				voltage readings that crossed the
				threshold will be included."
		::= 41

	cbVoltChange TRAP-TYPE
		ENTERPRISE	sun
		VARIABLES 	{ platformName,
				  cbStarfireNum,
				  cbStarfire5VDC,
				  cbStarfire5VDCHK,
				  cbStarfire3p3VDCHK,
				  cbStarfire5VDCPer,
				  cbStarfire5VDCFan
				}
		DESCRIPTION	"This trap indicates a Control Board
				voltage reading has changed within a
				specified delta. The platform name and
				board number variables will always be
				provided with this trap. Whereas, only those
				voltage readings that crossed the
				threshold will be included."
		::= 42

	centerplaneVoltNorm TRAP-TYPE
		ENTERPRISE	sun
		VARIABLES 	{ platformName,
				  centerplaneStarfireNum
				}
		DESCRIPTION	"This trap indicates a Centerplane
				transition to normal voltage reading. The
				platform name and board number variables
				will always be provided with this trap.'
				Whereas, only those voltage readings that
				crossed the threshold will be included."
		::= 43

	centerplaneVoltMax TRAP-TYPE
		ENTERPRISE	sun
		VARIABLES 	{ platformName,
				  centerplaneStarfireNum
				}
		DESCRIPTION	"This trap indicates a Centerplane max
				voltage reading. The platform name and
				board number variables will always be
				provided with this trap. Whereas, only those
				voltage readings that crossed the
				threshold will be included."
		::= 44

	centerplaneVoltMin TRAP-TYPE
		ENTERPRISE	sun
		VARIABLES 	{ platformName,
				  centerplaneStarfireNum
				}
		DESCRIPTION	"This trap indicates a Centerplane Min
				voltage reading. The platform name and
				board number variables will always be
				provided with this trap. Whereas, only those
				voltage readings that crossed the
				threshold will be included."
		::= 45

	centerplaneVoltBad TRAP-TYPE
		ENTERPRISE	sun
		VARIABLES 	{ platformName,
				  centerplaneStarfireNum
				}
		DESCRIPTION	"This trap indicates a Centerplane bad
				voltage reading. This means that at least
				half the voltage sensors on the board
				report invalid voltage readings. The platform
				name and board number variables will always be
				provided with this trap. Whereas, only those
				voltage readings that crossed the
				threshold will be included."
		::= 46

	centerplaneVoltChange TRAP-TYPE
		ENTERPRISE	sun
		VARIABLES 	{ platformName,
				  centerplaneStarfireNum
				}
		DESCRIPTION	"This trap indicates a Centerplane
				voltage reading has changed within a 
				specified delta. The platform name and
				board number variables will always be
				provided with this trap. Whereas, only those
				voltage readings that crossed the
				threshold will be included."
		::= 47

	suppBrdVoltNorm TRAP-TYPE
		ENTERPRISE	sun
		VARIABLES	{ platformName,
				  suppBrdStarfireNum,
				  suppBrdStarfire5VDCHK,
				  suppBrdStarfire3p3VDCHK
				}
		DESCRIPTION	"This trap indicates a Centerplane Support Board
				transition from over voltage reading to
				normal. The platform name and
				board number variables will always be
				provided with this trap. Whereas, only those
				voltage readings that crossed the
				threshold will be included."
		::= 48

	suppBrdVoltMax TRAP-TYPE
		ENTERPRISE	sun
		VARIABLES	{ platformName,
				  suppBrdStarfireNum,
				  suppBrdStarfire5VDCHK,
				  suppBrdStarfire3p3VDCHK
				}
		DESCRIPTION	"This trap indicates a Centerplane Support Board
				max voltage reading. The platform name and
				board number variables will always be
				provided with this trap. Whereas, only those
				voltage readings that crossed the
				threshold will be included."
		::= 49

	suppBrdVoltMin TRAP-TYPE
		ENTERPRISE	sun
		VARIABLES	{ platformName,
				  suppBrdStarfireNum,
				  suppBrdStarfire5VDCHK,
				  suppBrdStarfire3p3VDCHK
				}
		DESCRIPTION	"This trap indicates a Centerplane Support Board
				Min voltage reading. The platform name and
				board number variables will always be
				provided with this trap. Whereas, only those
				voltage readings that crossed the
				threshold will be included."
		::= 50

	suppBrdVoltBad TRAP-TYPE
		ENTERPRISE	sun
		VARIABLES	{ platformName,
				  suppBrdStarfireNum,
				  suppBrdStarfire5VDCHK,
				  suppBrdStarfire3p3VDCHK
				}
		DESCRIPTION	"This trap indicates a Centerplane Support Board
				bad voltage reading. This means that half
				the voltage sensors on the board do not
				report valid voltage readings. The platform
				name and board number variables will always be
				provided with this trap. Whereas, only those
				voltage readings that crossed the
				threshold will be included."
		::= 51

	suppBrdVoltChange TRAP-TYPE
		ENTERPRISE	sun
		VARIABLES	{ platformName,
				  suppBrdStarfireNum,
				  suppBrdStarfire5VDCHK,
				  suppBrdStarfire3p3VDCHK
				}
		DESCRIPTION	"This trap indicates a Centerplane Support
				Board voltage reading has changed within a
				specified delta. The platform name and
				board number variables will always be
				provided with this trap. Whereas, only those
				voltage readings that crossed the
				threshold will be included."
		::= 52

	fanNorm TRAP-TYPE
		ENTERPRISE	sun
		VARIABLES	{ platformName,
				  fanGenNum,
				  fanGenTraySlotNum,
				  fanGenStatus
				}
		DESCRIPTION	"This trap indicates a fan transition
				from failed to normal. All variables are
				mandatory for this trap."
		::= 53

	fanFail TRAP-TYPE
		ENTERPRISE	sun
		VARIABLES	{ platformName,
				  fanGenNum,
				  fanGenTraySlotNum
				}
		DESCRIPTION	"This trap indicates a fan failure. All
				variables are mandatory for this trap."
		::= 54

	systemConfigurationChange TRAP-TYPE
		ENTERPRISE	sun
		VARIABLES	{ platformName,
				  confSysBrdList,
				  confProcList,
				  confConBrdList,
				  confSuppBrdList,
				  confFanTrayList,
				  confBulkPowerList
				}
		DESCRIPTION	"This trap indicates that the system
				configuration has changed. It indicates
				what boards have been inserted or removed. The
				platform name will always be provided but
				only those lists that change will be included.
				Only when the system board list changes will
				the proc list be provided."
		::= 55

	arbitrationStop TRAP-TYPE
		ENTERPRISE	sun
		VARIABLES	{ platformName,
				  domainName
				}
		DESCRIPTION	"This trap indicates that a particular
				 domain has experienced an arbstop. All
				variables will be provided with this trap."
		::= 56

	recordStop TRAP-TYPE
		ENTERPRISE	sun
		VARIABLES	{ platformName,
				  domainName
				}
		DESCRIPTION	"This trap indicates that a particular
				 domain has experienced a recordarbstop. All
				variables will be provided with this trap."
		::= 57

	watchdog TRAP-TYPE
		ENTERPRISE	sun
		VARIABLES	{ platformName,
				  domainName
				}
		DESCRIPTION	"This trap indicates that a particular
				 domain has experienced a watchdog. All
				variables will be provided with this trap."
		::= 58

	environmentalShutdown TRAP-TYPE
		ENTERPRISE	sun
		VARIABLES	{ platformName,
				  domainName
				}
		DESCRIPTION	"This trap indicates that a particular
				domain has experienced an environmental
				shutdown. All variables will be provided
				with this trap."
		::= 59

	reboot TRAP-TYPE
		ENTERPRISE	sun
		VARIABLES	{ platformName,
				  domainName
				}
		DESCRIPTION	"This trap indicates that a particular
				 domain has experienced a reboot. All
				variables will be provided with this trap."
		::= 60

	panic1 TRAP-TYPE
		ENTERPRISE	sun
		VARIABLES	{ platformName,
				  domainName
				}
		DESCRIPTION	"This trap indicates that a particular
				 domain has experienced a panic1. All
				variables will be provided with this trap."
		::= 61

	panic2 TRAP-TYPE
		ENTERPRISE	sun
		VARIABLES	{ platformName,
				  domainName
				}
		DESCRIPTION	"This trap indicates that a particular
				 domain has experienced a panic2. All
				variables will be provided with this trap."
		::= 62

	panicReboot TRAP-TYPE
		ENTERPRISE	sun
		VARIABLES	{ platformName,
				  domainName
				}
		DESCRIPTION	"This trap indicates that a particular
				 domain has experienced a panic_reboot. All
				variables will be provided with this trap."
		::= 63

	heartbeatFailure TRAP-TYPE
		ENTERPRISE	sun
		VARIABLES	{ platformName,
				  domainName
				}
		DESCRIPTION	"This trap indicates that a particular
				 domain has experienced a heartbeat_failure.
				All variables will be provided with this trap."
		::= 64

	signatureBlockChange TRAP-TYPE
		ENTERPRISE	sun
		VARIABLES	{ platformName,
				  procStateGenNum,
				  procStateGenPgmSignature,
				  procStateGenPgmState,
				  procStateGenPgmSubState
				}
		DESCRIPTION	"This trap indicates that the
				 signature block has changed. All
				variables will be provided with this trap."
		::= 65

	sysbrdPowerOff TRAP-TYPE
		ENTERPRISE	sun
		VARIABLES	{ platformName,
				  sysBrdGenNum
				}
		DESCRIPTION	"This trap indicates that a system
				board has been powered off. The platform name
				will always be provided whereas one or more
				board number identifiers will be provided."
		::= 66

	sysbrdPowerOn TRAP-TYPE
		ENTERPRISE	sun
		VARIABLES	{ platformName,
				  sysBrdGenNum
				}
		DESCRIPTION	"This trap indicates that a system
				board has been powered on. The platform name
				will always be provided whereas one or more
				board number identifiers will be provided."
		::= 67

	suppbrdPowerOff TRAP-TYPE
		ENTERPRISE	sun
		VARIABLES	{ platformName,
				  suppBrdGenNum
				}
		DESCRIPTION	"This trap indicates that a support
				board has been powered off. The platform name
				will always be provided whereas one or more
				board number identifiers will be provided."
		::= 68

	suppbrdPowerOn TRAP-TYPE
		ENTERPRISE	sun
		VARIABLES	{ platformName,
				  suppBrdGenNum
				}
		DESCRIPTION	"This trap indicates that a support
				board has been powered on. The platform name
				will always be provided whereas one or more
				board number identifiers will be provided."
		::= 69

	bulkPowerNorm TRAP-TYPE
		ENTERPRISE	sun
		VARIABLES	{ platformName,
				  bulkPowerGenNum
				}
		DESCRIPTION	"This trap indicates that a particular
				Bulk Power has returned to (or is in)
				normal mode. All variables are mandatory for
				this trap."
		::= 70

	bulkPowerFail TRAP-TYPE
		ENTERPRISE	sun
		VARIABLES	{ platformName,
				  bulkPowerGenNum
				}
		DESCRIPTION	"This trap indicates Bulk Power failure. All
				variables are mandatory for this event." 
		::= 71

	bootProcChange TRAP-TYPE
		ENTERPRISE	sun
		VARIABLES	{ platformName,
				  domainName,
				  domainBootProc,
				  domainProcConfig,
				  domainABusConfig,
				  domainDBusConfig 
				}
		DESCRIPTION	"This trap indicates a change in the
				Boot Proc. All variables are mandatory
				for this event." 
		::= 72

	sigObpBooting TRAP-TYPE
		ENTERPRISE      sun
		VARIABLES       { platformName,
				  procStateGenNum,
				  domainName
				}
		DESCRIPTION     "This trap indicates that a proc in a particular
				domain has experienced a signature change
				indicating the domain is booting. The signature
				block specifies signature OBP and state BOOTING.
				All variables are mandatory
				for this event."
		::= 73

END
