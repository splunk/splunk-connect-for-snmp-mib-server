-- ZyXEL Communications Corporation
-- Private Enterprise MIB definition 
  
-- This file describes the ZyXEL Communications Corporation Enterprise MIB.
-- It contains ZyXEL products OIDs, and common managed objects.

-- $Log: ZYXEL-STATIC-ROUTE-MIB.mib $ 
-- Revision 1.5  2013/12/06 07:08:46  ccho 
-- remove uncessary imports 
-- Revision 1.4  2012/09/19 07:46:42  Kevin 
-- if it's leaf node, revise the vender name from zyxel to zy 
-- Revision 1.3  2012/08/22 09:49:12  Kevin 
-- clean warning for SNMPc 
-- Revision 1.2  2012/07/05 06:24:39  Kevin 
-- 1. upgrade from SNMP to SNMPv2  
-- 2. clean warning 
-- Revision 1.1  2012/05/30 07:50:18  Kevin 
-- Initial revision 

ZYXEL-STATIC-ROUTE-MIB DEFINITIONS ::= BEGIN

    IMPORTS
	OBJECT-TYPE
		FROM SNMPv2-SMI			-- RFC2578	
		
	MODULE-IDENTITY
		FROM SNMPv2-SMI
	
	RowStatus
		FROM SNMPv2-TC			-- RFC2579
		
	DisplayString                                          
	  	FROM SNMPv2-TC
	
  IpAddress
      FROM SNMPv2-SMI

	esMgmt			
		FROM ZYXEL-ES-SMI;

	zyxelStaticRoute MODULE-IDENTITY
		LAST-UPDATED	"201207010000Z"    
		ORGANIZATION "Enterprise Solution ZyXEL"     
		CONTACT-INFO
			""	   
		DESCRIPTION
			"The subtree for static route"
		::= { esMgmt 77 }

	zyxelStaticRouteSetup     			OBJECT IDENTIFIER ::= { zyxelStaticRoute 1 }
  
-- *******************************************************************
-- *
-- * zyxelStaticRouteSetup
-- *
-- *******************************************************************

-- zyxelStaticRouteMaxNumberOfRoutes
        zyStaticRouteMaxNumberOfRoutes OBJECT-TYPE
        SYNTAX  INTEGER
        MAX-ACCESS  read-only
        STATUS  current
        DESCRIPTION
					"The maximum number of static route entries that can be created."
        ::= { zyxelStaticRouteSetup 1 }
		
-- zyxelStaticRouteTable
        zyxelStaticRouteTable OBJECT-TYPE
        SYNTAX	SEQUENCE OF ZyxelStaticRouteEntry
        MAX-ACCESS  not-accessible
        STATUS  current
        DESCRIPTION
                 	"The table cantains  static route configuration."
        ::= { zyxelStaticRouteSetup 2 }
        
		zyxelStaticRouteEntry OBJECT-TYPE
        SYNTAX	ZyxelStaticRouteEntry
        MAX-ACCESS	not-accessible
        STATUS	current
        DESCRIPTION    	
					"An entry contains static route configuration."
        INDEX   { zyStaticRouteIpAddress, zyStaticRouteSubnetMask, zyStaticRouteGateway}
        ::= { zyxelStaticRouteTable 1 }

        ZyxelStaticRouteEntry ::=
        SEQUENCE {
           	zyStaticRouteName		DisplayString,
        	zyStaticRouteIpAddress	IpAddress,
        	zyStaticRouteSubnetMask	IpAddress,
        	zyStaticRouteGateway	IpAddress,
        	zyStaticRouteMetric		INTEGER,
        	zyStaticRouteRowStatus	RowStatus
        }

        zyStaticRouteName OBJECT-TYPE
        SYNTAX  DisplayString
        MAX-ACCESS  read-write
        STATUS  current
        DESCRIPTION
                      	"A descriptive name (up to 10 printable ASCII characters) for identification purposes."
        ::= { zyxelStaticRouteEntry 1 }

        zyStaticRouteIpAddress OBJECT-TYPE
        SYNTAX  IpAddress
        MAX-ACCESS  not-accessible
        STATUS  current
        DESCRIPTION
                     	"This parameter specifies the IP network address of the final destination. 
						Routing is always based on network number. 
						If you need to specify a route to a single host, use a subnet mask of 255.255.255.255 in the subnet mask field to force the network number to be identical to the host ID."
        ::= { zyxelStaticRouteEntry 2 }

        zyStaticRouteSubnetMask OBJECT-TYPE
        SYNTAX  IpAddress
        MAX-ACCESS  not-accessible
        STATUS  current
        DESCRIPTION
                     	"The subnet mask of an IP routing domain that is associated to a static route."
        ::= { zyxelStaticRouteEntry 3 }
        
        zyStaticRouteGateway OBJECT-TYPE
        SYNTAX  IpAddress
        MAX-ACCESS  not-accessible
        STATUS  current
        DESCRIPTION
                     	"The IP address of gateway. 
						The gateway is an immediate neighbor of your Switch that will forward the packet to the destination. 
						The gateway must be a router on the same segment as your Switch. "
        ::= { zyxelStaticRouteEntry 4 }
        
        zyStaticRouteMetric OBJECT-TYPE
        SYNTAX  INTEGER
        MAX-ACCESS  read-write
        STATUS  current
        DESCRIPTION
                     	"The metric represents the cost of transmission for routing purposes. 
						IP routing uses hop count as the measurement of cost, with a minimum of 1 for directly connected networks. 
						Enter a number that approximates the cost for this link. 
						The number need not be precise, but it must be between 1 and 15. 
						In practice, 2 or 3 is usually a good number."
        ::= { zyxelStaticRouteEntry 5 }

        zyStaticRouteRowStatus OBJECT-TYPE
        SYNTAX  RowStatus
        MAX-ACCESS  read-create
        STATUS  current
        DESCRIPTION
                     	"This object allows entries to be created and deleted from the static route table."

        ::= { zyxelStaticRouteEntry 6 }


END
