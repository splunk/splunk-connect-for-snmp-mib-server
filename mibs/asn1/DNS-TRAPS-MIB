DNS-TRAPS-MIB DEFINITIONS ::= BEGIN


           IMPORTS
                   OBJECT-TYPE, Integer32, MODULE-IDENTITY
                            FROM SNMPv2-SMI
                   bcs
                           FROM BCS-IDENT-MIB;

dns     MODULE-IDENTITY
        LAST-UPDATED "200604270000Z"

        ORGANIZATION "Motorola Connected Home Solutions"
        CONTACT-INFO "Motorola Technical Response Center
                      Inside USA     1-888-944-HELP (1-888-944-4357)
                      Outside USA    1-215-323-0044
                      TRC Hours:
                      Monday through Friday 8am - 7pm Eastern Standard Time
                      Saturdays            10am - 5pm Eastern Standard Time"

      DESCRIPTION   "The MIB module for the DNS common trap VARIABLES.
                    The MIB tree for this MIB is shown below:
                    revision number sds0.001 - initial version
                    revision number sds0.002 - revised with the changes
                        (1) traps are template defined here, it should be
                            copied to application mib module with correct
                            ENTERPRISE declared.
                        (2) all alarm var.'s SYNTAX use enumeration of
                            severity level definition."

         ::= {bcs 5}




--
--          The VARIABLES in this MIB are organized as follows:"
--
--			.gi
--			  .bcs
--                            .dns
--		 	  	.dnsTraps
--				.dnsAlarms
-- ****************************************************************************

-- This is the MIB module to manage common elements of 
-- subnetworks via the AM-NET Proxy Agent or GI Headend Controller Proxy.
--
-- groups in the DNS-TRAPS MIB

        dnsTraps OBJECT IDENTIFIER ::= { dns 1 }
        dnsAlarms OBJECT IDENTIFIER ::= { dns 2 }

-- *******************************************************************
--  The DNS Traps Group.
--
--  This group contains those VARIABLES which are specifically related
--  to trap and alarm processing by the DNS . The traps defined here 
--  are optional GI enterprise specific traps for DNS products.
-- *******************************************************************
--
-- trapConditionNotInList NOTIFICATION-TYPE
--         VARIABLES
--             {       
--                      trapIdentifier,
--                      trapSequenceId,
--                      trapNetworkElemModelNumber,
--                      trapNetworkElemSerialNum,
--                      trapPerceivedSeverity,
--                      trapNetworkElemOperState,
--                      trapNetworkElemAlarmStatus,  
--                      trapNetworkElemAdminState,
--                      trapNetworkElemAvailStatus,
--                      trapText,
--                      trapNETrapLastTrapTimeStamp,
--                      trapChangedObjectId,
--                      trapChangedValueInteger,  
--     		        trapAdditionalInfoInteger1,
--            	   	trapAdditionalInfoInteger2, 
--      	   	trapAdditionalInfoInteger3     
--            }
--            DESCRIPTION
--           " This trap is issued if a condition is being cleared and
--             it is not in the condition list.
--             trapAdditionalInfoInteger1 : Task and Function ID (task
--                                          and function generates the
--                                          error condition)
--             trapAdditionalInfoInteger2 : Condition number
--             trapAdditionalInfoInteger3 : Condition severity" 
--::= { gi 20 }
--
--trapConditionAlreadyInList NOTIFICATION-TYPE
--         VARIABLES
--             {       
--                      trapIdentifier,
--                      trapSequenceId,
--                      trapNetworkElemModelNumber,
--                      trapNetworkElemSerialNum,
--                      trapPerceivedSeverity,
--                      trapNetworkElemOperState,
--                      trapNetworkElemAlarmStatus,  
--                      trapNetworkElemAdminState,
--                      trapNetworkElemAvailStatus,
--                      trapText,
--                      trapNETrapLastTrapTimeStamp,
--                      trapChangedObjectId,
--                      trapChangedValueInteger,  
--     		        trapAdditionalInfoInteger1, 
--            	   	trapAdditionalInfoInteger2, 
--      	   	trapAdditionalInfoInteger3     
--            }
--            DESCRIPTION
--           " This trap is issued if a condition is being set and
--             it is already in the condition list.
--             trapAdditionalInfoInteger1 : Task and Function ID (task
--                                          and function generates the
--                                          error condition)
--                                          condition)
--             trapAdditionalInfoInteger2 : Condition number
--             trapAdditionalInfoInteger3 : Condition severity"
--::= { gi 21 }
--
--trapConditionListFull NOTIFICATION-TYPE
--         VARIABLES
--             {       
--                      trapIdentifier,
--                      trapSequenceId,
--                      trapNetworkElemModelNumber,
--                      trapNetworkElemSerialNum,
--                      trapPerceivedSeverity,
--                      trapNetworkElemOperState,
--                      trapNetworkElemAlarmStatus,  
--                      trapNetworkElemAdminState,
--                      trapNetworkElemAvailStatus,
--                      trapText,
--                      trapNETrapLastTrapTimeStamp,
--                      trapChangedObjectId,
--                      trapChangedValueInteger,  
--     		        trapAdditionalInfoInteger1, 
--            	   	trapAdditionalInfoInteger2, 
--      	   	trapAdditionalInfoInteger3     
--            }
--            DESCRIPTION
--           " This trap is issued if a condition is being set and
--             the condition list is full.
--             trapAdditionalInfoInteger1 : Task and Function ID (task
--                                          and function generates the
--                                          error condition)
--                                          condition)
--             trapAdditionalInfoInteger2 : Condition number
--             trapAdditionalInfoInteger3 : Condition servirty" 
--::= { gi 22 }
--
--trapInvalidCaseInSwitch NOTIFICATION-TYPE
--         VARIABLES
--             {       
--                      trapIdentifier,
--                      trapSequenceId,
--                      trapNetworkElemModelNumber,
--                      trapNetworkElemSerialNum,
--                      trapPerceivedSeverity,
--                      trapNetworkElemOperState,
--                      trapNetworkElemAlarmStatus,  
--                      trapNetworkElemAdminState,
--                      trapNetworkElemAvailStatus,
--                      trapText,
--                      trapNETrapLastTrapTimeStamp,
--                      trapChangedObjectId,
--                      trapChangedValueInteger,  
--     		        trapAdditionalInfoInteger1, 
--            	   	trapAdditionalInfoInteger2, 
--      	   	trapAdditionalInfoInteger3     
--            }
--            DESCRIPTION
--           " This trap is issued when in a switch statement the
--             default case is reached.  The trapAdditionalInfoInteger1
--     	       will contain the task and Function ID.  The
--             trapAdditionalInfoInteger2 will contain value of the switch.
--             trapAdditionalInfoInteger3 is not used."
--::= { gi 23 }
--
--trapCannotCreateSemaphore NOTIFICATION-TYPE
--         VARIABLES
--             {       
--                      trapIdentifier,
--                      trapSequenceId,
--                      trapNetworkElemModelNumber,
--                      trapNetworkElemSerialNum,
--                      trapPerceivedSeverity,
--                      trapNetworkElemOperState,
--                      trapNetworkElemAlarmStatus,  
--                      trapNetworkElemAdminState,
--                      trapNetworkElemAvailStatus,
--                      trapText,
--                      trapNETrapLastTrapTimeStamp,
--                      trapChangedObjectId,
--                      trapChangedValueInteger,  
--     		        trapAdditionalInfoInteger1, 
--            	   	trapAdditionalInfoInteger2, 
--      	   	trapAdditionalInfoInteger3     
--            }
--            DESCRIPTION
--           " This trap is issued when a semaphore cannot
--            be created. The trapAdditionalInfoInteger1 will contain the
--            task and Function ID, the trapAdditionalInfoInteger2 and
--            trapAdditionalInfoInteger3 will not be used."
--::= { gi 24 }
--
--trapCannotOpenSocket NOTIFICATION-TYPE
--         VARIABLES
--             {       
--                      trapIdentifier,
--                      trapSequenceId,
--                      trapNetworkElemModelNumber,
--                      trapNetworkElemSerialNum,
--                      trapPerceivedSeverity,
--                      trapNetworkElemOperState,
--                      trapNetworkElemAlarmStatus,  
--                      trapNetworkElemAdminState,
--                      trapNetworkElemAvailStatus,
--                      trapText,
--                      trapNETrapLastTrapTimeStamp,
--                      trapChangedObjectId,
--                      trapChangedValueInteger,  
--     		        trapAdditionalInfoInteger1, 
--            	   	trapAdditionalInfoInteger2, 
--      	   	trapAdditionalInfoInteger3     
--            }
--            DESCRIPTION
--           " This trap is issued when a socket cannot
--            be opened. The trapAdditionalInfoInteger1 will contain the
--            task and Function ID. The trapAdditionalInfoInteger2 will
--            contain the errno returned by the call to socket(). The
--            trapAdditionalInfoInteger3 is not used."
--::= { gi 25 }
--
--trapUnknownMessageReceived NOTIFICATION-TYPE
--         VARIABLES
--             {       
--                      trapIdentifier,
--                      trapSequenceId,
--                      trapNetworkElemModelNumber,
--                      trapNetworkElemSerialNum,
--                      trapPerceivedSeverity,
--                      trapNetworkElemOperState,
--                      trapNetworkElemAlarmStatus,  
--                      trapNetworkElemAdminState,
--                      trapNetworkElemAvailStatus,
--                      trapText,
--                      trapNETrapLastTrapTimeStamp,
--                      trapChangedObjectId,
--                      trapChangedValueInteger,  
--     		        trapAdditionalInfoInteger1, 
--            	   	trapAdditionalInfoInteger2, 
--      	   	trapAdditionalInfoInteger3     
--            }
--            DESCRIPTION
--           " This trap is issued when an unknown message
--            is received.  The trapAdditionalInfoInteger1 will contain the
--            task and Function ID. The trapAdditionalInfoInteger2 will 
--            contain the message ID and the trapAdditionalInfoInteger3 is
--            not used."
--::= { gi 26 }
--
--trapInvalidMessageReceived NOTIFICATION-TYPE
--         VARIABLES
--             {       
--                      trapIdentifier,
--                      trapSequenceId,
--                      trapNetworkElemModelNumber,
--                      trapNetworkElemSerialNum,
--                      trapPerceivedSeverity,
--                      trapNetworkElemOperState,
--                      trapNetworkElemAlarmStatus,  
--                      trapNetworkElemAdminState,
--                      trapNetworkElemAvailStatus,
--                      trapText,
--                      trapNETrapLastTrapTimeStamp,
--                      trapChangedObjectId,
--                      trapChangedValueInteger,  
--     		        trapAdditionalInfoInteger1, 
--            	   	trapAdditionalInfoInteger2, 
--      	   	trapAdditionalInfoInteger3     
--            }
--            DESCRIPTION
--           " This trap is issued when an invalid message
--            is received.  The trapAdditionalInfoInteger1 will contain the
--            task and Function ID. The trapAdditionalInfoInteger2 will
--            contain the message ID and the trapAdditionalInfoInteger3 is
--            not used."
--::= { gi 27 }
--
--
--
-- *******************************************************************
--  Alarm OIDs.  These OIDs correspond to traps declared above and
--  have the same number as the trap number above.
-- *******************************************************************

   alarmConditionNotInList OBJECT-TYPE
           SYNTAX          Integer32
     	   MAX-ACCESS      read-only
           STATUS          current
           DESCRIPTION 
        "Alarm which occurs when a clear condition command is
	 issued and there is no such condition in the
	 current condition list.  This is a counter for the trap 20."
   ::= { dnsAlarms 20 }

   alarmConditionAlreadyInList OBJECT-TYPE
           SYNTAX          Integer32
     	   MAX-ACCESS      read-only
           STATUS          current
           DESCRIPTION 
        "Alarm which occurs when a set condition command is
	 issued and there is already the same condition in the
	 current condition list.  This is a counter for the trap 21."
   ::= { dnsAlarms 21 }

   alarmConditionListFull OBJECT-TYPE
           SYNTAX          Integer32
     	   MAX-ACCESS      read-only
           STATUS          current
           DESCRIPTION 
        "Alarm which occurs when a set condition command is
	 issued and there is no room in the current condition list.
	 This is a counter for the trap 22."
   ::= { dnsAlarms 22 }

   alarmInvalidCaseInSwitch OBJECT-TYPE
           SYNTAX          Integer32
     	   MAX-ACCESS      read-only
           STATUS          current
           DESCRIPTION 
        "Alarm which occurs when in a switch statement the
         default case is reached.  This is a counter for the trap 23."
   ::= { dnsAlarms 23 }

   alarmCannotCreateSemaphore OBJECT-TYPE
           SYNTAX          Integer32
     	   MAX-ACCESS      read-only
           STATUS          current
           DESCRIPTION 
        "Alarm which occurs when a semaphore cannot be created.
	 This is a counter for the trap 24."
   ::= { dnsAlarms 24 }

   alarmCannotOpenSocket OBJECT-TYPE
           SYNTAX          Integer32
     	   MAX-ACCESS      read-only
           STATUS          current
           DESCRIPTION 
        "Alarm which occurs when a socket cannot be opened.
         This is a counter for the trap 25."
   ::= { dnsAlarms 25 }

   alarmUnknownMessageReceived OBJECT-TYPE
           SYNTAX          Integer32
     	   MAX-ACCESS      read-only
           STATUS          current
           DESCRIPTION 
        "Alarm which occurs when an unknown message is received.
	 This is a counter for the trap 26."
   ::= { dnsAlarms 26 }

   alarmInvalidMessageReceived OBJECT-TYPE
           SYNTAX          Integer32
     	   MAX-ACCESS      read-only
           STATUS          current
           DESCRIPTION 
        "Alarm which occurs when an invalid message is received.
	 This is a counter for the trap 27."
   ::= { dnsAlarms 27 }

END
