-- This file is corresponding to Release 9.1.10.101 from 2014/08/11 00:00:00


-- **********************************************************************
-- IEEE 802.11 Management Information Base
--
-- $RCSfile: mib-ieee802dot11,v $
-- $Revision: 1.11 $
-- $Date: 2011-03-23 10:54:12 $
-- **********************************************************************

-- with ARtem extensions:
-- 802.11a, 802.11b, 802.11d, 802.11e, 802.11g, 802.11h, 802.11i, 802.11n, 
-- parts of 802.11k

IEEE802dot11-MIB DEFINITIONS ::= BEGIN
    IMPORTS
	MODULE-IDENTITY, OBJECT-TYPE, 
        NOTIFICATION-TYPE,Integer32, Counter32, Counter64,
	Unsigned32	    	FROM SNMPv2-SMI
	DisplayString , MacAddress, RowStatus,
	TruthValue                              FROM SNMPv2-TC
	MODULE-COMPLIANCE, OBJECT-GROUP, 
	NOTIFICATION-GROUP                      FROM SNMPv2-CONF
	ifIndex                                 FROM IF-MIB;





member-body OBJECT IDENTIFIER ::= { iso 2 }
us	    OBJECT IDENTIFIER ::= { member-body 840 }

-- **********************************************************************
-- *  MODULE IDENTITY
-- **********************************************************************
ieee802dot11 MODULE-IDENTITY
    LAST-UPDATED "200103270000Z"
    ORGANIZATION "IEEE 802.11"
    CONTACT-INFO 
           "WG E-mail: stds-802-11@ieee.org

                Chair: Stuart J. Kerry
               Postal: Philips Semiconductors, Inc.
                       1109 McKay Drive
                       M/S 48 SJ
                       San Jose, CA 95130-1706 USA
                  Tel: +1 408 474 7356
                  Fax: +1 408 474 7247
               E-mail: stuart.kerry@philips.com

               Editor: Bob O'Hara
               Postal: Informed Technology, Inc.
                       1750 Nantucket Circle, Suite 138
                       Santa Clara, CA 95054 USA
                  Tel: +1 408 986 9596
                  Fax: +1 408 727 2654
               E-mail: bob@informed-technology.com"
    DESCRIPTION
        "The MIB module for IEEE 802.11 entities.
        iso(1).member-body(2).us(840).ieee802dot11(10036)"
    ::= { 1 2 840 10036 }

-- **********************************************************************
-- *  Major sections
-- **********************************************************************
--  Station ManagemenT (SMT) Attributes
    --  DEFINED AS "The SMT object class provides the necessary support at the
    --  station to manage the processes in the station such that the
    --  station may work cooperatively as a part of an IEEE 802.11 network.";

    dot11smt OBJECT IDENTIFIER 
    ::=   {ieee802dot11 1}

    -- dot11smt GROUPS
    -- dot11StationConfigTable			::= {dot11smt 1}
    -- dot11AuthenticationAlgorithmsTable	::= {dot11smt 2}
    -- dot11WEPDefaultKeysTable			::= {dot11smt 3}

    -- dot11WEPKeyMappingsTable			::= {dot11smt 4}

    -- dot11PrivacyTable			::= {dot11smt 5}
    -- dot11SMTnotification			::= {dot11smt 6}
    -- dot11MultiDomainCapabilityTable		::= {dot11smt 7}
    -- dot11SpectrumManagementTable		::= {dot11smt 8}
    -- dot11RSNAConfigTable			::= { dot11smt 9 }
    -- dot11RSNAConfigPairwiseCiphersTable	::= { dot11smt 10 }
    -- dot11RSNAConfigAuthenticationSuitesTable	::= { dot11smt 11 }
    -- dot11RSNAStatsTable			::= { dot11smt 12 }
    
    -- dot11HTStationConfigTable		::= { dot11smt 16 }
      
--  MAC Attributes
    --  DEFINED AS "The MAC object class provides the necessary support
    --  for the access control, generation, and verification of frame check
    --  sequences, and proper delivery of valid data to upper layers.";

    dot11mac OBJECT IDENTIFIER 
    ::=   {ieee802dot11 2}

    -- MAC GROUPS
    --  reference IEEE Std 802.1f-1993
    --    dot11OperationTable		::=    {dot11mac 1}
    --    dot11CountersTable		::=    {dot11mac 2}

    --    dot11GroupAddressesTable	::=    {dot11mac 3}
    -- 	dot11EDCATable 	    		::= 	{ dot11mac 4 }
    -- 	dot11QAPEDCATable 		::= 	{ dot11mac 5 }
    -- 	dot11QosCountersTable 		::= 	{ dot11mac 6 }


--  Resource Type ID
      dot11res OBJECT IDENTIFIER
     ::=   {ieee802dot11 3}
      dot11resAttribute OBJECT IDENTIFIER   ::=   {dot11res 1 }

--  PHY Attributes
    --  DEFINED AS "The PHY object class provides the necessary support
    --  for required PHY operational information that may vary from PHY
    --  to PHY and from STA to STA to be communicated to upper layers."

   dot11phy OBJECT IDENTIFIER 
   ::=   {ieee802dot11 4}

    -- phy GROUPS
    -- dot11PhyOperationTable		::=  {dot11phy 1}
    -- dot11PhyAntennaTable		::=  {dot11phy 2}
    -- dot11PhyTxPowerTable		::=  {dot11phy 3}

    -- dot11PhyFHSSTable		::=  {dot11phy 4}

    -- dot11PhyDSSSTable		::=  {dot11phy 5}

    -- dot11PhyIRTable			::=  {dot11phy 6}

    -- dot11RegDomainsSupportedTable	::=  {dot11phy 7}
    -- dot11AntennasListTable		::=  {dot11phy 8}
    -- dot11SupportedDataRatesTxTable	::=  {dot11phy 9}
    -- dot11SupportedDataRatesRxTable	::=  {dot11phy 10}
    -- dot11PhyHRDSSSTable		::= {dot11phy 12}

    -- dot11EHCCHoppingPatternTable	::= {dot11phy 13}

    -- dot11PhyERPTable			::= {dot11phy 14}
    -- dot11PhyHTTable 	    		::=  {dot11phy 15}
    -- dot11HTSupportedMCSTxTable 	::=  {dot11phy 16}
    -- dot11HTSupportedMCSRxTable 	::=  {dot11phy 17}
    -- dot11TxBFConfigTable 		::=  {dot11phy 18}

-- **********************************************************************
-- *  Textual conventions from 802 definitions
-- **********************************************************************
    WEPKeytype ::= OCTET STRING (SIZE (5))

-- **********************************************************************
-- *  MIB attribute OBJECT-TYPE definitions follow
-- **********************************************************************

-- **********************************************************************
-- *  SMT Station Config  Table
-- **********************************************************************
dot11StationConfigTable OBJECT-TYPE
        SYNTAX SEQUENCE OF Dot11StationConfigEntry
        MAX-ACCESS not-accessible
        STATUS current
        DESCRIPTION
            "Station Configuration attributes.  In tablular form to
            allow for multiple instances on an agent."
    ::= {  dot11smt 1 }

dot11StationConfigEntry OBJECT-TYPE
        SYNTAX Dot11StationConfigEntry
        MAX-ACCESS not-accessible
        STATUS current
        DESCRIPTION

            "An entry in the dot11StationConfigTable.  It is
            possible for there to be multiple IEEE 802.11 interfaces
            on one agent, each with its unique MAC address. The
            relationship between an IEEE 802.11 interface and an
            interface in the context of the Internet-standard MIB is
            one-to-one.  As such, the value of an ifIndex object
            instance can be directly used to identify corresponding
            instances of the objects defined herein.  

            ifIndex - Each 802.11 interface is represented by an
            ifEntry.  Interface tables in this MIB module are indexed
            by ifIndex."

        INDEX {ifIndex}
    ::= {  dot11StationConfigTable 1 }

Dot11StationConfigEntry ::=
        SEQUENCE {
	    dot11StationID	    			MacAddress,
	    dot11PrivacyOptionImplemented		TruthValue,
	    dot11PowerManagementMode			INTEGER,
	    dot11DesiredSSID				OCTET STRING,
	    dot11DesiredBSSType				INTEGER,
	    dot11OperationalRateSet			OCTET STRING,
	    dot11BeaconPeriod				INTEGER,
	    dot11DTIMPeriod	    			INTEGER,
	    dot11AssociationResponseTimeOut		Unsigned32,
	    dot11DisassociateReason			INTEGER,
	    dot11DisassociateStation			MacAddress,
	    dot11DeauthenticateReason			INTEGER,
	    dot11DeauthenticateStation			MacAddress,
	    dot11AuthenticateFailStatus			INTEGER,
	    dot11AuthenticateFailStation		MacAddress,
	    dot11MultiDomainCapabilityImplemented	TruthValue,
	    dot11MultiDomainCapabilityEnabled		TruthValue,
		dot11MediumOccupancyLimit		INTEGER,
		dot11CFPollable				TruthValue,
		dot11CFPPeriod				INTEGER,
		dot11CFPMaxDuration			INTEGER,
		dot11AuthenticationResponseTimeOut	Unsigned32,
	    dot11CountryString				OCTET STRING,
	    dot11SpectrumManagementImplemented		TruthValue,
	    dot11SpectrumManagementRequired		TruthValue,
	    dot11RSNAOptionImplemented			TruthValue,
	    dot11RSNAPreauthenticationImplemented 	TruthValue,
    --	    dot11RegulatoryClassesImplemented 		TruthValue,
    --	    dot11RegulatoryClassesRequired 		TruthValue,
	    dot11QosOptionImplemented 			TruthValue,
	    dot11ImmediateBlockAckOptionImplemented	TruthValue,
	    dot11DelayedBlockAckOptionImplemented 	TruthValue,
	    dot11DirectOptionImplemented 		TruthValue,
	    dot11APSDOptionImplemented 			TruthValue,
	    dot11QAckOptionImplemented 			TruthValue,
	    dot11QBSSLoadOptionImplemented 		TruthValue,
	    dot11QueueRequestOptionImplemented 		TruthValue,
	    dot11TXOPRequestOptionImplemented 		TruthValue,
	    dot11MoreDataAckOptionImplemented 		TruthValue,
	    dot11AssociateinNQBSS 			TruthValue,
	    dot11DLSAllowedInQBSS 			TruthValue,
	    dot11DLSAllowed 				TruthValue,
	    dot11HighThroughputOptionImplemented 	TruthValue }

dot11StationID OBJECT-TYPE
        SYNTAX MacAddress
        MAX-ACCESS read-write
        STATUS deprecated
        DESCRIPTION

            "The purpose of dot11StationID is to allow a manager to identify
            a station for its own purposes.  This attribute provides
            for that eventuality while keeping the true MAC address
            independent.  Its syntax is MAC address and default value
            is the station's assigned, unique MAC address."

    ::= { dot11StationConfigEntry 1 }

dot11MediumOccupancyLimit OBJECT-TYPE
        SYNTAX INTEGER (0..1000)
        MAX-ACCESS read-write
        STATUS current
        DESCRIPTION

            "This attribute shall indicate the maximum amount of time,
            in TU, that a point coordinator may control the usage of
            the wireless medium without relinquishing control for long
            enough to allow at least one instance of DCF access to the
            medium.  The default value of this attribute shall be 100,
            and the maximum value shall be 1000."

    ::= { dot11StationConfigEntry 2 }

dot11CFPollable OBJECT-TYPE
        SYNTAX TruthValue
        MAX-ACCESS read-only
        STATUS current
        DESCRIPTION

	    "When this attribute is true, it shall indicate that the STA
	    is able to respond to a CF-Poll with a data frame within a
	    SIFS time. This attribute shall be false if the STA is not
	    able to respond to a CF-Poll with a data frame within a SIFS
	    time."

    ::= { dot11StationConfigEntry 3 }

dot11CFPPeriod OBJECT-TYPE
        SYNTAX INTEGER (0..255)
        MAX-ACCESS read-write
        STATUS current
        DESCRIPTION

            "The attribute shall describe the number of DTIM intervals
            between the start of CFPs.  It is modified by
            MLME-START.request primitive."

::= {  dot11StationConfigEntry 4 }

dot11CFPMaxDuration OBJECT-TYPE
        SYNTAX INTEGER (0..65535)
        MAX-ACCESS read-write
        STATUS current
        DESCRIPTION

	    "The attribute shall describe the maximum duration of the CFP
	    in TU that may be generated by the PCF. It is modified by
	    MLME-START.request primitive."

::= {  dot11StationConfigEntry 5 }

dot11AuthenticationResponseTimeOut OBJECT-TYPE
        SYNTAX Unsigned32 (1..4294967295)
        MAX-ACCESS read-write
        STATUS current
        DESCRIPTION

            "This attribute shall specify the number of TU that a
            responding STA should wait for the next frame in the
            authentication sequence."

    ::= {  dot11StationConfigEntry 6 }

dot11PrivacyOptionImplemented OBJECT-TYPE
        SYNTAX TruthValue
        MAX-ACCESS read-only
        STATUS current
        DESCRIPTION

            "This attribute, when true, shall indicate that the IEEE
             802.11 WEP option is implemented.  The default value of
             this attribute shall be false."

    ::= {  dot11StationConfigEntry 7 }

dot11PowerManagementMode OBJECT-TYPE
	SYNTAX INTEGER { active(1), powersave(2) }
	MAX-ACCESS read-write
	STATUS current
	DESCRIPTION
	    "This attribute shall specify the power management
	     mode of the STA. When set to active, it shall indicate
	     that the station is not in power-save mode. When set
	     to powersave, it shall indicate that the station is
	     in power-save mode. The power management mode is
	     transmitted in all frames according to the rules
	     in  7.1.3.1.7."
    ::= { dot11StationConfigEntry 8 }

dot11DesiredSSID OBJECT-TYPE
	SYNTAX OCTET STRING (SIZE(0..32))
	MAX-ACCESS read-write
	STATUS current
	DESCRIPTION
	    "This attribute reflects the Service Set ID used
	    in the DesiredSSID parameter of the most recent
	    MLME_Scan.request.  This value may be modified
	    by an external management entity and used by the
	    local SME to make decisions about the Scanning process."
    ::= { dot11StationConfigEntry 9 }

dot11DesiredBSSType OBJECT-TYPE
	SYNTAX INTEGER { infrastructure(1), independent(2), any(3) }
	MAX-ACCESS read-write
	STATUS current
	DESCRIPTION
	    "This attribute shall specify the type of BSS the
	     station shall use when scanning for a BSS with which
	     to synchronize. This value is used to filter Probe
	     Response frames and Beacons. When set to infrastructure,
	     the station shall only synchronize with a BSS whose
	     Capability Information field has the ESS subfield set
	     to 1. When set to independent, the station shall only
	     synchronize with a BSS whose Capability Information
	     field has the IBSS subfield set to 1. When set to
	     any, the station may synchronize to either type of
	     BSS."
    ::= { dot11StationConfigEntry 10 }

dot11OperationalRateSet OBJECT-TYPE
	SYNTAX OCTET STRING (SIZE(1..126))
	MAX-ACCESS read-write
	STATUS current
	DESCRIPTION
	    "This attribute shall specify the set of data rates
	     at which the station may transmit data.  Each octet
	     contains a value representing a rate.  Each rate
	     shall be within the range from 2 to 127,
	     corresponding to data rates in increments of
	     500 kb/s from 1 Mb/s to 63.5 Mb/s, and shall be
	     supported (as indicated in the supported rates
	     table) for receiving data. This value is reported in
	     transmitted Beacon, Probe Request, Probe Response,
	     Association Request, Association Response,
	     Reassociation Request, and Reassociation Response
	     frames, and is used to determine whether a BSS
	     with which the station desires to synchronize is
	     suitable. It is also used when starting a BSS,
	     as specified in  10.3."
    ::= { dot11StationConfigEntry 11 }

dot11BeaconPeriod OBJECT-TYPE
	SYNTAX INTEGER (1..65535)
	MAX-ACCESS read-write
	STATUS current
	DESCRIPTION
	    "This attribute shall specify the number of TU that a
	     station shall use for scheduling Beacon transmissions.
	     This value is transmitted in Beacon and Probe Response
	     frames."
    ::= { dot11StationConfigEntry 12 }

dot11DTIMPeriod OBJECT-TYPE
	SYNTAX INTEGER(1..255)
	MAX-ACCESS read-write
	STATUS current
	DESCRIPTION
	    "This attribute shall specify the number of beacon
	     intervals that shall elapse between transmission of
	     Beacons frames containing a TIM element whose DTIM
	     Count field is 0. This value is transmitted in
	     the DTIM Period field of Beacon frames."
    ::= { dot11StationConfigEntry 13 }

dot11AssociationResponseTimeOut OBJECT-TYPE
	SYNTAX Unsigned32(1..4294967295)
	MAX-ACCESS read-write
	STATUS current
	DESCRIPTION
	    "This attribute shall specify the number of TU that a
	     requesting STA should wait for a response to a
	     transmitted association-request MMPDU."
    ::= { dot11StationConfigEntry 14 }

dot11DisassociateReason OBJECT-TYPE
	SYNTAX INTEGER(0..65535)
	MAX-ACCESS read-only
	STATUS current
	DESCRIPTION
	    "This attribute holds the most recently
	    transmitted Reason Code in a Disassociation
	    frame.  If no Disassociation frame has been
	    transmitted, the value of this attribute shall
	    be 0."

	REFERENCE "IEEE Std 802.11-1997, 7.3.1.7"
    ::= { dot11StationConfigEntry 15 }

dot11DisassociateStation OBJECT-TYPE
	SYNTAX MacAddress
	MAX-ACCESS read-only
	STATUS current
	DESCRIPTION
	    "This attribute holds the MAC address from the
	    Address 1 field of the most recently transmitted
	    Disassociation frame.  If no Disassociation
	    frame has been transmitted, the value of this
	    attribute shall be 0."
    ::= { dot11StationConfigEntry 16 }

dot11DeauthenticateReason OBJECT-TYPE
	SYNTAX INTEGER(0..65535)
	MAX-ACCESS read-only
	STATUS current
	DESCRIPTION
	    "This attribute holds the most recently
	    transmitted Reason Code in a Deauthentication
	    frame.  If no Deauthentication frame has been
	    transmitted, the value of this attribute shall
	    be 0."

REFERENCE "IEEE Std 802.11-1997, 7.3.1.7"
    ::= { dot11StationConfigEntry 17 }

dot11DeauthenticateStation OBJECT-TYPE
	SYNTAX MacAddress
	MAX-ACCESS read-only
	STATUS current
	DESCRIPTION
	    "This attribute holds the MAC address from the
	    Address 1 field of the most recently transmitted
	    Deauthentication frame.  If no Deauthentication
	    frame has been transmitted, the value of this
	    attribute shall be 0."
    ::= { dot11StationConfigEntry 18 }

dot11AuthenticateFailStatus OBJECT-TYPE
	SYNTAX INTEGER(0..65535)
	MAX-ACCESS read-only
	STATUS current
	DESCRIPTION
	    "This attribute holds the most recently
	    transmitted Status Code in a failed
	    Authentication frame.  If no failed
	    Authentication frame has been transmitted, the
	    value of this attribute shall be 0."

	REFERENCE "IEEE Std 802.11-1997, 7.3.1.9"
    ::= { dot11StationConfigEntry 19 }

dot11AuthenticateFailStation OBJECT-TYPE
	SYNTAX MacAddress
	MAX-ACCESS read-only
	STATUS current
	DESCRIPTION
	    "This attribute holds the MAC address from the
	    Address 1 field of the most recently transmitted
	    failed Authentication frame.  If no failed
	    Authentication frame has been transmitted, the
	    value of this attribute shall be 0."
    ::= { dot11StationConfigEntry 20 }

dot11MultiDomainCapabilityImplemented OBJECT-TYPE
        SYNTAX TruthValue
        MAX-ACCESS read-write
        STATUS current
        DESCRIPTION
	    "This attribute, when TRUE, indicates that the station implementation is
	    capable of supporting multiple regulatory domains. The capability is
	    disabled, otherwise. The default value of this attribute is FALSE."
        ::= { dot11StationConfigEntry 21 }
dot11MultiDomainCapabilityEnabled OBJECT-TYPE
        SYNTAX TruthValue
        MAX-ACCESS read-write
        STATUS current
        DESCRIPTION
	    "This attribute, when TRUE, indicates that the capability of the station
	    to operate in multiple regulatory domains is enabled. The capability is
	    disabled, otherwise. The default value of this attribute is FALSE."
::= { dot11StationConfigEntry 22 }
dot11CountryString OBJECT-TYPE
        SYNTAX OCTET STRING (SIZE (3))
        MAX-ACCESS read-only
        STATUS current
        DESCRIPTION
	    "This attribute identifies the country in which the station is operating.
	    The first two octets of this string is the two character country code as
	    described in document ISO/IEC 3166-1. The third octet shall be one of the
	    following:
	    1. an ASCII space character, if the regulations under which the
	       station is operating encompass all environments in the country,
	    2. an ASCII 'O' character, if the regulations under which the
	       station is operating are for an Outdoor environment only, or
	    3. an ASCII 'I' character, if the regulations under which the
	       station is operating are for an Indoor environment only."
::= { dot11StationConfigEntry 23 }

dot11SpectrumManagementImplemented OBJECT-TYPE
	SYNTAX TruthValue
	MAX-ACCESS read-write
	STATUS current
	DESCRIPTION
	    "This attribute, when TRUE, indicates that the station
	    implementation is capable of supporting spectrum management.                
	    The capability is disabled otherwise. The default value of this
	    attribute is FALSE."
::= { dot11StationConfigEntry 24 }

dot11SpectrumManagementRequired OBJECT-TYPE
	SYNTAX TruthValue
	MAX-ACCESS read-write
	STATUS current
	DESCRIPTION
	    "A STA will use the defined TPC and DFS procedures if and only
	    if this attribute is TRUE. The default value of this attribute
	    is FALSE."
::= { dot11StationConfigEntry 25 }

dot11RSNAOptionImplemented OBJECT-TYPE
	SYNTAX	    TruthValue
	MAX-ACCESS  read-only
	STATUS	    current
	DESCRIPTION
	    "This variable indicates whether the entity is RSNA-capable."
::= { dot11StationConfigEntry 26 }

dot11RSNAPreauthenticationImplemented OBJECT-TYPE
	SYNTAX	    TruthValue
	MAX-ACCESS  read-only
	STATUS	    current
	DESCRIPTION
	    "This variable indicates whether the entity supports RSNA
	    preauthentication. This cannot be TRUE unless
	    dot11RSNAOptionImplemented is TRUE."
::= { dot11StationConfigEntry 27 }

dot11QosOptionImplemented OBJECT-TYPE
	SYNTAX TruthValue
	MAX-ACCESS read-only
	STATUS current
	DESCRIPTION
	    "This attribute, when TRUE, indicates that the station
	    implementation is capable of supporting QoS. The capability
	    is disabled, otherwise. The default value of this attribute
	    is FALSE."
        DEFVAL { false }
::= { dot11StationConfigEntry 30}

dot11ImmediateBlockAckOptionImplemented OBJECT-TYPE
	SYNTAX TruthValue
	MAX-ACCESS read-only
	STATUS current
	DESCRIPTION
	    "This attribute, when TRUE, indicates that the station
	    implementation is capable of supporting Immediate Block Ack.
	    The capability is disabled, otherwise. The default value of
	    this attribute is FALSE."
        DEFVAL { false }
::= { dot11StationConfigEntry 31}

dot11DelayedBlockAckOptionImplemented OBJECT-TYPE
	SYNTAX TruthValue
	MAX-ACCESS read-only
	STATUS current
	DESCRIPTION
	    "This attribute, when TRUE, indicates that the station
	    implementation is capable of supporting Delayed Block Ack.
	    The capability is disabled, otherwise. The default value of
	    this attribute is FALSE."
        DEFVAL { false }
::= { dot11StationConfigEntry 32 }

dot11DirectOptionImplemented OBJECT-TYPE
	SYNTAX TruthValue
	MAX-ACCESS read-only
	STATUS current
	DESCRIPTION
	    "This attribute, when TRUE, indicates that the station
	    implementation is capable of sending and receiving frames
	    from a non-AP QSTA in the QBSS. The capability is disabled,
	    otherwise. The default value of this attribute is FALSE."
        DEFVAL { false }
::= { dot11StationConfigEntry 33 }

dot11APSDOptionImplemented OBJECT-TYPE
	SYNTAX TruthValue
	MAX-ACCESS read-only
	STATUS current
	DESCRIPTION
	    "This attribute is available only at a QAP. When TRUE,
	    this attribute indicates that the QAP implementation is
	    capable of delivering data and polls to stations using
	    APSD."
        DEFVAL { false }
::= { dot11StationConfigEntry 34 }

dot11QAckOptionImplemented OBJECT-TYPE
	SYNTAX TruthValue
	MAX-ACCESS read-only
	STATUS current
	DESCRIPTION
	    "This attribute, when TRUE, indicates that the station
	    implementation is capable of interpreting the CF-Ack bit
	    in a received frame of type data even if the frame is not
	    directed to the QoS station. The capability is disabled,
	    otherwise. A QSTA is capable of interpreting the CF-Ack bit
	    in a received data frame if that station is the recipient
	    of the data frame, regardless of the value of this MIB
	    variable. The default value of this attribute is FALSE."
        DEFVAL { false }
::= { dot11StationConfigEntry 35 }

dot11QBSSLoadOptionImplemented OBJECT-TYPE
	SYNTAX TruthValue
	MAX-ACCESS read-only
	STATUS current
	DESCRIPTION
	    "This attribute is available only at a QAP. This attribute,
	    when TRUE, indicates that the QAP implementation is capable
	    of generating and transmitting the QBSS load element in the
	    Beacon and Probe Response frames. The capability is
	    disabled, otherwise. The default value of this attribute is
	    FALSE."
        DEFVAL { false }
::= { dot11StationConfigEntry 36 }

dot11QueueRequestOptionImplemented OBJECT-TYPE
	SYNTAX TruthValue
	MAX-ACCESS read-only
	STATUS current
	DESCRIPTION
	    "This attribute is available only at a QAP. This attribute,
	    when TRUE, indicates that the QAP is capable of processing
	    the Queue Size field in QoS Control field of QoS Data type
	    frames. The capability is disabled, otherwise. The default
	    value of this attribute is FALSE."
        DEFVAL { false }
::= { dot11StationConfigEntry 37 }

dot11TXOPRequestOptionImplemented OBJECT-TYPE
	SYNTAX TruthValue
	MAX-ACCESS read-only
	STATUS current
	DESCRIPTION
	    "This attribute is available only at a QAP. This attribute,
	    when TRUE, indicates that the QAP is capable of processing
	    the TXOP Duration requested field in QoS Control field of
	    QoS Data type frames. The capability is disabled, otherwise.
	    The default value of this attribute is FALSE."
        DEFVAL { false }
::= { dot11StationConfigEntry 38 }

dot11MoreDataAckOptionImplemented OBJECT-TYPE
	SYNTAX TruthValue
	MAX-ACCESS read-only
	STATUS current
	DESCRIPTION
	    "This attribute, when TRUE, indicates that the station
	    implementation is capable of interpreting the More Data
	    bit in the ACK frames. The capability is disabled,
	    otherwise. The default value of this attribute is FALSE."
        DEFVAL { false }
::= { dot11StationConfigEntry 39 }

dot11AssociateinNQBSS OBJECT-TYPE
	SYNTAX TruthValue
	MAX-ACCESS read-write
	STATUS current
	DESCRIPTION
	    "This attribute, when TRUE, indicates that the station may
	    associate in an nQBSS. When FALSE, this attribute indicates
	    that the station may only associate in a QBSS. The default
	    value of this attribute is TRUE."
        DEFVAL { true }
::= { dot11StationConfigEntry 40 }

dot11DLSAllowedInQBSS OBJECT-TYPE
	SYNTAX TruthValue
	MAX-ACCESS read-write
	STATUS current
	DESCRIPTION
	    "This attribute available at the QAP, when TRUE, indicates
	    that non-AP QSTAs may set up DLS and communicate with other
	    non-AP QSTAs in the QBSS. When FALSE, this attribute
	    indicates that the stations shall not set up DLS nor
	    communicate with other non-AP QSTAs in the QBSS. The default
	    value of this attribute is TRUE."
        DEFVAL { true }
::= { dot11StationConfigEntry 41 }

dot11DLSAllowed OBJECT-TYPE
	SYNTAX TruthValue
	MAX-ACCESS read-write
	STATUS current
	DESCRIPTION
	    "This attribute available at the non-AP QSTAs, when TRUE,
	    indicates that QSTA may set up DLS or accept DLS Requests,
	    and communicate with other non-AP QSTAs in the QBSS. When
	    FALSE, this attribute indicates that the QSTA shall not set
	    up DLS nor accept DLS, nor communicate with other non-AP
	    QSTAs in the QBSS. The default value of this attribute is
	    TRUE."
        DEFVAL { true }
::= { dot11StationConfigEntry 42}

dot11HighThroughputOptionImplemented OBJECT-TYPE
	SYNTAX TruthValue
	MAX-ACCESS read-only
	STATUS current
	DESCRIPTION
	    "This attribute indicates whether the entity is HT Capable."
        DEFVAL { false }
::= { dot11StationConfigEntry 58 }

-- **********************************************************************
-- *    End of dot11StationConfig  TABLE
-- **********************************************************************

-- **********************************************************************
-- *    AuthenticationAlgorithms  TABLE
-- **********************************************************************
dot11AuthenticationAlgorithmsTable OBJECT-TYPE
        SYNTAX SEQUENCE OF Dot11AuthenticationAlgorithmsEntry
        MAX-ACCESS not-accessible
        STATUS current
        DESCRIPTION
            "This (conceptual) table of attributes shall be a set of
            all the authentication algorithms supported by the
            stations.  The following are the default values and the
            associated algorithm:
                Value = 1: Open System
                Value = 2: Shared Key"
        REFERENCE "IEEE Std 802.11-1997, 7.3.1.1"
    ::= {  dot11smt 2 }

dot11AuthenticationAlgorithmsEntry OBJECT-TYPE
        SYNTAX Dot11AuthenticationAlgorithmsEntry
        MAX-ACCESS not-accessible
        STATUS current
        DESCRIPTION

            "An Entry (conceptual row) in the Authentication
            Algorithms Table.  

            ifIndex - Each 802.11 interface is represented by an
            ifEntry.  Interface tables in this MIB module are indexed
            by ifIndex."

        INDEX { ifIndex,
              dot11AuthenticationAlgorithmsIndex}
    ::= {  dot11AuthenticationAlgorithmsTable  1 }

Dot11AuthenticationAlgorithmsEntry ::= SEQUENCE {
            dot11AuthenticationAlgorithmsIndex	Integer32,
            dot11AuthenticationAlgorithm	INTEGER,
	    dot11AuthenticationAlgorithmsEnable	TruthValue }

dot11AuthenticationAlgorithmsIndex OBJECT-TYPE
        SYNTAX Integer32 (1..2147483647)
        MAX-ACCESS read-only
        STATUS current
        DESCRIPTION
            "The auxiliary variable used to identify instances
            of the columnar objects in the Authentication Algorithms Table."
    ::= {  dot11AuthenticationAlgorithmsEntry 1 }

dot11AuthenticationAlgorithm OBJECT-TYPE
        SYNTAX INTEGER {  openSystem (1),   sharedKey (2) }
        MAX-ACCESS read-only
        STATUS current
        DESCRIPTION

	    "This attribute shall be a set of all the authentication
	    algorithms supported by the STAs. The following are the
	    default values and the associated algorithm.  
	    Value = 1: Open System 
	    Value = 2: Shared Key"

    ::= {  dot11AuthenticationAlgorithmsEntry 2 }

dot11AuthenticationAlgorithmsEnable  OBJECT-TYPE
        SYNTAX TruthValue
        MAX-ACCESS read-write
        STATUS current
        DESCRIPTION

	    "This attribute, when true at a station, shall enable the acceptance 
	    of the authentication algorithm described in the corresponding table 
	    entry in authentication frames received by the station that have odd 
	    authentication sequence numbers.  The default value of this attribute 
	    shall be 1 for the Open System table entry and 2 for all other table 
	    entries."

    ::= {  dot11AuthenticationAlgorithmsEntry 3 }

-- **********************************************************************
-- *    End of AuthenticationAlgorithms  TABLE
-- **********************************************************************

-- **********************************************************************
-- *    WEPDefaultKeys  TABLE
-- **********************************************************************
dot11WEPDefaultKeysTable OBJECT-TYPE
        SYNTAX SEQUENCE OF Dot11WEPDefaultKeysEntry
        MAX-ACCESS not-accessible
        STATUS current
        DESCRIPTION

            "Conceptual table for WEP default keys.  This table shall
            contain the four WEP default secret key values
            corresponding to the four possible KeyID values.  The WEP
            default secret keys are logically WRITE-ONLY.  Attempts to
            read the entries in this table shall return unsuccessful
            status and values of null or zero.  The default value of
            each WEP default key shall be null."

        REFERENCE "IEEE Std 802.11-1997, 8.3.2"
    ::= {  dot11smt 3 }

dot11WEPDefaultKeysEntry OBJECT-TYPE
        SYNTAX Dot11WEPDefaultKeysEntry
        MAX-ACCESS not-accessible
        STATUS current
        DESCRIPTION

            "An Entry (conceptual row) in the WEP Default Keys Table.

            ifIndex - Each 802.11 interface is represented by an
            ifEntry.  Interface tables in this MIB module are indexed
            by ifIndex."

        INDEX {ifIndex, dot11WEPDefaultKeyIndex}
    ::= {  dot11WEPDefaultKeysTable  1 }

Dot11WEPDefaultKeysEntry ::= SEQUENCE {
            dot11WEPDefaultKeyIndex     INTEGER,
            dot11WEPDefaultKeyValue     WEPKeytype}

dot11WEPDefaultKeyIndex OBJECT-TYPE
        SYNTAX INTEGER (1..4)
        MAX-ACCESS read-only
        STATUS current
        DESCRIPTION
            "The auxiliary variable used to identify instances
            of the columnar objects in the WEP Default Keys Table.
The value of this variable is equal to the WEPDefaultKeyID + 1"
    ::= {  dot11WEPDefaultKeysEntry 1 }

dot11WEPDefaultKeyValue OBJECT-TYPE
        SYNTAX WEPKeytype
        MAX-ACCESS read-write
        STATUS current
        DESCRIPTION
            "A WEP default secret key value."
    ::= {  dot11WEPDefaultKeysEntry 2 }

-- **********************************************************************
-- *    End of WEPDefaultKeys  TABLE
-- **********************************************************************

-- **********************************************************************
-- *    WEPKeyMappings  TABLE
-- **********************************************************************

dot11WEPKeyMappingsTable OBJECT-TYPE
        SYNTAX SEQUENCE OF Dot11WEPKeyMappingsEntry
        MAX-ACCESS not-accessible
        STATUS current
        DESCRIPTION
            "Conceptual table for WEP Key Mappings.  The MIB supports
            the ability to share a separate WEP key for each RA/TA
            pair.  The Key Mappings Table contains zero or one entry
            for each MAC address and contains two fields for each
            entry: WEPOn and the corresponding WEP key.  The WEP key
            mappings are logically WRITE-ONLY.  Attempts to read the
            entries in this table shall return unsuccessful status and
            values of null or zero.  The default value for all WEPOn
            fields is false."
        REFERENCE "IEEE Std 802.11-1997, 8.3.2"
    ::= {  dot11smt 4 }

dot11WEPKeyMappingsEntry OBJECT-TYPE
        SYNTAX Dot11WEPKeyMappingsEntry
        MAX-ACCESS not-accessible
        STATUS current
        DESCRIPTION

            "An Entry (conceptual row) in the WEP Key Mappings Table.

            ifIndex - Each 802.11 interface is represented by an
            ifEntry.  Interface tables in this MIB module are indexed
            by ifIndex."

        INDEX {ifIndex, dot11WEPKeyMappingIndex}
    ::= {  dot11WEPKeyMappingsTable  1 }

Dot11WEPKeyMappingsEntry ::= SEQUENCE {
            dot11WEPKeyMappingIndex	Integer32,
            dot11WEPKeyMappingAddress   MacAddress,
            dot11WEPKeyMappingWEPOn	TruthValue,
            dot11WEPKeyMappingValue     WEPKeytype,
	    dot11WEPKeyMappingStatus    RowStatus }

dot11WEPKeyMappingIndex OBJECT-TYPE
        SYNTAX Integer32 (1..2147483647)
        MAX-ACCESS read-only
        STATUS current
        DESCRIPTION
            "The auxiliary variable used to identify instances
            of the columnar objects in the WEP Key Mappings Table."
    ::= {  dot11WEPKeyMappingsEntry 1 }

dot11WEPKeyMappingAddress OBJECT-TYPE
        SYNTAX MacAddress
        MAX-ACCESS read-create
        STATUS current
        DESCRIPTION
            "The MAC address of the STA for which the values from this
            key mapping entry are to be used."
    ::= {  dot11WEPKeyMappingsEntry 2 }

dot11WEPKeyMappingWEPOn OBJECT-TYPE
        SYNTAX TruthValue
        MAX-ACCESS read-create
        STATUS current
        DESCRIPTION
            "Boolean as to whether WEP is to be used when communicating
            with the dot11WEPKeyMappingAddress STA."
    ::= {  dot11WEPKeyMappingsEntry 3 }

dot11WEPKeyMappingValue OBJECT-TYPE
        SYNTAX WEPKeytype
        MAX-ACCESS read-create
        STATUS current
        DESCRIPTION
            "A WEP secret key value."
    ::= {  dot11WEPKeyMappingsEntry 4 }

dot11WEPKeyMappingStatus OBJECT-TYPE
        SYNTAX RowStatus
        MAX-ACCESS read-create
        STATUS current
        DESCRIPTION

            "The status column used for creating, modifying, and
            deleting instances of the columnar objects in the WEP key
            mapping Table."

        DEFVAL {active}
    ::= { dot11WEPKeyMappingsEntry 5 }


-- **********************************************************************
-- *    End of WEPKeyMappings  TABLE
-- **********************************************************************

-- **********************************************************************
-- *    dot11PrivacyTable  TABLE
-- **********************************************************************
dot11PrivacyTable OBJECT-TYPE
        SYNTAX SEQUENCE OF Dot11PrivacyEntry
        MAX-ACCESS not-accessible
        STATUS current
        DESCRIPTION

            "Group containing attributes concerned with IEEE 802.11
            Privacy.  Created as a table to allow multiple
            instantiations on an agent."

    ::= {  dot11smt 5 }

dot11PrivacyEntry OBJECT-TYPE
        SYNTAX Dot11PrivacyEntry
        MAX-ACCESS not-accessible
        STATUS current
        DESCRIPTION
            "An entry in the dot11PrivacyTable Table.

            ifIndex - Each 802.11 interface is represented by an
            ifEntry.  Interface tables in this MIB module are indexed
            by ifIndex."
        INDEX {ifIndex}
    ::= {  dot11PrivacyTable 1 }

Dot11PrivacyEntry ::= 
	SEQUENCE {
	    dot11PrivacyInvoked			TruthValue,
	    dot11WEPDefaultKeyID		INTEGER,
	    dot11WEPKeyMappingLength		Unsigned32,
	    dot11ExcludeUnencrypted		TruthValue,
	    dot11WEPICVErrorCount		Counter32,
	    dot11WEPExcludedCount		Counter32,
	    dot11RSNAEnabled			TruthValue,
	    dot11RSNAPreAuthenticationEnabled	TruthValue}


dot11PrivacyInvoked OBJECT-TYPE
        SYNTAX TruthValue
        MAX-ACCESS read-write
        STATUS current
        DESCRIPTION

	    "When this attribute is TRUE, it shall indicate that 
	    some level of security is invoked for transmitting 
	    frames of type Data. For WEP-only clients, the security 
	    mechanism used is WEP.
	    For RSNA-capable clients, an additional variable dot11RSNAEnabled
	    indicates whether RSNA is enabled. If dot11RSNAEnabled is FALSE or
	    the MIB variable does not exist, the security mechanism invoked is
	    WEP; if dot11RSNAEnabled is TRUE, RSNA security mechanisms invoked
	    are configured in the dot11RSNAConfigTable. The default value of
	    this attribute shall be FALSE."
::= {  dot11PrivacyEntry 1 }

dot11WEPDefaultKeyID  OBJECT-TYPE
        SYNTAX INTEGER (0..3)
        MAX-ACCESS read-write
        STATUS current
        DESCRIPTION

            "This attribute shall indicate the use of the first,
            second, third, or fourth element of the WEPDefaultKeys
            array when set to values of zero, one, two, or three.  The
            default value of this attribute shall be 0."
        REFERENCE "IEEE Std 802.11-1997, 8.3.2"
::= {  dot11PrivacyEntry 2 }

dot11WEPKeyMappingLength  OBJECT-TYPE
        SYNTAX Unsigned32 (10..4294967295)
        MAX-ACCESS read-write
        STATUS current
        DESCRIPTION
            "The maximum number of tuples that dot11WEPKeyMappings can hold."
        REFERENCE "IEEE Std 802.11-1997, 8.3.2"
::= {  dot11PrivacyEntry 3 }

dot11ExcludeUnencrypted  OBJECT-TYPE
        SYNTAX TruthValue
        MAX-ACCESS read-write
        STATUS current
        DESCRIPTION

	    "When this attribute is true, the STA shall not indicate at
	    the MAC service interface received MSDUs that have the WEP
	    subfield of the Frame Control field equal to zero. When this
	    attribute is false, the STA may accept MSDUs that have the WEP
	    subfield of the Frame Control field equal to zero. The default
	    value of this attribute shall be false."

::= {  dot11PrivacyEntry 4 }

dot11WEPICVErrorCount  OBJECT-TYPE
        SYNTAX Counter32
        MAX-ACCESS read-only
        STATUS current
        DESCRIPTION
            "This counter shall increment when a frame is received with the
            WEP subfield of the Frame Control field set to one and the value
            of the ICV as received in the frame does not match the ICV value
            that is calculated for the contents of the received frame."
::= {  dot11PrivacyEntry 5 }

dot11WEPExcludedCount  OBJECT-TYPE
        SYNTAX	    Counter32
        MAX-ACCESS  read-only
        STATUS	    current
        DESCRIPTION
            "This counter shall increment when a frame is received with the
            Protected Frame subfield of the Frame Control field set to zero
            and the value of dot11ExcludeUnencrypted causes that frame 
            to be discarded."
::= {  dot11PrivacyEntry 6 }

dot11RSNAEnabled OBJECT-TYPE
	SYNTAX	    TruthValue
	MAX-ACCESS  read-write
	STATUS	    current
	DESCRIPTION
	    "When this object is set to TRUE, this shall indicate that RSNA is
	    enabled on this entity. The entity will advertise the RSN Information
	    Element in its Beacon and Probe Response frames. Configuration
	    variables for RSNA operation are found in the dot11RSNAConfigTable.
	    This object requires that dot11PrivacyInvoked also be set to TRUE."
::= { dot11PrivacyEntry 7 }

dot11RSNAPreAuthenticationEnabled OBJECT-TYPE
	SYNTAX	    TruthValue
	MAX-ACCESS  read-write
	STATUS	    current
	DESCRIPTION
	    "When this object is set to TRUE, this shall indicate that RSNA
	    preauthentication is enabled on this entity.
	    This object requires that dot11RSNAEnabled also be set to TRUE."
::= { dot11PrivacyEntry 8 }

-- **********************************************************************
-- *    End of dot11Privacy  TABLE
-- **********************************************************************

-- **********************************************************************
-- *    SMT notification Objects
-- **********************************************************************
    dot11SMTnotification OBJECT IDENTIFIER ::= { dot11smt 6 }

dot11SMT-unknown    OBJECT IDENTIFIER ::= { dot11SMTnotification 0 }

dot11Disassociate NOTIFICATION-TYPE
        OBJECTS { ifIndex, dot11DisassociateReason, dot11DisassociateStation }
        STATUS current
        DESCRIPTION

	    "The disassociate notification shall be sent when the STA
	    sends a Disassociation frame. The value of the notification
	    shall include the MAC address of the MAC to which the Disassociation
	    frame was sent and the reason for the disassociation.

	    ifIndex - Each 802.11 interface is represented by an
	    ifEntry.  Interface tables in this MIB module are indexed
	    by ifIndex."

    ::= { dot11SMT-unknown 1 }

dot11Deauthenticate NOTIFICATION-TYPE
        OBJECTS { ifIndex, dot11DeauthenticateReason, dot11DeauthenticateStation }
        STATUS current
        DESCRIPTION

	    "The deauthenticate notification shall be sent when the STA
	    sends a Deauthentication frame. The value of the notification
	    shall include the MAC address of the MAC to which the Deauthentication
	    frame was sent and the reason for the deauthentication.

	    ifIndex - Each 802.11 interface is represented by an
	    ifEntry.  Interface tables in this MIB module are indexed
	    by ifIndex."

    ::= { dot11SMT-unknown 2 }

dot11AuthenticateFail NOTIFICATION-TYPE
        OBJECTS { ifIndex, dot11AuthenticateFailStatus, dot11AuthenticateFailStation }
        STATUS current
        DESCRIPTION

	    "The authenticate failure notification shall be sent when the STA
	    sends an Authentication frame with a status code other than 
	    'successful'. The value of the notification
	    shall include the MAC address of the MAC to which the Authentication
	    frame was sent and the reason for the authentication failure.

		ifIndex - Each 802.11 interface is represented by an
		ifEntry.  Interface tables in this MIB module are indexed
		by ifIndex."

::= { dot11SMT-unknown 3 }


-- **********************************************************************
-- *    End of SMT notification Objects
-- **********************************************************************

-- ********************************************************************
-- * dot11MultiDomainCapability TABLE
-- ********************************************************************
dot11MultiDomainCapabilityTable OBJECT-TYPE
	SYNTAX SEQUENCE OF Dot11MultiDomainCapabilityEntry
	MAX-ACCESS not-accessible
	STATUS current
       
	DESCRIPTION
	    "This (conceptual) table of attributes for cross-domain mobility."
       ::= { dot11smt 7 }
       
dot11MultiDomainCapabilityEntry OBJECT-TYPE
	SYNTAX Dot11MultiDomainCapabilityEntry
	MAX-ACCESS not-accessible
	STATUS current
       
	DESCRIPTION
	    "An entry (conceptual row) in the Multiple Domain Capability Table.
	    IfIndex - Each 802.11 interface is represented by an ifEntry. Interface
	    tables in this MIB are indexed by ifIndex."
	INDEX { ifIndex,
            dot11MultiDomainCapabilityIndex}
       ::= {dot11MultiDomainCapabilityTable 1}
       
Dot11MultiDomainCapabilityEntry ::=
       SEQUENCE {
	    dot11MultiDomainCapabilityIndex	Integer32,
	    dot11FirstChannelNumber		Integer32,
	    dot11NumberofChannels		Integer32,
              dot11MaximumTransmitPowerLevel Integer32}

dot11MultiDomainCapabilityIndex OBJECT-TYPE
	SYNTAX Integer32 (1..2147483647)
        MAX-ACCESS read-only
	STATUS current
	DESCRIPTION
	    "The auxiliary variable used to identify instances of the columnar objects
	    in the Multi Domain Capability Table."

::= { dot11MultiDomainCapabilityEntry 1}

dot11FirstChannelNumber OBJECT-TYPE
	SYNTAX Integer32
	MAX-ACCESS read-write
	STATUS current
       
	DESCRIPTION
	    "This attribute shall indicate the value of the lowest channel number in
	    the subband for the associated domain country string. The default value of
	    this attribute shall be zero."       
       
::= { dot11MultiDomainCapabilityEntry 2}

dot11NumberofChannels OBJECT-TYPE
	SYNTAX Integer32
	MAX-ACCESS read-write
	STATUS current
       
	DESCRIPTION
	    "This attribute shall indicate the value of the total number of channels
	    allowed in the subband for the associated domain country string. The
	    default value of this attribute shall be zero."
::= { dot11MultiDomainCapabilityEntry 3}       
       
dot11MaximumTransmitPowerLevel OBJECT-TYPE
	SYNTAX Integer32
	MAX-ACCESS read-write
	STATUS current
       
	DESCRIPTION
	    "This attribute shall indicate the maximum transmit power, in dBm, allowed
	    in the subband for the associated domain country string. The default value
	    of this attribute shall be zero."
::= { dot11MultiDomainCapabilityEntry 4}
       
-- ********************************************************************
-- * End of dot11MultiDomainCapability TABLE
-- ********************************************************************

-- ********************************************************************
-- * dot11SpectrumManagement TABLE
-- ********************************************************************

dot11SpectrumManagementTable OBJECT-TYPE
	SYNTAX SEQUENCE OF Dot11SpectrumManagementEntry
	MAX-ACCESS not-accessible
	STATUS current
	DESCRIPTION
	    "(Conceptual) table of attributes for spectrum management"
::= {dot11smt 8}

dot11SpectrumManagementEntry OBJECT-TYPE
	SYNTAX Dot11SpectrumManagementEntry
	MAX-ACCESS not-accessible
	STATUS current
	DESCRIPTION
	    "An entry (conceptual row) in the Spectrum Management Table.
	    IfIndex - Each 802.11 interface is represented by an ifEntry.
	    Interface tables in this MIB are indexed by ifIndex."
	    INDEX {ifIndex, dot11SpectrumManagementIndex}
::= { dot11SpectrumManagementTable 1 }

Dot11SpectrumManagementEntry ::=
	SEQUENCE {
	    dot11SpectrumManagementIndex    Integer32,
	    dot11MitigationRequirement	    Integer32,
	    dot11ChannelSwitchTime	    Integer32,
	    dot11PowerCapabilityMax	    Integer32,
	    dot11PowerCapabilityMin	    Integer32 }

dot11SpectrumManagementIndex OBJECT-TYPE
	SYNTAX Integer32 (1..2147483647)
        MAX-ACCESS read-only
	STATUS current
	DESCRIPTION
	    "The auxiliary variable used to identify instances of the
	    columnar objects in the Spectrum Management Table."
::= { dot11SpectrumManagementEntry 1 }

dot11MitigationRequirement OBJECT-TYPE
	SYNTAX Integer32
	MAX-ACCESS read-write
	STATUS current
	DESCRIPTION
	    "This attribute shall indicate the mitigation requirement in dB
	    required. The default value of this attribute shall be 3 dB."
::= { dot11SpectrumManagementEntry 2 }

dot11ChannelSwitchTime OBJECT-TYPE
	SYNTAX Integer32
	MAX-ACCESS read-write
	STATUS current
	DESCRIPTION
	    "This attribute shall indicate assumed channel switch time,
	    measured in TUs. The unit of this attribute is TUs. The default
	    value of this attribute shall be 2 TUs. The minimum value shall
	    be 1 TU."
::= { dot11SpectrumManagementEntry 3 }

dot11PowerCapabilityMax OBJECT-TYPE
	SYNTAX Integer32
	MAX-ACCESS read-only
	STATUS current
	DESCRIPTION
	    "This attribute shall indicate the maximum transmit Power
	    Capability of this station. The unit of this attribute is dBm.
	    The default value of this attribute shall be 0 dBm."
::= { dot11SpectrumManagementEntry 4 }

dot11PowerCapabilityMin OBJECT-TYPE
	SYNTAX Integer32
	MAX-ACCESS read-only
	STATUS current
	DESCRIPTION
	    "This attribute shall indicate the minimum transmit Power
	    Capability of this station. The unit of this attribute is dBm.
	    The default value of this attribute shall be -100 dBm."
::= { dot11SpectrumManagementEntry 5 }

-- ******************************************************************
-- * End of dot11SpectrumManagement TABLE
-- ******************************************************************

-- **********************************************************************
-- *    MAC Attribute Templates
-- **********************************************************************

-- **********************************************************************
-- *    dot11OperationTable  TABLE
-- **********************************************************************
dot11OperationTable OBJECT-TYPE
        SYNTAX SEQUENCE OF Dot11OperationEntry
        MAX-ACCESS not-accessible
        STATUS current
        DESCRIPTION

            "Group contains MAC attributes pertaining to the operation
            of the MAC.  This has been implemented as a table in order
            to allow for multiple instantiations on an agent."

    ::= {  dot11mac 1 }

dot11OperationEntry OBJECT-TYPE
        SYNTAX Dot11OperationEntry
        MAX-ACCESS not-accessible
        STATUS current
        DESCRIPTION
            "An entry in the dot11OperationEntry Table.

            ifIndex - Each 802.11 interface is represented by an
            ifEntry.  Interface tables in this MIB module are indexed
            by ifIndex."
        INDEX {ifIndex}
    ::= {  dot11OperationTable 1 }

Dot11OperationEntry ::= SEQUENCE {
            dot11MACAddress			MacAddress,
            dot11RTSThreshold			INTEGER,
            dot11ShortRetryLimit		INTEGER,
            dot11LongRetryLimit			INTEGER,
            dot11FragmentationThreshold		INTEGER,
            dot11MaxTransmitMSDULifetime	Unsigned32,
            dot11MaxReceiveLifetime		Unsigned32,
            dot11ManufacturerID			DisplayString,
            dot11ProductID			DisplayString,
            dot11CAPLimit 	    		INTEGER,
	    dot11HCCWmin 	    		INTEGER,
	    dot11HCCWmax 	    		INTEGER,
	    dot11HCCAIFSN 	    		INTEGER,
	    dot11ADDBAResponseTimeout 		INTEGER,
	    dot11ADDTSResponseTimeout 		INTEGER,
	    dot11ChannelUtilizationBeaconInterval   INTEGER,
	    dot11ScheduleTimeout 		INTEGER,
	    dot11DLSResponseTimeout 		INTEGER,
	    dot11QAPMissingAckRetryLimit 	INTEGER,
	    dot11EDCAAveragingPeriod 		INTEGER,
	    dot11HTOperatingMode 		INTEGER,
	    dot11RIFSMode 	    		TruthValue,
	    dot11PSMPControlledAccess 		TruthValue,
	    dot11ServiceIntervalGranularity	INTEGER,
	    dot11DualCTSProtection 		TruthValue,
	    dot11LSigTxopFullProtectionEnabled	TruthValue,
	    dot11NonGFEntitiesPresent 		TruthValue,
	    dot11PCOActivated 	    		TruthValue,
	    dot11PCO40MaxDuration 		INTEGER,
	    dot11PCO20MaxDuration 		INTEGER,
	    dot11PCO40MinDuration 		INTEGER,
	    dot11PCO20MinDuration 		INTEGER }

dot11MACAddress OBJECT-TYPE
        SYNTAX MacAddress
        MAX-ACCESS read-only
        STATUS current
        DESCRIPTION
            "Unique MAC Address assigned to the STA."
    ::= {  dot11OperationEntry 1 }

dot11RTSThreshold OBJECT-TYPE
        SYNTAX INTEGER (0..65535)
        MAX-ACCESS read-write
        STATUS current

        DESCRIPTION
	    "This attribute shall indicate the number of octets in an PSDU,
	    below which an RTS/CTS handshake shall not be performed, except as
	    RTS/CTS is used as a cross modulation protection mechanism as
	    defined in 9.10. An RTS/CTS handshake shall be performed at the
	    beginning of any frame exchange sequence where the PSDU is of
	    type Data or Management, the PSDU has an individual address in
	    the Address1 field, and the length of the PSDU is greater than
	    this threshold. (For additional details, refer to Table 21 in 9.7.)
	    Setting this attribute to be larger than the maximum PSDU size
	    shall have the effect of turning off the RTS/CTS handshake for
	    frames of Data or Management type transmitted by this STA. Setting
	    this attribute to zero shall have the effect of turning on the RTS/
	    CTS handshake for all frames of Data or Management type transmitted
	    by this STA. The default value of this attribute shall be
	    65535."
        DEFVAL { 65535 }
    ::= {  dot11OperationEntry 2 }

dot11ShortRetryLimit OBJECT-TYPE
        SYNTAX INTEGER (1..255)
        MAX-ACCESS read-write
        STATUS current
        DESCRIPTION

	    "This attribute shall indicate the maximum number of
	    transmission attempts of a frame, the length of which is less
	    than or equal to dot11RTSThreshold, that shall be made before a
	    failure condition is indicated. The default value of this
	    attribute shall be 7."

    ::= {  dot11OperationEntry 3 }

dot11LongRetryLimit OBJECT-TYPE
        SYNTAX INTEGER (1..255)
        MAX-ACCESS read-write
        STATUS current
        DESCRIPTION

	    "This attribute shall indicate the maximum number of
	    transmission attempts of a frame, the length of which is
	    greater than dot11RTSThreshold, that shall be made before a
	    failure condition is indicated. The default value of this
	    attribute shall be 4."

    ::= {  dot11OperationEntry 4 }

dot11FragmentationThreshold OBJECT-TYPE
        SYNTAX INTEGER (256..8000)
        MAX-ACCESS read-write
        STATUS current
        DESCRIPTION

            "This attribute shall specify the current maximum size, in
	    octets, of the PSDU that may be delivered to the PHY.
	    This maximum size does not apply in the case of A-MPDU. An
	    MSDU, A-MSDU or MMPDU shall be broken into fragments if its
	    size exceeds the value of this attribute after adding MAC
	    headers and trailers. An MSDU, A-MSDU or MMPDU shall be
	    fragmented when the resulting frame has an individual address
	    in the Address1 field, and the length of the frame is larger
	    than this threshold. The default value for this attribute
	    shall be the lesser of 8000 or the aMPDUMaxLength or the
	    aPSDUMaxLength of the attached PHY and shall never exceed the
	    lesser of 8000 or the aMPDUMaxLength or the
	    aPSDUMaxLength of the attached PHY. The value of this
	    attribute shall never be less than 256."
    ::= {  dot11OperationEntry 5 }

dot11MaxTransmitMSDULifetime OBJECT-TYPE
        SYNTAX Unsigned32 (1..4294967295)
        MAX-ACCESS read-write
        STATUS current
        DESCRIPTION

	    "The MaxTransmitMSDULifetime shall be the elapsed time in TU,
	    after the initial transmission of an MSDU, after which further
	    attempts to transmit the MSDU shall be terminated. The default
	    value of this attribute shall be 512."

    ::= {  dot11OperationEntry 6 }

dot11MaxReceiveLifetime OBJECT-TYPE
        SYNTAX Unsigned32 (1..4294967295)
        MAX-ACCESS read-write
        STATUS current
        DESCRIPTION

            "The MaxReceiveLifetime shall be the elapsed time in TU,
            after the initial reception of a fragmented MMPDU or MSDU,
            after which further attempts to reassemble the MMPDU or
            MSDU shall be terminated. The default value shall be
            512."
    ::= {  dot11OperationEntry 7 }

dot11ManufacturerID OBJECT-TYPE
        SYNTAX DisplayString (SIZE(0..128))
        MAX-ACCESS read-only
        STATUS current
        DESCRIPTION

            "The ManufacturerID shall include, at a minimum, the name
            of the manufacturer.  It may include additional
            information at the manufacturer's discretion.  The default
            value of this attribute shall be null."

    ::= {  dot11OperationEntry 8 }

dot11ProductID OBJECT-TYPE
        SYNTAX DisplayString (SIZE(0..128))
        MAX-ACCESS read-only
        STATUS current
        DESCRIPTION

            "The ProductID shall include, at a minimum, an identifier
            that is unique to the manufacturer.  It may include
            additional information at the manufacturer's discretion.
            The default value of this attribute shall be null."

::= {  dot11OperationEntry 9 }

dot11CAPLimit OBJECT-TYPE
	SYNTAX INTEGER
	MAX-ACCESS read-write
	STATUS current
	DESCRIPTION
	    "This attribute shall specify the maximum number of TUs a
	    Controlled access phase(CAP) can last."
::= { dot11OperationEntry 10 }

dot11HCCWmin OBJECT-TYPE
	SYNTAX INTEGER (0..255)
	MAX-ACCESS read-write
	STATUS current
	DESCRIPTION
	    "This attribute shall specify the value of the minimum size of the
	    window that shall be used by the HC for generating a random number
	    for the backoff. The value of this attribute shall be such that it
	    could always be expressed in the form of 2X - 1, where X is an
	    integer. The default value of this attribute shall be 0."
        DEFVAL { 0 }
::= { dot11OperationEntry 11 }

dot11HCCWmax OBJECT-TYPE
	SYNTAX INTEGER (0..255)
	MAX-ACCESS read-write
	STATUS current
	DESCRIPTION
	    "This attribute shall specify the value of the maximum size of the
	    window that shall be used by the HC for generating a random number
	    for the backoff. The value of this attribute shall be such that it
	    could always be expressed in the form of 2X - 1, where X is an
	    integer. The default value of this attribute shall be 0." 
        DEFVAL { 0 }
::= { dot11OperationEntry 12 }

dot11HCCAIFSN OBJECT-TYPE
	SYNTAX INTEGER (1..15)
	MAX-ACCESS read-write
	STATUS current
	DESCRIPTION
	    "This attribute shall specify the number of slots, after a SIFS
	    duration, that the HC shall sense the medium idle either before
	    transmitting or executing a backoff. The default value of this
	    attribute shall be 1."
        DEFVAL { 1 }
::= { dot11OperationEntry 13 }

dot11ADDBAResponseTimeout OBJECT-TYPE
	SYNTAX INTEGER (1..65535)
	MAX-ACCESS read-write
	STATUS current
	DESCRIPTION
	    "This attribute shall specify the maximum number of seconds a BA is
	    to be responded. The default value of this attribute shall be 1."
        DEFVAL { 1 }
::= { dot11OperationEntry 14 }

dot11ADDTSResponseTimeout OBJECT-TYPE
	SYNTAX INTEGER (1..65535)
	MAX-ACCESS read-write
	STATUS current
	DESCRIPTION
	    "This attribute shall specify the maximum number of seconds an
	    ADDTS request is to be responded. The default value of this
	    attribute shall be 1."
        DEFVAL { 1 }
::= { dot11OperationEntry 15 }

dot11ChannelUtilizationBeaconInterval OBJECT-TYPE
	SYNTAX INTEGER (1..100)
	MAX-ACCESS read-write
	STATUS current
	DESCRIPTION
	    "This attribute shall indicate the number of beacon intervals over
	    which the channel busy time should be averaged. The default value
	    for this parameter shall be 50."
        DEFVAL { 50 }
::= { dot11OperationEntry 16 }

dot11ScheduleTimeout OBJECT-TYPE
	SYNTAX INTEGER (1..100)
	MAX-ACCESS read-write
	STATUS current
	DESCRIPTION
	    "This attribute shall indicate the duration in TUs after which a
	    STA could go into power-save mode. The default value for this
	    parameter shall be 10."
        DEFVAL { 10 }
::= { dot11OperationEntry 17 }

dot11DLSResponseTimeout OBJECT-TYPE
	SYNTAX INTEGER (1..65535)
	MAX-ACCESS read-write
	STATUS current
	DESCRIPTION
	    "This attribute shall specify the maximum number of seconds a
	    direct link request is to be responded. The default value of this
	    attribute shall be 10."
        DEFVAL { 10 }
::= { dot11OperationEntry 18 }

dot11QAPMissingAckRetryLimit OBJECT-TYPE
	SYNTAX INTEGER (1..100)
	MAX-ACCESS read-write
	STATUS current
	DESCRIPTION
	    "This attribute indicates the number of times the QAP may retry a
	    frame for which it does not receive an ACK for a STA in power-save
	    mode after receiving a PS-Poll and sending a directed response or
	    after the QAP does not receive an ACK to a directed MPDU sent with
	    the EOSP set to 1."
::= { dot11OperationEntry 19 }

dot11EDCAAveragingPeriod OBJECT-TYPE
	SYNTAX INTEGER (1..100)
	MAX-ACCESS read-write
	STATUS current
	DESCRIPTION
	    "This attribute shall indicate the number of seconds over which
	    the admitted_time and used_time are computed. The default value
	    for this parameter shall be 5."
        DEFVAL { 5 }
::= { dot11OperationEntry 20 }

dot11HTOperatingMode OBJECT-TYPE
	SYNTAX INTEGER { htPure (0), optionalProtection (1),
	    mandatoryFortyProtection (2), mandatoryAllProtection (3) }
	MAX-ACCESS read-write
	STATUS current
	DESCRIPTION
	    "This attribute indicates the level of protection that needs
	    to be provided to the transmissions in an IEEE 802.11 network with HT STAs.
	    The default value of this attribute is 0."
        DEFVAL { 0 }
::= { dot11OperationEntry 21 }

dot11RIFSMode OBJECT-TYPE
	SYNTAX TruthValue
	MAX-ACCESS read-write
	STATUS current
	DESCRIPTION
	    "This attribute, when TRUE, indicates that RIFS mode is
	    allowed in the BSS. The default value of this attribute is FALSE."
        DEFVAL { false }
::= { dot11OperationEntry 22 }

dot11PSMPControlledAccess OBJECT-TYPE
	SYNTAX TruthValue
	MAX-ACCESS read-write
	STATUS current
	DESCRIPTION
	    "This attribute, when TRUE indicates that the AP accepts
	    associations only from stations for which dot11PSMPOptionImplemented is
	    TRUE. The default value of this attribute is FALSE."
        DEFVAL { false }
::= { dot11OperationEntry 23 }

dot11ServiceIntervalGranularity OBJECT-TYPE
	SYNTAX INTEGER (0..7)
	MAX-ACCESS read-write
	STATUS current
	DESCRIPTION
	    "This attribute indicates the Service Interval Granularity to
	    be used for scheduled PSMP. The value of the granularity is given by
	    (dot11ServiceIntervalGranularity+1)*5 milliseconds. The default value of
	    this attribute is 0."
        DEFVAL { 0 }
::= { dot11OperationEntry 24 }

dot11DualCTSProtection OBJECT-TYPE
	SYNTAX TruthValue
	MAX-ACCESS read-write
	STATUS current
	DESCRIPTION
	    "This attribute, when TRUE indicates that the AP uses dual CTS
	    protection to protect the non-STBC frame and STBC frame transmissions. The
	    default value of this attribute is FALSE."
        DEFVAL { false }
::= { dot11OperationEntry 25 }
		
dot11LSigTxopFullProtectionEnabled OBJECT-TYPE
	SYNTAX TruthValue
	MAX-ACCESS read-write
	STATUS current
	DESCRIPTION
	    "This attribute, when TRUE, indicates that the LSIG TXOP
	    Protection may be used by stations that have the attribute
	    dot11LSigTxopProtectionOptionImplemented set to TRUE. The default value of
	    this attribute is FALSE."
        DEFVAL { false }
::= { dot11OperationEntry 26 }

dot11NonGFEntitiesPresent OBJECT-TYPE
	SYNTAX TruthValue
	MAX-ACCESS read-write
	STATUS current
	DESCRIPTION
	    "This attribute, when TRUE, indicates that STA that are not
	    Greenfield Capable are present in the BSS. The default value of this
	    attribute is FALSE."
        DEFVAL { false }
::= { dot11OperationEntry 27 }

dot11PCOActivated OBJECT-TYPE
	SYNTAX TruthValue
	MAX-ACCESS read-write
	STATUS current
	DESCRIPTION
	    "This attribute, when TRUE, indicates that the PCO is
	    activated. The default value of this attribute is FALSE."
        DEFVAL { false }
::= { dot11OperationEntry 28 }

dot11PCO40MaxDuration OBJECT-TYPE
	SYNTAX INTEGER (1..65535)
	MAX-ACCESS read-write
	STATUS current
	DESCRIPTION
	    "The attribute indicates the maximum duration of 40 MHz phase in TU under PCO
	    operation. The default value of this attribute shall be 60. The value of this
	    attribute shall be equal to or larger than dot11PCO40MinDuration."
        DEFVAL { 60 }
::= { dot11OperationEntry 29 }

dot11PCO20MaxDuration OBJECT-TYPE
	SYNTAX INTEGER (1..65535)
	MAX-ACCESS read-write
	STATUS current
	DESCRIPTION
	    "The attribute indicates the maximum duration of 20 MHz phase in TU under PCO
	    operation. The default value of this attribute shall be 60. The value of this
	    attribute shall be equal to or larger than dot11PCO20MinDuration."
        DEFVAL { 60 }
::= { dot11OperationEntry 30 }

dot11PCO40MinDuration OBJECT-TYPE
	SYNTAX INTEGER (1..65535)
	MAX-ACCESS read-write
	STATUS current
	DESCRIPTION
	    "The attribute indicates the minimum duration of 40 MHz phase in TU under PCO
	    operation. The default value of this attribute shall be 40."
        DEFVAL { 40 }
::= { dot11OperationEntry 31 }

dot11PCO20MinDuration OBJECT-TYPE
	SYNTAX INTEGER (1..65535)
	MAX-ACCESS read-write
	STATUS current
	DESCRIPTION
	    "The attribute indicates the minimum duration of 20 MHz phase in TU under PCO
	    operation. The default value of this attribute shall be 40."
        DEFVAL { 40 }
::= { dot11OperationEntry 32 }
		
-- **********************************************************************
-- *    End of dot11OperationEntry  TABLE
-- **********************************************************************

-- **********************************************************************
-- *    dot11Counters TABLE
-- **********************************************************************
dot11CountersTable OBJECT-TYPE
        SYNTAX SEQUENCE OF Dot11CountersEntry
        MAX-ACCESS not-accessible
        STATUS current
        DESCRIPTION

            "Group containing attributes that are MAC counters.
            Implemented as a table to allow for multiple
            instantiations on an agent."

    ::= {  dot11mac 2 }

dot11CountersEntry OBJECT-TYPE
        SYNTAX	    Dot11CountersEntry
        MAX-ACCESS  not-accessible
        STATUS	    current
        DESCRIPTION
            "An entry in the dot11CountersEntry Table.

            ifIndex - Each 802.11 interface is represented by an
            ifEntry.  Interface tables in this MIB module are indexed
            by ifIndex."
        INDEX {ifIndex}
    ::= {  dot11CountersTable 1 }

Dot11CountersEntry ::= SEQUENCE {
            dot11TransmittedFragmentCount	Counter32,
            dot11MulticastTransmittedFrameCount	Counter32,
            dot11FailedCount			Counter32,
            dot11RetryCount			Counter32,
            dot11MultipleRetryCount		Counter32,
            dot11FrameDuplicateCount		Counter32,
            dot11RTSSuccessCount		Counter32,
            dot11RTSFailureCount		Counter32,
            dot11ACKFailureCount		Counter32,
            dot11ReceivedFragmentCount		Counter32,
            dot11MulticastReceivedFrameCount	Counter32,
            dot11FCSErrorCount			Counter32,
	    dot11TransmittedFrameCount		Counter32,
	    dot11WEPUndecryptableCount		Counter32,
	    dot11QosDiscardedFragmentCount 	Counter32,
	    dot11AssociatedStationCount 	Counter32,
	    dot11QosCFPollsReceivedCount 	Counter32,
	    dot11QosCFPollsUnusedCount 		Counter32,
	    dot11QosCFPollsUnusableCount 	Counter32,
	    dot11TransmittedAMSDUCount		Counter32,
	    dot11FailedAMSDUCount	    	Counter32,
	    dot11RetryAMSDUCount	    	Counter32,
	    dot11MultipleRetryAMSDUCount	Counter32,
	    dot11TransmittedOctetsInAMSDUCount	Counter64,
	    dot11AMSDUAckFailureCount 		Counter32,
	    dot11ReceivedAMSDUCount	    	Counter32,
	    dot11ReceivedOctetsInAMSDUCount	Counter64,
	    dot11TransmittedAMPDUCount		Counter32,
	    dot11TransmittedMPDUsInAMPDUCount	Counter32,
	    dot11TransmittedOctetsInAMPDUCount	Counter64,
	    dot11AMPDUReceivedCount	    	Counter32,
	    dot11MPDUInReceivedAMPDUCount	Counter32,
	    dot11ReceivedOctetsInAMPDUCount	Counter64,
	    dot11AMPDUDelimiterCRCErrorCount	Counter32,
	    dot11ImplicitBARFailureCount	Counter32,
	    dot11ExplicitBARFailureCount	Counter32,
	    dot11ChannelWidthSwitchCount	Counter32,
	    dot11TwentyMHzFrameTransmittedCount	Counter32,
	    dot11FortyMHzFrameTransmittedCount	Counter32,
	    dot11TwentyMHzFrameReceivedCount	Counter32,
	    dot11FortyMHzFrameReceivedCount	Counter32,
	    dot11PSMPSuccessCount	    	Counter32,
	    dot11PSMPFailureCount	    	Counter32,
	    dot11GrantedRDGUsedCount		Counter32,
	    dot11GrantedRDGUnusedCount		Counter32,
	    dot11TransmittedFramesInGrantedRDGCount	Counter32,
	    dot11TransmittedOctetsInGrantedRDGCount	Counter64,
	    dot11BeamformingFrameCount		Counter32,
	    dot11DualCTSSuccessCount		Counter32,
	    dot11DualCTSFailureCount		Counter32,
	    dot11STBCCTSSuccessCount		Counter32,
	    dot11STBCCTSFailureCount		Counter32,
	    dot11nonSTBCCTSSuccessCount		Counter32,
	    dot11nonSTBCCTSFailureCount		Counter32,
	    dot11RTSLSIGSuccessCount		Counter32,
	    dot11RTSLSIGFailureCount		Counter32 }

dot11TransmittedFragmentCount OBJECT-TYPE
        SYNTAX Counter32
        MAX-ACCESS read-only
        STATUS current
        DESCRIPTION

            "This counter shall be incremented for an acknowledged MPDU
            with an individual address in the address 1 field or an MPDU
            with a multicast address in the address 1 field of type Data
            or Management."

    ::= {  dot11CountersEntry 1 }

dot11MulticastTransmittedFrameCount OBJECT-TYPE
        SYNTAX Counter32
        MAX-ACCESS read-only
        STATUS current
        DESCRIPTION

            " This counter shall increment only when the multicast bit
            is set in the destination MAC address of a successfully
            transmitted MSDU.  When operating as a STA in an ESS, where
            these frames are directed to the AP, this implies having
            received an acknowledgment to all associated MPDUs. "

    ::= {  dot11CountersEntry 2 }

dot11FailedCount OBJECT-TYPE
        SYNTAX Counter32
        MAX-ACCESS read-only
        STATUS current
        DESCRIPTION

	    "This counter shall increment when an MSDU is not transmitted
	    successfully due to the number of transmit attempts exceeding
	    either the  dot11ShortRetryLimit or dot11LongRetryLimit. "

    ::= {  dot11CountersEntry 3 }

dot11RetryCount OBJECT-TYPE
        SYNTAX Counter32
        MAX-ACCESS read-only
        STATUS current
        DESCRIPTION

            "This counter shall increment when an MSDU is successfully
            transmitted after one or more retransmissions."
    ::= {  dot11CountersEntry 4 }

dot11MultipleRetryCount OBJECT-TYPE
        SYNTAX Counter32
        MAX-ACCESS read-only
        STATUS current
        DESCRIPTION

            "This counter shall increment when an MSDU is successfully
            transmitted after more than one retransmission."

    ::= {  dot11CountersEntry 5 }

dot11FrameDuplicateCount  OBJECT-TYPE
        SYNTAX Counter32
        MAX-ACCESS read-only
        STATUS current
        DESCRIPTION

            "This counter shall increment when a frame is received
            that the Sequence Control field indicates is a
            duplicate."

    ::= {  dot11CountersEntry 6 }

dot11RTSSuccessCount OBJECT-TYPE
        SYNTAX Counter32
        MAX-ACCESS read-only
        STATUS current
        DESCRIPTION

            "This counter shall increment when a CTS is received in
            response to an RTS."
 ::= {  dot11CountersEntry 7 }

dot11RTSFailureCount OBJECT-TYPE
        SYNTAX Counter32
        MAX-ACCESS read-only
        STATUS current
        DESCRIPTION


	    "This counter shall increment when a CTS is not received in
	    response to an RTS."

    ::= { dot11CountersEntry 8 }

dot11ACKFailureCount OBJECT-TYPE
        SYNTAX Counter32
        MAX-ACCESS read-only
        STATUS current
        DESCRIPTION

            "This counter shall increment when an ACK is not received
            when expected."

    ::= {  dot11CountersEntry 9 }

dot11ReceivedFragmentCount OBJECT-TYPE
        SYNTAX Counter32
        MAX-ACCESS read-only
        STATUS current
        DESCRIPTION

            "This counter shall be incremented for each successfully
            received MPDU of type Data or Management."

    ::= {  dot11CountersEntry 10 }

dot11MulticastReceivedFrameCount OBJECT-TYPE
        SYNTAX Counter32
        MAX-ACCESS read-only
        STATUS current
        DESCRIPTION

            "This counter shall increment when a MSDU is received
            with the multicast bit set in the destination
            MAC address."
    ::= {  dot11CountersEntry 11 }

dot11FCSErrorCount OBJECT-TYPE
        SYNTAX Counter32
        MAX-ACCESS read-only
        STATUS current
        DESCRIPTION

            "This counter shall increment when an FCS error is
            detected in a received MPDU."

::= {  dot11CountersEntry 12 }

dot11TransmittedFrameCount OBJECT-TYPE
        SYNTAX Counter32
        MAX-ACCESS read-only
        STATUS current
        DESCRIPTION

"This counter shall increment for each successfully transmitted MSDU."

::= {  dot11CountersEntry 13 }

dot11WEPUndecryptableCount OBJECT-TYPE
        SYNTAX	    Counter32
        MAX-ACCESS  read-only
        STATUS	    current
        DESCRIPTION

	    "This counter shall increment when a frame is received with
	    the Protected Frame subfield of the Frame Control field set 
	    to one and the WEPOn value for the key mapped to the TA's MAC address
	    indicates that the frame should not have been encrypted or
	    that frame is discarded due to the receiving STA not
	    implementing the privacy option."

::= { dot11CountersEntry 14 }

dot11QosDiscardedFragmentCount OBJECT-TYPE
	SYNTAX Counter32
	MAX-ACCESS read-only
	STATUS current
	DESCRIPTION
	    "This counter shall increment for each QoS Data MPDU that has been
	    discarded."
::= { dot11CountersEntry 15 }

dot11AssociatedStationCount OBJECT-TYPE
	SYNTAX Counter32
	MAX-ACCESS read-only
	STATUS current
	DESCRIPTION
	    "This counter, only available at QAP, shall increment when a
	    station associates or reassociates. This counter shall decrement
	    when a station disassociates."
::= { dot11CountersEntry 16 }

dot11QosCFPollsReceivedCount OBJECT-TYPE
	SYNTAX Counter32
	MAX-ACCESS read-only
	STATUS current
	DESCRIPTION
	    "This counter shall increment for each QoS (+)CF-Poll that has been
	    received."
::= { dot11CountersEntry 17 }

dot11QosCFPollsUnusedCount OBJECT-TYPE
	SYNTAX Counter32
	MAX-ACCESS read-only
	STATUS current
	DESCRIPTION
	    "This counter shall increment for each QoS (+)CF-Poll that has been
	    received but not used."
::= { dot11CountersEntry 18 }

dot11QosCFPollsUnusableCount OBJECT-TYPE
	SYNTAX Counter32
	MAX-ACCESS read-only
	STATUS current
	DESCRIPTION
	    "This counter shall increment for each QoS (+)CF-Poll that has been
	    received but could not be used due to the TXOP size being smaller
	    than the time that is required for one frame exchange sequence."
::= { dot11CountersEntry 19 }

dot11TransmittedAMSDUCount OBJECT-TYPE
	SYNTAX Counter32
	MAX-ACCESS read-only
	STATUS current
	DESCRIPTION
	    "This counter shall be incremented for an acknowledged A-MSDU
	    frame with an individual address in the address 1 field or an AMSDU frame
	    with a multicast address in the address 1 field."
::= { dot11CountersEntry 21 }

dot11FailedAMSDUCount OBJECT-TYPE
	SYNTAX Counter32
	MAX-ACCESS read-only
	STATUS current
	DESCRIPTION
	    "This counter shall be incremented when an A-MSDU is not
	    transmitted successfully due to the number of transmit attempts exceeding
	    either the dot11ShortRetryLimit or dot11LongRetryLimit."  
::= { dot11CountersEntry 22 }

dot11RetryAMSDUCount OBJECT-TYPE
	SYNTAX Counter32
	MAX-ACCESS read-only
	STATUS current
	DESCRIPTION
	    "This counter shall be incremented when an A-MSDU is
	    successfully transmitted after one or more retransmissions."
::= { dot11CountersEntry 23 }

dot11MultipleRetryAMSDUCount OBJECT-TYPE
	SYNTAX Counter32
	MAX-ACCESS read-only
	STATUS current
	DESCRIPTION
	    "This counter shall be incremented when an A-MSDU is
	    successfully transmitted after more than one retransmission."
::= { dot11CountersEntry 24 }

dot11TransmittedOctetsInAMSDUCount OBJECT-TYPE
	SYNTAX Counter64
	MAX-ACCESS read-only
	STATUS current
	DESCRIPTION
	    "This counter shall be incremented by the number of octets in
	    the framebody of an A-MSDU frame when an A-MSDU frame is successfully
	    transmitted."
::= { dot11CountersEntry 25 }

dot11AMSDUAckFailureCount OBJECT-TYPE
	SYNTAX Counter32
	MAX-ACCESS read-only
	STATUS current
	DESCRIPTION
	    "This counter shall be incremented when an acknowledgement to
	    an AMSDU is not received when expected. This acknowledgement can be in an ACK
	    or the BlockAck frame."
::= { dot11CountersEntry 26 }

dot11ReceivedAMSDUCount OBJECT-TYPE
	SYNTAX Counter32
	MAX-ACCESS read-only
	STATUS current
	DESCRIPTION
	    "This counter shall be incremented for a received A-MSDU frame
	    with the station's MAC address in the address 1 field or an AMSDU frame with
	    a multicast address in the address 1 field."
::= { dot11CountersEntry 27 }

dot11ReceivedOctetsInAMSDUCount OBJECT-TYPE
	SYNTAX Counter64
	MAX-ACCESS read-only
	STATUS current
	DESCRIPTION
	    "This counter shall be incremented by the number of octets in
	    the framebody of an A-MSDU frame when an A-MSDU frame is received."
::= { dot11CountersEntry 28 }

dot11TransmittedAMPDUCount OBJECT-TYPE
	SYNTAX Counter32
	MAX-ACCESS read-only
	STATUS current
	DESCRIPTION
	    "This counter shall be incremented when an A-MPDU is
	    transmitted."
::= { dot11CountersEntry 29 }

dot11TransmittedMPDUsInAMPDUCount OBJECT-TYPE
	SYNTAX Counter32
	MAX-ACCESS read-only
	STATUS current
	DESCRIPTION
	    "This counter shall increment by the number of MPDUs in the AMPDU
	    when an A-MPDU is transmitted."
::= { dot11CountersEntry 30 }

dot11TransmittedOctetsInAMPDUCount OBJECT-TYPE
	SYNTAX Counter64
	MAX-ACCESS read-only
	STATUS current
	DESCRIPTION
	    "This counter shall be incremented by the number of octets in
	    the A-MPDU frame when an A-MPDU frame is transmitted."
::= { dot11CountersEntry 31 }

dot11AMPDUReceivedCount OBJECT-TYPE
	SYNTAX Counter32
	MAX-ACCESS read-only
	STATUS current
	DESCRIPTION
	    "This counter shall be incremented when the MAC receives an AMPDU
	    from the PHY."
::= { dot11CountersEntry 32 }

dot11MPDUInReceivedAMPDUCount OBJECT-TYPE
	SYNTAX Counter32
	MAX-ACCESS read-only
	STATUS current
	DESCRIPTION
	    "This counter shall be incremented by the number of MPDUs
	    received in the A-MPDU when an A-MPDU is received."
::= { dot11CountersEntry 33 }

dot11ReceivedOctetsInAMPDUCount OBJECT-TYPE
	SYNTAX Counter64
	MAX-ACCESS read-only
	STATUS current
	DESCRIPTION
	    "This counter shall be incremented by the number of octets in
	    the A-MPDU frame when an A-MPDU frame is received."
::= { dot11CountersEntry 34 }

dot11AMPDUDelimiterCRCErrorCount OBJECT-TYPE
	SYNTAX Counter32
	MAX-ACCESS read-only
	STATUS current
	DESCRIPTION
	    "This counter shall be incremented when an A-MPDU delimiter
	    has CRC error when this is the first CRC error in the received A-MPDU or when
	    the previous delimiter has been decoded correctly."
::= { dot11CountersEntry 35 }

dot11ImplicitBARFailureCount OBJECT-TYPE
	SYNTAX Counter32
	MAX-ACCESS read-only
	STATUS current
	DESCRIPTION
	    "This counter shall be incremented when the expected BlockAck
	    is not received in response to an Implicit BlockAckReq frame."
::= { dot11CountersEntry 36 }

dot11ExplicitBARFailureCount OBJECT-TYPE
	SYNTAX Counter32
	MAX-ACCESS read-only
	STATUS current
	DESCRIPTION
	    "This counter shall be incremented when the expected BlockAck
	    is not received in response to an Explicit BlockAckReq."
::= { dot11CountersEntry 37 }

dot11ChannelWidthSwitchCount OBJECT-TYPE
	SYNTAX Counter32
	MAX-ACCESS read-only
	STATUS current
	DESCRIPTION
	    "This counter shall be increment when the bandwidth used is
	    switched from 20 to 40 or vice-versa."
::= { dot11CountersEntry 38 }

dot11TwentyMHzFrameTransmittedCount OBJECT-TYPE
	SYNTAX Counter32
	MAX-ACCESS read-only
	STATUS current
	DESCRIPTION
	    "This counter shall be incremented when a Frame is transmitted
	    only on the primary channel."
::= { dot11CountersEntry 39 }

dot11FortyMHzFrameTransmittedCount OBJECT-TYPE
	SYNTAX Counter32
	MAX-ACCESS read-only
	STATUS current
	DESCRIPTION
	    "This counter shall be incremented when a Frame is transmitted
	    on both control and secondary channels."
::= { dot11CountersEntry 40 }

dot11TwentyMHzFrameReceivedCount OBJECT-TYPE
	SYNTAX Counter32
	MAX-ACCESS read-only
	STATUS current
	DESCRIPTION
	    "This counter shall be incremented when a Frame is received
	    only on the primary channel."
::= { dot11CountersEntry 41 }        

dot11FortyMHzFrameReceivedCount OBJECT-TYPE
	SYNTAX Counter32
	MAX-ACCESS read-only
	STATUS current
	DESCRIPTION
	    "This counter shall be incremented when a Frame is received on
	    both the control and secondary channels."
::= { dot11CountersEntry 42 }

dot11PSMPSuccessCount OBJECT-TYPE
	SYNTAX Counter32
	MAX-ACCESS read-only
	STATUS current
	DESCRIPTION
	    "This counter shall be incremented when an allocated PSMP-UTT
	    is used."
::= { dot11CountersEntry 43 }

dot11PSMPFailureCount OBJECT-TYPE
	SYNTAX Counter32
	MAX-ACCESS read-only
	STATUS current
	DESCRIPTION
	    "This counter shall be incremented when an allocated PSMP-UTT
	    is not used."
::= { dot11CountersEntry 44 }

dot11GrantedRDGUsedCount OBJECT-TYPE
	SYNTAX Counter32
	MAX-ACCESS read-only
	STATUS current
	DESCRIPTION
	    "This counter at the RD initiator shall be incremented when an
	    allocated RDG is used by the station, apart from transmitting a response
	    frame such as ACK or Block Ack frames."
::= { dot11CountersEntry 45 }

dot11GrantedRDGUnusedCount OBJECT-TYPE
	SYNTAX Counter32
	MAX-ACCESS read-only
	STATUS current
	DESCRIPTION
	    "This counter at the initiatior shall be incremented when an
	    allocated RDG is not used by the station, apart from transmitting a response
	    frame such as ACK or Block Ack frames."
::= { dot11CountersEntry 46 }

dot11TransmittedFramesInGrantedRDGCount OBJECT-TYPE
	SYNTAX Counter32
	MAX-ACCESS read-only
	STATUS current
	DESCRIPTION
	    "This counter at the initiatior shall be incremented for every
	    frame, other than response frames such as ACK or Block Ack frames,
	    transmitted by the station during a granted RDG."
::= { dot11CountersEntry 47 }

dot11TransmittedOctetsInGrantedRDGCount OBJECT-TYPE
	SYNTAX Counter64
	MAX-ACCESS read-only
	STATUS current
 	DESCRIPTION
	    "This counter at the initiatior shall be incremented by the
	    number of octets in the framebody of a frame, other than response frames such
	    as ACK or Block Ack frames, transmitted by the station during a granted RDG."
::= { dot11CountersEntry 48 }

dot11BeamformingFrameCount OBJECT-TYPE
	SYNTAX Counter32
	MAX-ACCESS read-only
	STATUS current
	DESCRIPTION
	    "This counter shall be incremented when th transmitter sends a
	    frame with new/updated beam forming parameters."
::= { dot11CountersEntry 49 }

dot11DualCTSSuccessCount OBJECT-TYPE
	SYNTAX Counter32
	MAX-ACCESS read-only
	STATUS current
	DESCRIPTION
	    "This counter shall be incremented when AP sends a dual CTS in
	    response to a STA initiating TXOP in extended range."
::= { dot11CountersEntry 50 }

dot11DualCTSFailureCount OBJECT-TYPE
	SYNTAX Counter32
	MAX-ACCESS read-only
	STATUS current
	DESCRIPTION
	    "This counter shall be incremented when AP fails to send a
	    dual CTS in response to a STA initiating TXOP in extended range."
::= { dot11CountersEntry 51 }

dot11STBCCTSSuccessCount OBJECT-TYPE
	SYNTAX Counter32
	MAX-ACCESS read-only
	STATUS current
	DESCRIPTION
	    "This counter shall be incremented when AP does not detect a
	    collision PIFS after sending a CTS to self STBC frame in extended range."
::= { dot11CountersEntry 52 }

dot11STBCCTSFailureCount OBJECT-TYPE
	SYNTAX Counter32
	MAX-ACCESS read-only
	STATUS current
	DESCRIPTION
	    "This counter shall be incremented when AP detects a collision
	    PIFS after sending a CTS to self STBC frame in extended range."
::= { dot11CountersEntry 53 }

dot11nonSTBCCTSSuccessCount OBJECT-TYPE
	SYNTAX Counter32
	MAX-ACCESS read-only
	STATUS current
	DESCRIPTION
	    "This counter shall be incremented when AP does not detect a
	    collision PIFS after sending a CTS to self that is an non-STBC frame in
	    extended range."
::= { dot11CountersEntry 54 }

dot11nonSTBCCTSFailureCount OBJECT-TYPE
	SYNTAX Counter32
	MAX-ACCESS read-only
	STATUS current
	DESCRIPTION
	    "This counter shall be incremented when AP detects a collision
	    PIFS after sending a CTS to self that is an non-STBC frame in extended
	    range."
::= { dot11CountersEntry 55 }

dot11RTSLSIGSuccessCount OBJECT-TYPE
	SYNTAX Counter32
	MAX-ACCESS read-only
	STATUS current
	DESCRIPTION
	    "This counter shall be incremented when the duration/ID field
	    is set according to the rules of EPP in the received CTS following a
	    transmission of RTS in EPP mode."
::= { dot11CountersEntry 56 }

dot11RTSLSIGFailureCount OBJECT-TYPE
	SYNTAX Counter32
	MAX-ACCESS read-only
	STATUS current
	DESCRIPTION
	    "This counter shall be incremented when the duration/ID field
	    is not set according to the rules of EPP in the received CTS following a
	    transmission of RTS in EPP mode."
::= { dot11CountersEntry 57 }

-- **********************************************************************
-- *    End of dot11CountersEntry  TABLE
-- **********************************************************************

-- **********************************************************************
-- *    GroupAddresses  TABLE
-- **********************************************************************

dot11GroupAddressesTable OBJECT-TYPE
        SYNTAX SEQUENCE OF Dot11GroupAddressesEntry
        MAX-ACCESS not-accessible
        STATUS current
        DESCRIPTION

            "A conceptual table containing a set of MAC addresses
            identifying the multicast addresses for which this STA
            will receive frames.  The default value of this attribute
            shall be null."

    ::= {  dot11mac 3 }

dot11GroupAddressesEntry OBJECT-TYPE
        SYNTAX Dot11GroupAddressesEntry
        MAX-ACCESS not-accessible
        STATUS current
        DESCRIPTION
            "An Entry (conceptual row) in the Group Addresses Table.

            ifIndex - Each 802.11 interface is represented by an
            ifEntry.  Interface tables in this MIB module are indexed
            by ifIndex."
        INDEX {ifIndex, dot11GroupAddressesIndex}
    ::= {  dot11GroupAddressesTable  1 }

Dot11GroupAddressesEntry ::= SEQUENCE {
            dot11GroupAddressesIndex    Integer32,
            dot11Address                MacAddress,
            dot11GroupAddressesStatus   RowStatus}

dot11GroupAddressesIndex OBJECT-TYPE
        SYNTAX Integer32 (1..2147483647)
        MAX-ACCESS read-only
        STATUS current
        DESCRIPTION
            "The auxiliary variable used to identify instances
            of the columnar objects in the Group Addresses Table."
    ::= {  dot11GroupAddressesEntry 1 }

dot11Address OBJECT-TYPE
        SYNTAX MacAddress
        MAX-ACCESS read-create
        STATUS current
        DESCRIPTION
            "MAC address identifying a multicast addresses
            from which this STA will receive frames."
    ::= {  dot11GroupAddressesEntry 2 }

dot11GroupAddressesStatus OBJECT-TYPE
        SYNTAX RowStatus
        MAX-ACCESS read-create
        STATUS current
        DESCRIPTION

            "The status column used for creating, modifying, and
            deleting instances of the columnar objects in the Group
            Addresses Table."

        DEFVAL {active}
    ::= {  dot11GroupAddressesEntry 3 }

-- **********************************************************************
-- *    End of GroupAddress  TABLE
-- **********************************************************************

-- **********************************************************************
-- * SMT EDCA Config TABLE
-- **********************************************************************
dot11EDCATable OBJECT-TYPE
	SYNTAX SEQUENCE OF Dot11EDCATableEntry
	MAX-ACCESS not-accessible
	STATUS current
	DESCRIPTION
	    "Conceptual table for EDCA default parameter values at a non-AP
	    QSTA. This table shall contain the four entries of the EDCA
	    parameters corresponding to four possible ACs. Index 1 corresponds
	    to AC_BK, index 2 to AC_BE, index 3 to AC_VI, and index 4 to AC_VO."
		REFERENCE
	    "IEEE 802.11 Tge Draft Version, 9.1.3.1"
    ::= { dot11mac 4 }

dot11EDCATableEntry OBJECT-TYPE
	SYNTAX Dot11EDCATableEntry
	MAX-ACCESS not-accessible
	STATUS current
	DESCRIPTION
	    "An Entry (conceptual row) in the EDCA Table.
	    ifIndex - Each IEEE 802.11 interface is represented by an ifEntry.
	    Interface tables in this MIB module are indexed by ifIndex."
	INDEX { ifIndex,
	    dot11EDCATableIndex }
    ::= { dot11EDCATable 1 }

Dot11EDCATableEntry ::= SEQUENCE { 
	    dot11EDCATableIndex		INTEGER,
	    dot11EDCATableCWmin		INTEGER,
	    dot11EDCATableCWmax		INTEGER,
	    dot11EDCATableAIFSN		INTEGER,
	    dot11EDCATableTXOPLimit	INTEGER,
	    dot11EDCATableMSDULifetime	INTEGER,
	    dot11EDCATableMandatory	TruthValue }

dot11EDCATableIndex OBJECT-TYPE
	SYNTAX INTEGER (1..4)
        MAX-ACCESS read-only
	STATUS current
	DESCRIPTION
	    "The auxiliary variable used to identify instances of the columnar
	    objects in the EDCA Table. The value of this variable is
	    1) 1, if the value of the AC is AC_BK.
	    2) 2, if the value of the AC is AC_BE.
	    3) 3, if the value of the AC is AC_VI.
	    4) 4, if the value of the AC is AC_VO."
    ::= { dot11EDCATableEntry 1 }

dot11EDCATableCWmin OBJECT-TYPE
	SYNTAX INTEGER (0..255)
	MAX-ACCESS read-write
	STATUS current
	DESCRIPTION
	    "This attribute shall specify the value of the minimum size of the
	    window that shall be used by a QSTA for a particular AC for
	    generating a random number for the backoff. The value of this
	    attribute shall be such that it could always be expressed in the
	    form of 2X - 1, where X is an integer. The default value for this
	    attribute is
	    1) aCWmin, if dot11EDCATableIndex is 1 or 2.
	    2) (aCWmin+1)/2 - 1, if dot11EDCATableIndex is 3.
	    3) (aCWmin+1)/4 - 1, if dot11EDCATableIndex is 4."
    ::= { dot11EDCATableEntry 2 }

dot11EDCATableCWmax OBJECT-TYPE
	SYNTAX INTEGER (0..65535)
	MAX-ACCESS read-write
	STATUS current
	DESCRIPTION
	    "This attribute shall specify the value of the maximum size of the
	    window that shall be used by a QSTA for a particular AC for
	    generating a random number for the backoff. The value of this
	    attribute shall be such that it could always be expressed in the
	    form of 2X - 1, where X is an integer. The default value for this
	    attribute is
	    1) aCWmax, if dot11EDCATableIndex is 1 or 2.
	    2) aCWmin, if dot11EDCATableIndex is 3.
	    3) (aCWmin+1)/2 - 1, if dot11EDCATableIndex is 4."
    ::= { dot11EDCATableEntry 3 }

dot11EDCATableAIFSN OBJECT-TYPE
	SYNTAX INTEGER (2..15)
	MAX-ACCESS read-write
	STATUS current
	DESCRIPTION
	    "This attribute shall specify the number of slots, after a SIFS
	    duration, that the QSTA, for a particular AC, shall sense the
	    medium idle either before transmitting or executing a backoff. The
	    default value for this attribute is
	    1) 7, if dot11EDCATableIndex is 1,
	    2) 3, if dot11EDCATableIndex is 2
	    3) 2, otherwise."
    ::= { dot11EDCATableEntry 4 }

dot11EDCATableTXOPLimit OBJECT-TYPE
	SYNTAX INTEGER (0..65535)
	MAX-ACCESS read-write
	STATUS current
	DESCRIPTION
	    "This attribute shall specify the maximum number of microseconds of
	    an EDCA TXOP for a given AC at a non-AP QSTA. The default value for
	    this attribute is
	    1) 0 for all PHYs, if dot11EDCATableIndex is 1 or 2; this
	    implies that the sender can send one MSDU in an EDCA TXOP,
	    2) 3008 microseconds for IEEE 802.11a/g PHY and 6016
	    microseconds for IEEE 802.11b PHY, if dot11EDCATableIndex is 3,
	    3) 1504 microseconds for IEEE 802.11a/g PHY and 3264
	    microseconds for IEEE 802.11b PHY, if dot11EDCATableIndex is 4."
    ::= { dot11EDCATableEntry 5 }

dot11EDCATableMSDULifetime OBJECT-TYPE
	SYNTAX INTEGER (0..500)
	MAX-ACCESS read-write
	STATUS current
	DESCRIPTION
	    "This attribute shall specify (in TUs) the maximum duration an
	    MSDU, for a given AC, would be retained by the MAC before it is
	    discarded. The default value for this parameter shall be 500."
        DEFVAL { 500 }
    ::= { dot11EDCATableEntry 6 }

dot11EDCATableMandatory OBJECT-TYPE
	SYNTAX TruthValue
	MAX-ACCESS read-write
	STATUS current
	DESCRIPTION
	    "This attribute, when TRUE, indicates that admission control is
	    mandatory for the given AC. When False, this attribute indicates
	    that the admission control is not mandatory for the given AC. The
	    default value for this parameter shall be FALSE."
        DEFVAL { false }
    ::= { dot11EDCATableEntry 7 }

-- **********************************************************************
-- * End of SMT EDCA Config TABLE
-- **********************************************************************

-- **********************************************************************
-- * SMT QAP EDCA Config TABLE
-- **********************************************************************

dot11QAPEDCATable OBJECT-TYPE
	SYNTAX SEQUENCE OF Dot11QAPEDCATableEntry
	MAX-ACCESS not-accessible
	STATUS current
	DESCRIPTION
	    "Conceptual table for EDCA default parameter values at the QAP.
	    This table shall contain the four entries of the EDCA parameters
	    corresponding to four possible ACs. Index 1 corresponds to AC_BK,
	    index 2 to AC_BE, index 3 to AC_VI, and index 4 to AC_VO."
	REFERENCE
	    "IEEE 802.11 Tge Draft Version, 9.9.1"
    ::= { dot11mac 5 }

dot11QAPEDCATableEntry OBJECT-TYPE
	SYNTAX Dot11QAPEDCATableEntry
	MAX-ACCESS not-accessible
	STATUS current
	DESCRIPTION
	    "An Entry (conceptual row) in the EDCA Table.
	    ifIndex - Each IEEE 802.11 interface is represented by an
	    ifEntry. Interface tables in this MIB module are indexed
	    by ifIndex."
	INDEX { ifIndex,
	    dot11QAPEDCATableIndex }
    ::= { dot11QAPEDCATable 1 }

Dot11QAPEDCATableEntry ::= SEQUENCE { 
	    dot11QAPEDCATableIndex 		INTEGER,
	    dot11QAPEDCATableCWmin 		INTEGER,
	    dot11QAPEDCATableCWmax 		INTEGER,
	    dot11QAPEDCATableAIFSN 		INTEGER,
	    dot11QAPEDCATableTXOPLimit 		INTEGER,
	    dot11QAPEDCATableMSDULifetime	INTEGER,
	    dot11QAPEDCATableMandatory 		TruthValue }

dot11QAPEDCATableIndex OBJECT-TYPE
	SYNTAX INTEGER (1..4)
        MAX-ACCESS read-only
	STATUS current
	DESCRIPTION
	    "The auxiliary variable used to identify instances of the columnar
	    objects in the EDCA Table. The value of this variable is
	    1) 1, if the value of the AC is AC_BK.
	    2) 2, if the value of the AC is AC_BE.
	    3) 3, if the value of the AC is AC_VI.
	    4) 4, if the value of the AC is AC_VO."
    ::= { dot11QAPEDCATableEntry 1 }

dot11QAPEDCATableCWmin OBJECT-TYPE
	SYNTAX INTEGER (0..255)
	MAX-ACCESS read-write
	STATUS current
	DESCRIPTION
	    "This attribute shall specify the value of the minimum size of the
	    window that shall be used by a QAP for a particular AC for
	    generating a random number for the backoff. The value of this
	    attribute shall be such that it could always be expressed in the
	    form of 2X - 1, where X is an integer. The default value for this
	    attribute is
	    1) aCWmin, if dot11QAPEDCATableIndex is 1 or 2.
	    2) (aCWmin+1)/2 - 1, if dot11QAPEDCATableIndex is 3.
	    3) (aCWmin+1)/4 - 1, if dot11QAPEDCATableIndex is 4."
    ::= { dot11QAPEDCATableEntry 2 }

dot11QAPEDCATableCWmax OBJECT-TYPE
	SYNTAX INTEGER (0..65535)
	MAX-ACCESS read-write
	STATUS current
	DESCRIPTION
	    "This attribute shall specify the value of the maximum size of the
	    window that shall be used by a QAP for a particular AC for
	    generating a random number for the backoff. The value of this
	    attribute shall be such that it could always be expressed in the
	    form of 2X - 1, where X is an integer. The default value for this
	    attribute is
	    1) aCWmax, if dot11QAPEDCATableIndex is 1.
	    2) 4*(aCWmin+1) - 1, if dot11QAPEDCATableIndex is 2.
	    3) aCWmin, if dot11QAPEDCATableIndex is 3.
	    4) (aCWmin+1)/2 - 1, if dot11QAPEDCATableIndex is 4."
    ::= { dot11QAPEDCATableEntry 3 }

dot11QAPEDCATableAIFSN OBJECT-TYPE
	SYNTAX INTEGER (1..15)
	MAX-ACCESS read-write
	STATUS current
	DESCRIPTION
	    "This attribute shall specify the number of slots, after a SIFS
	    duration, that the QAP, for a particular AC, shall sense the
	    medium idle either before transmitting or executing a backoff. The
	    default value for this attribute is
	    1) 7, if dot11QAPEDCATableIndex is 1,
	    2) 3, if dot11QAPEDCATableIndex is 2
	    3) 1, otherwise."
    ::= { dot11QAPEDCATableEntry 4 }

dot11QAPEDCATableTXOPLimit OBJECT-TYPE
	SYNTAX INTEGER (0..65535)
	MAX-ACCESS read-write
	STATUS current
	DESCRIPTION
	    "This attribute shall specify the maximum number of microseconds of
	    an EDCA TXOP for a given AC at the QAP. The default value for
	    this attribute is
	    1) 0 for all PHYs, if dot11QAPEDCATableIndex is 1 or 2; this
	       implies that the sender can send one MSDU in an EDCA TXOP,
	    2) 3008 microseconds for IEEE 802.11a/g PHY and 6016
	       microseconds for IEEE 802.11b PHY, if dot11QAPEDCATableIndex is 3,
	    3) 1504 microseconds for IEEE 802.11a/g PHY and 3264
	       microseconds for IEEE 802.11b PHY, if dot11QAPEDCATableIndex is 4."
    ::= { dot11QAPEDCATableEntry 5 }

dot11QAPEDCATableMSDULifetime OBJECT-TYPE
	SYNTAX INTEGER (0..500)
	MAX-ACCESS read-write
	STATUS current
	DESCRIPTION
	    "This attribute shall specify (in TUs) the maximum duration an
	    MSDU, for a given AC, would be retained by the MAC at the QAP before
	    it is discarded. The default value for this parameter shall be
	    500."
        DEFVAL { 500 }
    ::= { dot11QAPEDCATableEntry 6 }

dot11QAPEDCATableMandatory OBJECT-TYPE
	SYNTAX TruthValue
	MAX-ACCESS read-write
	STATUS current
	DESCRIPTION
	    "This attribute, when TRUE, indicates that admission control is
	    mandatory for the given AC. When False, this attribute indicates
	    that the admission control is not mandatory for the given AC. The
	    default value for this parameter shall be FALSE."
        DEFVAL { false }
    ::= { dot11QAPEDCATableEntry 7 }

-- **********************************************************************
-- * End of SMT QAP EDCA Config TABLE
-- **********************************************************************

-- **********************************************************************
-- * dot11QosCounters TABLE
-- **********************************************************************

dot11QosCountersTable OBJECT-TYPE
	SYNTAX SEQUENCE OF Dot11QosCountersEntry
	MAX-ACCESS not-accessible
	STATUS current
	DESCRIPTION
	    "Group containing attributes that are MAC counters implemented as a
	    table to allow for multiple instantiations on an agent."
    ::= { dot11mac 6 }

dot11QosCountersEntry OBJECT-TYPE
	SYNTAX Dot11QosCountersEntry
	MAX-ACCESS not-accessible
	STATUS current
	DESCRIPTION
	    "An Entry (conceptual row) in the EDCA Table.
	    ifIndex - Each IEEE 802.11 interface is represented by an
	    ifEntry. Interface tables in this MIB module are indexed
	    by ifIndex."
	INDEX { ifIndex,
	    dot11QosCountersIndex }
    ::= { dot11QosCountersTable 1 }

Dot11QosCountersEntry ::= SEQUENCE { 
	    dot11QosCountersIndex 		INTEGER,
	    dot11QosTransmittedFragmentCount	Counter32,
	    dot11QosFailedCount 	    	Counter32,
	    dot11QosRetryCount 	    		Counter32,
	    dot11QosMultipleRetryCount 		Counter32,
	    dot11QosFrameDuplicateCount 	Counter32,
	    dot11QosRTSSuccessCount 		Counter32,
	    dot11QosRTSFailureCount 		Counter32,
	    dot11QosACKFailureCount 		Counter32,
	    dot11QosReceivedFragmentCount 	Counter32,
	    dot11QosTransmittedFrameCount 	Counter32,
	    dot11QosDiscardedFrameCount 	Counter32,
	    dot11QosMPDUsReceivedCount 		Counter32,
	    dot11QosRetriesReceivedCount 	Counter32 }

dot11QosCountersIndex OBJECT-TYPE
	SYNTAX INTEGER (1..16)
        MAX-ACCESS read-only
	STATUS current
	DESCRIPTION
	    "The auxiliary variable used to identify instances of the columnar
	    objects in the QoSCounter Table. The value of this variable is
	    equal to TID + 1."
    ::= { dot11QosCountersEntry 1 }

dot11QosTransmittedFragmentCount OBJECT-TYPE
	SYNTAX Counter32
	MAX-ACCESS read-only
	STATUS current
	DESCRIPTION
	    "This counter shall be incremented for an acknowledged MPDU, for a
	    particular UP, with an individual address in the address 1 field or
	    an MPDU with a multicast address in the address 1 field, either
	    belonging to a particular TID. This counter has relevance only for
	    TIDs between 0 and 7."
    ::= { dot11QosCountersEntry 2 }

dot11QosFailedCount OBJECT-TYPE
	SYNTAX Counter32
	MAX-ACCESS read-only
	STATUS current
	DESCRIPTION
	    "This counter shall increment when an MSDU, for a particular UP, is
	    not transmitted successfully due to the number of transmit attempts
	    exceeding either the dot11ShortRetryLimit or dot11LongRetryLimit.
	    This counter has relevance only for TIDs between 0 and 7."
    ::= { dot11QosCountersEntry 3 }

dot11QosRetryCount OBJECT-TYPE
	SYNTAX Counter32
	MAX-ACCESS read-only
	STATUS current
	DESCRIPTION
	    "This counter shall increment when an MSDU, of a particular UP, is
	    successfully transmitted after one or more retransmissions. This
	    counter has relevance only for TIDs between 0 and 7."
    ::= { dot11QosCountersEntry 4 }

dot11QosMultipleRetryCount OBJECT-TYPE
	SYNTAX Counter32
	MAX-ACCESS read-only
	STATUS current
	DESCRIPTION
	    "This counter shall increment when an MSDU, of a particular UP, is
	    successfully transmitted after more than one retransmissions. This
	    counter has relevance only for TIDs between 0 and 7."
    ::= { dot11QosCountersEntry 5 }

dot11QosFrameDuplicateCount OBJECT-TYPE
	SYNTAX Counter32
	MAX-ACCESS read-only
	STATUS current
	DESCRIPTION
	    "This counter shall increment when a frame, of a particular UP, is
	    received that the Sequence Control field indicates is a duplicate.
	    This counter has relevance only for TIDs between 0 and 7."
    ::= { dot11QosCountersEntry 6 }

dot11QosRTSSuccessCount OBJECT-TYPE
	SYNTAX Counter32
	MAX-ACCESS read-only
	STATUS current
	DESCRIPTION
	    "This counter shall increment when a CTS is received in response to
	    an RTS that has been sent for the transmission of an MPDU of a
	    particular UP. This counter has relevance only for TIDs between 0
	    and 7."
    ::= { dot11QosCountersEntry 7 }

dot11QosRTSFailureCount OBJECT-TYPE
	SYNTAX Counter32
	MAX-ACCESS read-only
	STATUS current
	DESCRIPTION
	    "This counter shall increment when a CTS is not received in
	    response to an RTS that has been sent for the transmission of an
	    MPDU of a particular UP. This counter has relevance only for TIDs
	    between 0 and 7."
    ::= { dot11QosCountersEntry 8 }

dot11QosACKFailureCount OBJECT-TYPE
	SYNTAX Counter32
	MAX-ACCESS read-only
	STATUS current
	DESCRIPTION
	    "This counter shall increment when an ACK is not received in
	    response to an MPDU of a particular UP. This counter has relevance
	    only for TIDs between 0 and 7."
    ::= { dot11QosCountersEntry 9 }

dot11QosReceivedFragmentCount OBJECT-TYPE
	SYNTAX Counter32
	MAX-ACCESS read-only
	STATUS current
	DESCRIPTION
	    "This counter shall be incremented for each successfully received
	    MPDU of type Data of a particular UP. This counter has relevance
	    only for TIDs between 0 and 7."
    ::= { dot11QosCountersEntry 10 }

dot11QosTransmittedFrameCount OBJECT-TYPE
	SYNTAX Counter32
	MAX-ACCESS read-only
	STATUS current
	DESCRIPTION
	    "This counter shall increment for each successfully transmitted
	    MSDU of a particular UP. This counter has relevance only for TIDs
	    between 0 and 7."
    ::= { dot11QosCountersEntry 11 }

dot11QosDiscardedFrameCount OBJECT-TYPE
	SYNTAX Counter32
	MAX-ACCESS read-only
	STATUS current
	DESCRIPTION
	    "This counter shall increment for each Discarded MSDU of a
	    particular UP. This counter has relevance only for TIDs between 0
	    and 7."
    ::= { dot11QosCountersEntry 12 }

dot11QosMPDUsReceivedCount OBJECT-TYPE
	SYNTAX Counter32
	MAX-ACCESS read-only
	STATUS current
	DESCRIPTION
	    "This counter shall increment for each received MPDU of a
	    particular TID."
    ::= { dot11QosCountersEntry 13 }

dot11QosRetriesReceivedCount OBJECT-TYPE
	SYNTAX Counter32
	MAX-ACCESS read-only
	STATUS current
	DESCRIPTION
	    "This counter shall increment for each received MPDU of a
	    particular TID with the retry bit set to 1."
    ::= { dot11QosCountersEntry 14 }

-- **********************************************************************
-- * End of dot11QosCounters TABLE
-- **********************************************************************


-- **********************************************************************
-- *    Resource Type Attribute Templates
-- **********************************************************************
dot11ResourceTypeIDName OBJECT-TYPE
        SYNTAX DisplayString (SIZE(4))
        MAX-ACCESS read-only
        STATUS current
        DESCRIPTION

            "Contains the name of the Resource Type ID managed object.
            The attribute is read-only and always contains the value
            RTID.  This attribute value shall not be used as a naming
            attribute for any other managed object class."

        REFERENCE "IEEE Std 802.1F-1993,  A.7"
        DEFVAL {"RTID"}
    ::= {  dot11resAttribute 1 }

-- **********************************************************************
-- *    dot11ResourceInfo  TABLE
-- **********************************************************************
dot11ResourceInfoTable OBJECT-TYPE
        SYNTAX SEQUENCE OF Dot11ResourceInfoEntry
        MAX-ACCESS not-accessible
        STATUS current
        DESCRIPTION

            "Provides a means of indicating, in data readable from a
            managed object, information that identifies the source of
            the implementation."

        REFERENCE "IEEE Std 802.1F-1993,  A.7"
    ::= {  dot11resAttribute 2 }

dot11ResourceInfoEntry OBJECT-TYPE
        SYNTAX Dot11ResourceInfoEntry
        MAX-ACCESS not-accessible
        STATUS current
        DESCRIPTION
            "An entry in the dot11ResourceInfo Table.

            ifIndex - Each 802.11 interface is represented by an
            ifEntry.  Interface tables in this MIB module are indexed
            by ifIndex."
        INDEX {ifIndex}
    ::= {  dot11ResourceInfoTable 1 }

Dot11ResourceInfoEntry ::= SEQUENCE {
            dot11manufacturerOUI             OCTET STRING,
            dot11manufacturerName            DisplayString,
            dot11manufacturerProductName     DisplayString,
            dot11manufacturerProductVersion  DisplayString}


dot11manufacturerOUI OBJECT-TYPE
        SYNTAX OCTET STRING (SIZE(3))
        MAX-ACCESS read-only
        STATUS current
        DESCRIPTION
            "Takes the value of an organizationally unique identifier."
    ::= {  dot11ResourceInfoEntry 1 }

dot11manufacturerName OBJECT-TYPE
        SYNTAX DisplayString (SIZE(0..128))
        MAX-ACCESS read-only
        STATUS current
        DESCRIPTION
            "A printable string used to identify the manufacturer of the
            resource.  Maximum string length is 128 octets."
    ::= {  dot11ResourceInfoEntry 2 }

dot11manufacturerProductName OBJECT-TYPE
        SYNTAX DisplayString (SIZE(0..128))
        MAX-ACCESS read-only
        STATUS current
        DESCRIPTION
            "A printable string used to identify the manufacturer's product
            name of the resource.  Maximum string length is 128 octets."
    ::= {  dot11ResourceInfoEntry 3 }

dot11manufacturerProductVersion OBJECT-TYPE
        SYNTAX DisplayString (SIZE(0..128))
        MAX-ACCESS read-only
        STATUS current
        DESCRIPTION
            "Printable string used to identify the manufacturer's product
            version of the resource.  Maximum string length is 128 octets."
    ::= {  dot11ResourceInfoEntry 4 }

-- **********************************************************************
-- *    End of dot11ResourceInfo  TABLE
-- **********************************************************************

-- **********************************************************************
-- *   PHY Attribute Templates
-- **********************************************************************

-- **********************************************************************
-- *    dot11PhyOperation  TABLE
-- **********************************************************************
dot11PhyOperationTable OBJECT-TYPE
        SYNTAX SEQUENCE OF Dot11PhyOperationEntry
        MAX-ACCESS not-accessible
        STATUS current
        DESCRIPTION

        "PHY level attributes concerned with
        operation.  Implemented as a table indexed on
        ifIndex to allow for multiple instantiations on an
        Agent."

    ::= {  dot11phy 1 }

dot11PhyOperationEntry OBJECT-TYPE
        SYNTAX Dot11PhyOperationEntry
        MAX-ACCESS not-accessible
        STATUS current
        DESCRIPTION
            "An entry in the dot11PhyOperation Table.

            ifIndex - Each 802.11 interface is represented by an
            ifEntry.  Interface tables in this MIB module are indexed
            by ifIndex."
        INDEX {ifIndex}
    ::= {  dot11PhyOperationTable 1 }

Dot11PhyOperationEntry ::= SEQUENCE {
--	    dot11PhyOperationGroupTableIndex	Integer32,
	    dot11PHYType			INTEGER,
	    dot11CurrentRegDomain		Integer32,
--	    dot11CCATime			Integer32,
	    dot11TempType			INTEGER
--	    dot11PhyOperationGroupRowStatus	RowStatus 
	    }

dot11PHYType OBJECT-TYPE
	SYNTAX INTEGER {fhss(1), dsss(2), irbaseband(3), ofdm(4), hrdsss(5), erp(6), ht(7)}
        MAX-ACCESS read-only
        STATUS current
        DESCRIPTION

	    "This is an 8-bit integer value that identifies the PHY
	    type supported by the attached PLCP and PMD. Currently
	    defined values and their corresponding PHY types are:
	    FHSS 2.4 GHz = 01, DSSS 2.4 GHz = 02, IR Baseband = 03,
	    OFDM 5GHz = 04, HRDSSS = 05, ERP = 06, HT = 07"
    ::= {  dot11PhyOperationEntry 1 }

dot11CurrentRegDomain OBJECT-TYPE
	SYNTAX Integer32 (0..2147483647)
        MAX-ACCESS read-write
        STATUS current
        DESCRIPTION

            "The current regulatory domain this instance of the PMD is
            supporting.  This object corresponds to one of the
            RegDomains listed in dot11RegDomainsSupported."

    ::= {   dot11PhyOperationEntry 2 }

dot11TempType OBJECT-TYPE
        SYNTAX INTEGER {tempType1(1), tempType2(2) }
        MAX-ACCESS read-only
        STATUS current
        DESCRIPTION

	    "There are different operating temperature requirements
	    dependent on the anticipated environmental conditions. This
	    attribute describes the current PHY's operating temperature
	    range capability. Currently defined values and their
	    corresponding temperature ranges are:

	    Type 1 = X'01'-Commercial range of 0 to 40 degrees C,

	    Type 2 = X'02'-Industrial range of -30 to 70 degrees C."

    ::= {   dot11PhyOperationEntry 3 }




-- **********************************************************************
-- *    End of dot11PhyOperation  TABLE
-- **********************************************************************

-- **********************************************************************
-- *    dot11PhyAntenna  TABLE
-- **********************************************************************
dot11PhyAntennaTable OBJECT-TYPE
        SYNTAX SEQUENCE OF Dot11PhyAntennaEntry
        MAX-ACCESS not-accessible
        STATUS current
        DESCRIPTION

            "Group of attributes for PhyAntenna.  Implemented as a
            table indexed on ifIndex to allow for multiple instances on
            an agent."

    ::= {  dot11phy 2}

dot11PhyAntennaEntry OBJECT-TYPE
        SYNTAX Dot11PhyAntennaEntry
        MAX-ACCESS not-accessible
        STATUS current
        DESCRIPTION
            "An entry in the dot11PhyAntenna Table.

            ifIndex - Each 802.11 interface is represented by an
            ifEntry.  Interface tables in this MIB module are indexed
            by ifIndex."
        INDEX {ifIndex}
    ::= {  dot11PhyAntennaTable 1 }

Dot11PhyAntennaEntry ::= SEQUENCE {
            dot11CurrentTxAntenna					Integer32,
            dot11DiversitySupport					INTEGER,
	    dot11CurrentRxAntenna					Integer32,
	    dot11AntennaSelectionOptionImplemented	    		TruthValue,
	    dot11TransmitExplicitCSIFeedbackASOptionImplemented		TruthValue,
	    dot11TransmitIndicesFeedbackASOptionImplemented 		TruthValue,
	    dot11ExplicitCSIFeedbackASOptionImplemented 		TruthValue,
	    dot11TransmitIndicesComputationFeedbackASOptionImplemented	TruthValue,
	    dot11ReceiveAntennaSelectionOptionImplemented 		TruthValue,
	    dot11TransmitSoundingPPDUOptionImplemented 			TruthValue }

dot11CurrentTxAntenna OBJECT-TYPE
        SYNTAX Integer32 (1..255)
        MAX-ACCESS read-write
        STATUS current
        DESCRIPTION

            "The current antenna being used to transmit.  This value
	    is one of the values appearing in
        dot11SupportedTxAntenna. This may be used by a management agent to control which antenna is used for transmission. "

    ::= {  dot11PhyAntennaEntry 1 }

dot11DiversitySupport OBJECT-TYPE
        SYNTAX INTEGER {fixedlist(1), notsupported(2), dynamic(3)}
        MAX-ACCESS read-only
        STATUS current
        DESCRIPTION

	    "This implementation's support for diversity, encoded as:

	    X'01'-diversity is available and is performed over the fixed
		list of antennas defined in dot11DiversitySelectionRx.

	    X'02'-diversity is not supported.

	    X'03'-diversity is supported and control of diversity is also
		available, in which case the attribute 
		dot11DiversitySelectionRx can be dynamically modified by the
		LME."
    ::= {  dot11PhyAntennaEntry 2 }

dot11CurrentRxAntenna OBJECT-TYPE
        SYNTAX Integer32 (1..255)
        MAX-ACCESS read-write
        STATUS current
        DESCRIPTION

"The current antenna being used to receive, if the dot11 DiversitySupport indicates that diversity is not supported.  The selected antenna shall be one of the antennae marked for receive in the dot11AntennasListTable. "

    ::= {  dot11PhyAntennaEntry 3 }

dot11AntennaSelectionOptionImplemented OBJECT-TYPE
	SYNTAX TruthValue
	MAX-ACCESS read-only
	STATUS current
	DESCRIPTION
	    "This attribute, when TRUE, indicates that antenna selection
	    is supported by the station implementation. The default value of this
	    attribute is FALSE."
        DEFVAL { false }
    ::= {  dot11PhyAntennaEntry 4 }
    
dot11TransmitExplicitCSIFeedbackASOptionImplemented OBJECT-TYPE
	SYNTAX TruthValue
	MAX-ACCESS read-only
	STATUS current
	DESCRIPTION
	    "This attribute, when TRUE, indicates that the transmit
	    Antenna Selection based on explicit CSI feedback is supported by the station
	    implementation. The default value of this attribute is FALSE."
        DEFVAL { false }
    ::= { dot11PhyAntennaEntry 5 }

dot11TransmitIndicesFeedbackASOptionImplemented OBJECT-TYPE
	SYNTAX TruthValue
	MAX-ACCESS read-only
	STATUS current
	DESCRIPTION
	    "This attribute, when TRUE, indicates that the transmit
	    antenna selection based on antenna indices feedback is supported by the
	    station implementation. The default value of this attribute is FALSE."
        DEFVAL { false }
    ::= { dot11PhyAntennaEntry 6 }

dot11ExplicitCSIFeedbackASOptionImplemented OBJECT-TYPE
	SYNTAX TruthValue
	MAX-ACCESS read-only
	STATUS current
	DESCRIPTION
	    "This attribute, when TRUE, indicates that the computation of
	    CSI and feedback to support the peer to do antenna selection is supported by
	    the station implementation. The default value of this attribute is FALSE."
        DEFVAL { false }
    ::= { dot11PhyAntennaEntry 7 }

dot11TransmitIndicesComputationFeedbackASOptionImplemented OBJECT-TYPE
	SYNTAX TruthValue
	MAX-ACCESS read-only
	STATUS current
	DESCRIPTION
	    "This attribute, when TRUE, indicates that the transmit
	    antenna selection based on antenna indices selection computation and
	    feedback the results to support the peer to do antenna selection is supported
	    by the station implementation. The default value of this attribute is
	    FALSE."
        DEFVAL { false }
    ::= { dot11PhyAntennaEntry 8 }

dot11ReceiveAntennaSelectionOptionImplemented OBJECT-TYPE
	SYNTAX TruthValue
	MAX-ACCESS read-only
	STATUS current
	DESCRIPTION
	    "This attribute, when TRUE, indicates that the receive antenna
	    selection is supported by the station implementation. The default value of
	    this attribute is FALSE."
        DEFVAL { false }
    ::= { dot11PhyAntennaEntry 9 }

dot11TransmitSoundingPPDUOptionImplemented OBJECT-TYPE
	SYNTAX TruthValue
	MAX-ACCESS read-only
	STATUS current
	DESCRIPTION
	    "This attribute, when TRUE, indicates that the transmission of
	    sounding PPDUs is supported by the station implementation. The default value
	    of this attribute is FALSE."
        DEFVAL { false }
    ::= { dot11PhyAntennaEntry 10 }

-- **********************************************************************
-- *    End of dot11PhyAntenna  TABLE
-- **********************************************************************

-- **********************************************************************
-- *    dot11PhyTxPower  TABLE
-- **********************************************************************
dot11PhyTxPowerTable OBJECT-TYPE
        SYNTAX SEQUENCE OF Dot11PhyTxPowerEntry
        MAX-ACCESS not-accessible
        STATUS current
        DESCRIPTION

            "Group of attributes for dot11PhyTxPowerTable.  Implemented
            as a table indexed on STA ID to allow for multiple
            instances on an Agent."

    ::= {  dot11phy 3}

dot11PhyTxPowerEntry OBJECT-TYPE
        SYNTAX Dot11PhyTxPowerEntry
        MAX-ACCESS not-accessible
        STATUS current
        DESCRIPTION
            "An entry in the dot11PhyTxPower Table.

            ifIndex - Each 802.11 interface is represented by an
            ifEntry.  Interface tables in this MIB module are indexed
            by ifIndex."
        INDEX {ifIndex}
    ::= {  dot11PhyTxPowerTable 1 }

Dot11PhyTxPowerEntry ::= SEQUENCE {
            dot11NumberSupportedPowerLevels  INTEGER,
            dot11TxPowerLevel1               INTEGER,
            dot11TxPowerLevel2               INTEGER,
            dot11TxPowerLevel3               INTEGER,
            dot11TxPowerLevel4               INTEGER,
            dot11TxPowerLevel5               INTEGER,
            dot11TxPowerLevel6               INTEGER,
            dot11TxPowerLevel7               INTEGER,
            dot11TxPowerLevel8               INTEGER,
            dot11CurrentTxPowerLevel         INTEGER}

dot11NumberSupportedPowerLevels OBJECT-TYPE
        SYNTAX INTEGER (1..8)
        MAX-ACCESS read-only
        STATUS current
        DESCRIPTION
            "The number of power levels supported by the PMD.
            This attribute can have a value of 1 to 8."
    ::= {  dot11PhyTxPowerEntry 1 }

dot11TxPowerLevel1 OBJECT-TYPE
        SYNTAX INTEGER (0..10000)
        MAX-ACCESS read-only
        STATUS current
        DESCRIPTION
            "The transmit output power for LEVEL1 in mW.
            This is also the default power level."
    ::= {   dot11PhyTxPowerEntry 2 }

dot11TxPowerLevel2 OBJECT-TYPE
        SYNTAX INTEGER (0..10000)
        MAX-ACCESS read-only
        STATUS current
        DESCRIPTION
            "The transmit output power for LEVEL2 in mW."
    ::= {   dot11PhyTxPowerEntry 3 }

dot11TxPowerLevel3 OBJECT-TYPE
        SYNTAX INTEGER (0..10000)
        MAX-ACCESS read-only
        STATUS current
        DESCRIPTION
            "The transmit output power for LEVEL3 in mW."
    ::= {   dot11PhyTxPowerEntry 4 }

dot11TxPowerLevel4 OBJECT-TYPE
        SYNTAX INTEGER (0..10000)
        MAX-ACCESS read-only
        STATUS current
        DESCRIPTION
            "The transmit output power for LEVEL4 in mW."
    ::= {   dot11PhyTxPowerEntry 5 }

dot11TxPowerLevel5 OBJECT-TYPE
        SYNTAX INTEGER (0..10000)
        MAX-ACCESS read-only
        STATUS current
        DESCRIPTION
            "The transmit output power for LEVEL5 in mW."
    ::= {   dot11PhyTxPowerEntry 6 }

dot11TxPowerLevel6 OBJECT-TYPE
        SYNTAX INTEGER (0..10000)
        MAX-ACCESS read-only
        STATUS current
        DESCRIPTION
            "The transmit output power for LEVEL6 in mW."
    ::= {   dot11PhyTxPowerEntry 7 }

dot11TxPowerLevel7 OBJECT-TYPE
        SYNTAX INTEGER (0..10000)
        MAX-ACCESS read-only
        STATUS current
        DESCRIPTION
            "The transmit output power for LEVEL7 in mW."
    ::= {   dot11PhyTxPowerEntry 8 }

dot11TxPowerLevel8 OBJECT-TYPE
        SYNTAX INTEGER (0..10000)
        MAX-ACCESS read-only
        STATUS current
        DESCRIPTION
            "The transmit output power for LEVEL8 in mW."
    ::= {   dot11PhyTxPowerEntry 9 }

dot11CurrentTxPowerLevel OBJECT-TYPE
        SYNTAX INTEGER (1..8)
        MAX-ACCESS read-write
        STATUS current
        DESCRIPTION

            "The TxPowerLevel N currently being used to transmit data.
            Some PHYs also use this value to determine the receiver
            sensitivity requirements for CCA."

    ::= {   dot11PhyTxPowerEntry 10 }

-- **********************************************************************
-- *    End of dot11PhyTxPower  TABLE
-- **********************************************************************

-- **********************************************************************
-- *    dot11PhyFHSS  TABLE
-- **********************************************************************

dot11PhyFHSSTable OBJECT-TYPE
        SYNTAX SEQUENCE OF Dot11PhyFHSSEntry
        MAX-ACCESS not-accessible
        STATUS current
        DESCRIPTION

            "Group of attributes for dot11PhyFHSSTable.  Implemented as a
            table indexed on STA ID to allow for multiple instances on
            an Agent."

    ::= {  dot11phy 4 }

dot11PhyFHSSEntry OBJECT-TYPE
        SYNTAX Dot11PhyFHSSEntry
        MAX-ACCESS not-accessible
        STATUS current
        DESCRIPTION
            "An entry in the dot11PhyFHSS Table.

            ifIndex - Each 802.11 interface is represented by an
            ifEntry.  Interface tables in this MIB module are indexed
            by ifIndex."
        INDEX {ifIndex}
    ::= {  dot11PhyFHSSTable 1 }

Dot11PhyFHSSEntry ::= SEQUENCE {
             dot11HopTime				INTEGER,
             dot11CurrentChannelNumber			INTEGER,
             dot11MaxDwellTime				INTEGER,
             dot11CurrentDwellTime			INTEGER,
             dot11CurrentSet				INTEGER,
             dot11CurrentPattern			INTEGER,
             dot11CurrentIndex				INTEGER,
             dot11EHCCPrimeRadix			Integer32,
             dot11EHCCNumberofChannelsFamilyIndex	Integer32,
             dot11EHCCCapabilityImplemented		TruthValue,
             dot11EHCCCapabilityEnabled			TruthValue,
             dot11HopAlgorithmAdopted			INTEGER,
             dot11RandomTableFlag			TruthValue,
             dot11NumberofHoppingSets			Integer32,
             dot11HopModulus				Integer32,
             dot11HopOffset Integer32}

dot11HopTime OBJECT-TYPE
        SYNTAX INTEGER (224)
        MAX-ACCESS read-only
        STATUS current
        DESCRIPTION
            "The time in microseconds for the PMD to change from
            channel 2 to channel 80"
    ::= {   dot11PhyFHSSEntry 1 }

dot11CurrentChannelNumber OBJECT-TYPE
        SYNTAX INTEGER (0..99)
        MAX-ACCESS read-write
        STATUS current
        DESCRIPTION
	    "The current channel number of the frequency output by the RF
	    synthesizer"
    ::= {   dot11PhyFHSSEntry 2 }

dot11MaxDwellTime OBJECT-TYPE
        SYNTAX INTEGER (1..65535)
        MAX-ACCESS read-only
        STATUS current
        DESCRIPTION
            "The maximum time in TU that the transmitter
            is permitted to operate on a single channel."
    ::= {   dot11PhyFHSSEntry 3 }

dot11CurrentDwellTime OBJECT-TYPE
        SYNTAX INTEGER (1..65535)
        MAX-ACCESS read-write
        STATUS current
        DESCRIPTION
            "The current time in TU that the transmitter shall operate
            on a single channel, as set by the MAC.  Default is 19 TU."
    ::= {   dot11PhyFHSSEntry 4 }

dot11CurrentSet OBJECT-TYPE
        SYNTAX INTEGER (1..255)
        MAX-ACCESS read-write
        STATUS current
        DESCRIPTION
            "The current set of patterns the PHY
            LME is using to determine the hopping sequence. "
    ::= {   dot11PhyFHSSEntry 5 }

dot11CurrentPattern OBJECT-TYPE
        SYNTAX INTEGER (0..255)
        MAX-ACCESS read-write
        STATUS current
        DESCRIPTION
            "The current pattern the PHY LME is
            using to determine the hop sequence."
    ::= {   dot11PhyFHSSEntry 6 }

dot11CurrentIndex OBJECT-TYPE
        SYNTAX INTEGER (1..255)
        MAX-ACCESS read-write
        STATUS current
        DESCRIPTION

            "The current index value the PHY LME is using to determine
            the CurrentChannelNumber."

    ::= {   dot11PhyFHSSEntry 7 }

dot11EHCCPrimeRadix OBJECT-TYPE
        SYNTAX Integer32
        MAX-ACCESS read-write
        STATUS current
        
        DESCRIPTION
	    "This attribute indicates the value to be used as the prime radix (N) in
	    the HCC and EHCC algorithms."
::= { dot11PhyFHSSEntry 8 }

dot11EHCCNumberofChannelsFamilyIndex OBJECT-TYPE
        SYNTAX Integer32
        MAX-ACCESS read-write
        STATUS current
        
        DESCRIPTION
	    "This attribute indicates the value to be used as the maximum for the
	    family index (a) in the HCC and EHCC algorithms. The value of this field
	    shall not be less than the prime radix minus 3 (N - 3). The valid range of
	    allowed values is (N - 1), (N - 2), and (N - 3)."
::= { dot11PhyFHSSEntry 9 }

dot11EHCCCapabilityImplemented OBJECT-TYPE
        SYNTAX TruthValue
        MAX-ACCESS read-write
        STATUS current
        
        DESCRIPTION
	    "This attribute, when TRUE, indicates that the station implementation is
	    capable of generating the HCC or EHCC algorithms for determining Hopping
	    patterns. The capability is disabled, otherwise. The default value of
	    this attribute is FALSE."
::= { dot11PhyFHSSEntry 10 }

dot11EHCCCapabilityEnabled OBJECT-TYPE
        SYNTAX TruthValue
        MAX-ACCESS read-write
        STATUS current
        
        DESCRIPTION
	    "This attribute, when TRUE, indicates that the capability of the station
	    to operate using the HCC or EHCC algorithms for determining Hopping
	    Patterns is enabled. The capability is disabled, otherwise. The default
	    value of this attribute is FALSE."
::= { dot11PhyFHSSEntry 11 }

dot11HopAlgorithmAdopted OBJECT-TYPE
        SYNTAX INTEGER { current(0), hop-index(1), hcc(2) }
        MAX-ACCESS read-write
        STATUS current
        
        DESCRIPTION
	    "This attribute, indicates which of the algorithms will be used to
	    generate the Hopping Patterns. Valid Values are:
	    0 - hopping patterns as defined in clause 14 of the current version
	    of IEEE Std 802.11
	    1 - hop index method (with or without table)
	    2 - HCC/EHCC method"
::= { dot11PhyFHSSEntry 12 }

dot11RandomTableFlag OBJECT-TYPE
        SYNTAX TruthValue
        MAX-ACCESS read-write
        STATUS current
        
        DESCRIPTION
	    "This attribute, indicates that a Random Table is present when the value
	    is True. When the value is False it indicates that a Random Table is not
	    present and that the hop index method is to be used to determine the hopping
	    sequence. The default value of this attribute is True."
::= { dot11PhyFHSSEntry 13 }

dot11NumberofHoppingSets OBJECT-TYPE
        SYNTAX Integer32
        MAX-ACCESS read-only
        STATUS current
        DESCRIPTION
	    "The Number of Sets field indicates the total number of sets within the
	    hopping patterns."
::= { dot11PhyFHSSEntry 14 }

dot11HopModulus OBJECT-TYPE
        SYNTAX Integer32
        MAX-ACCESS read-only
        STATUS current
        DESCRIPTION
	    "The number of allowed channels for the hopping set. This is defined by
	    the governing regulatory agency for the country code of the country in
	    which this device is operating."
::= { dot11PhyFHSSEntry 15 }

dot11HopOffset OBJECT-TYPE
        SYNTAX Integer32
        MAX-ACCESS read-write
        STATUS current
        
        DESCRIPTION
	    "The next position in the hopping set."
::= { dot11PhyFHSSEntry 16 }


-- **********************************************************************
-- *    End of dot11PhyFHSS  TABLE
-- **********************************************************************

-- ********************************************************************
-- * dot11 Hopping Pattern TABLE
-- ********************************************************************


dot11HoppingPatternTable OBJECT-TYPE
        SYNTAX SEQUENCE OF Dot11HoppingPatternEntry
        MAX-ACCESS not-accessible
        STATUS current

        DESCRIPTION
	    "The (conceptual) table of attributes necessary for a frequency hopping
	    implementation to be able to create the hopping sequences necessary to
	    operate in the subband for the associated domain country string."
::= { dot11phy 13 }

dot11HoppingPatternEntry OBJECT-TYPE
        SYNTAX Dot11HoppingPatternEntry
        MAX-ACCESS not-accessible
        STATUS current
        
        DESCRIPTION
	    "An entry (conceptual row) in the Hopping Pattern Table that indicates the
	    random hopping sequence to be followed.
	    IfIndex - Each 802.11 interface is represented by an ifEntry. Interface
	    tables in this MIB are indexed by ifIndex."
        INDEX { ifIndex,
                dot11HoppingPatternIndex}
::= {dot11HoppingPatternTable 1}

Dot11HoppingPatternEntry ::=
        SEQUENCE {
	    dot11HoppingPatternIndex	Integer32,
        dot11RandomTableFieldNumber Integer32}
        
dot11HoppingPatternIndex OBJECT-TYPE
        SYNTAX Integer32 (1..2147483647)
        MAX-ACCESS read-only
        STATUS current
        DESCRIPTION
	    "The auxiliary variable used to identify instances of the columnar objects
	    in the Hopping Pattern Table."
::= { dot11HoppingPatternEntry 1}

dot11RandomTableFieldNumber OBJECT-TYPE
        SYNTAX Integer32
        MAX-ACCESS read-write
        STATUS current
        
        DESCRIPTION
	    "This attribute shall indicate the value of the starting channel number in
	    the hopping sequence of the subband for the associated domain country
	    string. The default value of this attribute shall be zero."
::= { dot11HoppingPatternEntry 2}


-- **********************************************************************
-- * End of dot11 Hopping Pattern TABLE
-- **********************************************************************

-- **********************************************************************
-- * dot11PhyERPEntry TABLE
-- **********************************************************************
dot11PhyERPTable OBJECT-TYPE
	SYNTAX SEQUENCE OF Dot11PhyERPEntry
	MAX-ACCESS not-accessible
	STATUS current
	
	DESCRIPTION
	    "Entry of attributes for dot11PhyERPEntry. Implemented
	    as a table indexed on ifIndex to allow for multiple
	    instances on an Agent."
::= { dot11phy 14 }

dot11PhyERPEntry OBJECT-TYPE
	SYNTAX Dot11PhyERPEntry
	MAX-ACCESS not-accessible
	STATUS current
	
	DESCRIPTION
	    "An entry in the dot11PhyERPEntry Table.
	    ifIndex - Each 802.11 interface is represented by an
	    ifEntry. Interface tables in this MIB module are indexed
	    by ifIndex."
	INDEX {ifIndex}
::= { dot11PhyERPTable 1 }

Dot11PhyERPEntry ::= SEQUENCE {
	    dot11ERPPBCCOptionImplemented	TruthValue,
	    dot11ERPBCCOptionEnabled		TruthValue,
	    dot11DSSSOFDMOptionImplemented	TruthValue,
	    dot11DSSSOFDMOptionEnabled		TruthValue,
	    dot11ShortSlotTimeOptionImplemented	TruthValue,
	    dot11ShortSlotTimeOptionEnabled	TruthValue }
	
dot11ERPPBCCOptionImplemented OBJECT-TYPE
	SYNTAX TruthValue
	MAX-ACCESS read-only
	STATUS current
	DESCRIPTION
	    "This attribute, when true, shall indicate that the ERPPBCC
	    modulation option as defined in 19.6 is implemented.
	    The default value of this attribute is false."
::= {dot11PhyERPEntry 1 }

dot11ERPBCCOptionEnabled OBJECT-TYPE
	SYNTAX TruthValue
	MAX-ACCESS read-write
	STATUS current
	
	DESCRIPTION
	    "This attribute, when true, shall indicate that the ERPPBCCoption
	    as defined in 19.6 is enabled. The default
	    value of this attribute is false."
::= {dot11PhyERPEntry 2 }

dot11DSSSOFDMOptionImplemented OBJECT-TYPE
	SYNTAX TruthValue
	MAX-ACCESS read-only
	STATUS current
	DESCRIPTION
	    "This attribute, when true, shall indicate that the
	    DSSS-OFDM option as defined in 19.7 is implemented. The
	    default value of this attribute is false."
::= {dot11PhyERPEntry 3 }

dot11DSSSOFDMOptionEnabled OBJECT-TYPE
	SYNTAX TruthValue
	MAX-ACCESS read-write
	STATUS current
	
	DESCRIPTION
	    "This attribute, when true, shall indicate that the
	    DSSS-OFDM option as defined in 19.7 is enabled. The
	    default value of this attribute is false."
::= {dot11PhyERPEntry 4 }

dot11ShortSlotTimeOptionImplemented OBJECT-TYPE
	SYNTAX TruthValue
	MAX-ACCESS read-write
	STATUS current
	
	DESCRIPTION
	    "This attribute, when true, shall indicate that the
	    Short Slot Time option as defined in 7.3.1.4 is implemented.
	    The default value of this attribute is false."
::= {dot11PhyERPEntry 5}

dot11ShortSlotTimeOptionEnabled OBJECT-TYPE
	SYNTAX TruthValue
	MAX-ACCESS read-write
	STATUS current
	
	DESCRIPTION
	    "This attribute, when true, shall indicate that the
	    Short Slot Time option as defined in 7.3.1.4 is enabled.
	    The default value of this attribute is false."
::= {dot11PhyERPEntry 6 }

-- **********************************************************************
-- * End of dot11PhyERPEntry TABLE
-- **********************************************************************

-- **********************************************************************
-- * dot11 Phy HT TABLE
-- **********************************************************************

dot11PhyHTTable OBJECT-TYPE
	SYNTAX SEQUENCE OF Dot11PhyHTEntry
	MAX-ACCESS not-accessible
	STATUS current
	DESCRIPTION
	    "Entry of attributes for dot11PhyHTTable. Implemented as a
	    table indexed on ifIndex to allow for multiple instances on an Agent."
    ::= { dot11phy 15 }

dot11PhyHTEntry OBJECT-TYPE
	SYNTAX Dot11PhyHTEntry
	MAX-ACCESS not-accessible
	STATUS current
	DESCRIPTION
	    "An entry in the dot11PhyHTEntry Table. ifIndex - Each 802.11
	    interface is represented by an ifEntry. Interface tables in this MIB module
	    are indexed by ifIndex."
	INDEX {ifIndex}
    ::= { dot11PhyHTTable 1 }

Dot11PhyHTEntry ::= SEQUENCE {
	    dot11FortyMHzOperationImplemented		TruthValue,
	    dot11FortyMHzOperationEnabled		TruthValue,
	    dot11CurrentPrimaryChannel			INTEGER,
	    dot11CurrentSecondaryChannel		INTEGER,
	    dot11NumberOfSpatialStreamsImplemented	INTEGER,
	    dot11NumberOfSpatialStreamsEnabled		INTEGER,
	    dot11GreenfieldOptionImplemented		TruthValue,
	    dot11GreenfieldOptionEnabled		TruthValue,
	    dot11ShortGIOptionInTwentyImplemented	TruthValue,
	    dot11ShortGIOptionInTwentyEnabled		TruthValue,
	    dot11ShortGIOptionInFortyImplemented	TruthValue,
	    dot11ShortGIOptionInFortyEnabled		TruthValue,
	    dot11LDPCCodingOptionImplemented		TruthValue,
	    dot11LDPCCodingOptionEnabled		TruthValue,
	    dot11TxSTBCOptionImplemented		TruthValue,
	    dot11TxSTBCOptionEnabled			TruthValue,
	    dot11RxSTBCOptionImplemented		TruthValue,
	    dot11RxSTBCOptionEnabled			TruthValue,
	    dot11BeamFormingOptionImplemented		TruthValue,
	    dot11BeamFormingOptionEnabled		TruthValue,
	    dot11HighestSupportedDataRate		INTEGER,
	    dot11TxMCSSetDefined			TruthValue,
	    dot11TxRxMCSSetNotEqual			TruthValue,
	    dot11TxMaximumNumberSpatialStreamsSupported	INTEGER,
	    dot11TxUnequalModulationSupported		TruthValue }
	    
dot11FortyMHzOperationImplemented OBJECT-TYPE
	SYNTAX TruthValue
	MAX-ACCESS read-only
	STATUS current
	DESCRIPTION
	    "This attribute, when TRUE, indicates that the 40 MHz
	    Operation is implemented. The default value of this attribute is FALSE."
        DEFVAL { false }
    ::= { dot11PhyHTEntry 1 }

dot11FortyMHzOperationEnabled OBJECT-TYPE
	SYNTAX TruthValue
	MAX-ACCESS read-write
	STATUS current
	DESCRIPTION
	    "This attribute, when TRUE, indicates that the 40 MHz
	    Operation is enabled. The default value of this attribute is FALSE."
        DEFVAL { false }
    ::= { dot11PhyHTEntry 2 }

dot11CurrentPrimaryChannel OBJECT-TYPE
	SYNTAX INTEGER
	MAX-ACCESS read-only
	STATUS current
	DESCRIPTION
	    "This attribute indicates the operating channel. If 20/40 MHz
	    Mode is currently in use then this attribute indicates the primary channel."
    ::= { dot11PhyHTEntry 3 }

dot11CurrentSecondaryChannel OBJECT-TYPE
	SYNTAX INTEGER
	MAX-ACCESS read-write
	STATUS current
	DESCRIPTION
	    "This attribute indicates the channel number of the secondary
	    channel. If 20/40 MHz mode is not currently in use, this attribute value
	    shall be 0."
    ::= { dot11PhyHTEntry 4 }

dot11NumberOfSpatialStreamsImplemented OBJECT-TYPE
	SYNTAX INTEGER (1..4)
	MAX-ACCESS read-only
	STATUS current
	DESCRIPTION
	    "This attribute indicates the maximum number of spatial
	    streams implemented. The default value of this attribute is 2."
        DEFVAL { 2 }
    ::= { dot11PhyHTEntry 5 }

dot11NumberOfSpatialStreamsEnabled OBJECT-TYPE
	SYNTAX INTEGER (1..4)
	MAX-ACCESS read-write
	STATUS current
	DESCRIPTION
	    "This attribute indicates the maximum number of spatial
	    streams enabled. The default value of this attribute is 2."
        DEFVAL { 2 }
    ::= { dot11PhyHTEntry 6 }
		
dot11GreenfieldOptionImplemented OBJECT-TYPE
	SYNTAX TruthValue
	MAX-ACCESS read-only
	STATUS current
	DESCRIPTION
	    "This attribute, when TRUE, indicates that the HT Greenfield
	    option is implemented. The default value of this attribute is FALSE."
        DEFVAL { false }
    ::= { dot11PhyHTEntry 7 }

dot11GreenfieldOptionEnabled OBJECT-TYPE
	SYNTAX TruthValue
	MAX-ACCESS read-write
	STATUS current
	DESCRIPTION
	    "This attribute, when TRUE, indicates that the HT Greenfield
	    option is enabled. The default value of this attribute is FALSE."
        DEFVAL { false }
    ::= { dot11PhyHTEntry 8 }

dot11ShortGIOptionInTwentyImplemented OBJECT-TYPE
	SYNTAX TruthValue
	MAX-ACCESS read-only
	STATUS current
	DESCRIPTION
	    "This attribute, when TRUE, indicates that the Short Guard
	    option is implemented for 20 MHz operation. The default value of this
	    attribute is FALSE."
        DEFVAL { false }
    ::= { dot11PhyHTEntry 9 }
		
dot11ShortGIOptionInTwentyEnabled OBJECT-TYPE
	SYNTAX TruthValue
	MAX-ACCESS read-write
	STATUS current
	DESCRIPTION
	    "This attribute, when TRUE, indicates that the Short Guard
	    option is enabled for 20 MHz operation. The default value of this attribute
	    is FALSE."
        DEFVAL { false }
    ::= { dot11PhyHTEntry 10 }

dot11ShortGIOptionInFortyImplemented OBJECT-TYPE
	SYNTAX TruthValue
	MAX-ACCESS read-only
	STATUS current
	DESCRIPTION
	    "This attribute, when TRUE, indicates that the Short Guard
	    option is implemented for 40 MHz operation. The default value of this
	    attribute is FALSE."
        DEFVAL { false }
    ::= { dot11PhyHTEntry 11 }

dot11ShortGIOptionInFortyEnabled OBJECT-TYPE
	SYNTAX TruthValue
	MAX-ACCESS read-write
	STATUS current
	DESCRIPTION
	    "This attribute, when TRUE, indicates that the Short Guard
	    option is enabled for 40 MHz operation. The default value of this attribute
	    is FALSE."
        DEFVAL { false }
    ::= { dot11PhyHTEntry 12 }

dot11LDPCCodingOptionImplemented OBJECT-TYPE
	SYNTAX TruthValue
	MAX-ACCESS read-only
	STATUS current
	DESCRIPTION
	    "This attribute, when TRUE, indicates that the LDPC coding
	    option is implemented. The default value of this attribute is FALSE."
        DEFVAL { false }
    ::= { dot11PhyHTEntry 13 }

dot11LDPCCodingOptionEnabled OBJECT-TYPE
	SYNTAX TruthValue
	MAX-ACCESS read-write
	STATUS current
	DESCRIPTION
	    "This attribute, when TRUE, indicates that the LDPC coding
	    option is enabled. The default value of this attribute is FALSE."
        DEFVAL { false }
    ::= { dot11PhyHTEntry 14 }

dot11TxSTBCOptionImplemented OBJECT-TYPE
	SYNTAX TruthValue
	MAX-ACCESS read-only
	STATUS current
	DESCRIPTION
	    "This attribute, when TRUE, indicates that the entity is
	    capable of transmitting frames using Space-Time Block Code (STBC) option.
	    The default value of this attribute is FALSE."
        DEFVAL { false }
    ::= { dot11PhyHTEntry 15 }

dot11TxSTBCOptionEnabled OBJECT-TYPE
	SYNTAX TruthValue
	MAX-ACCESS read-write
	STATUS current
	DESCRIPTION
	    "This attribute, when TRUE, indicates that the entity's
	    capability of transmitting frames using Space-Time Block Code (STBC) option
	    is enabled. The default value of this attribute is FALSE."
        DEFVAL { false }
    ::= { dot11PhyHTEntry 16 }

dot11RxSTBCOptionImplemented OBJECT-TYPE
	SYNTAX TruthValue
	MAX-ACCESS read-only
	STATUS current
	DESCRIPTION
	    "This attribute, when TRUE, indicates that the entity is
	    capable of receiving frames that are sent using the Space-Time Block Code
	    (STBC). The default value of this attribute is FALSE."
        DEFVAL { false }
    ::= { dot11PhyHTEntry 17 }

dot11RxSTBCOptionEnabled OBJECT-TYPE
	SYNTAX TruthValue
	MAX-ACCESS read-write
	STATUS current
	DESCRIPTION
	    "This attribute, when TRUE, indicates that the entity's
	    capability of receiving frames that are sent using the Space-Time Block Code
	    (STBC) is enabled. The default value of this attribute is FALSE."
        DEFVAL { false }
    ::= { dot11PhyHTEntry 18 }

dot11BeamFormingOptionImplemented OBJECT-TYPE
	SYNTAX TruthValue
	MAX-ACCESS read-only
	STATUS current
	DESCRIPTION
	    "This attribute, when TRUE, indicates that the Beam Forming
	    option is implemented. The default value of this attribute is FALSE."
        DEFVAL { false }
    ::= { dot11PhyHTEntry 19 }

dot11BeamFormingOptionEnabled OBJECT-TYPE
	SYNTAX TruthValue
	MAX-ACCESS read-write
	STATUS current
	DESCRIPTION
	    "This attribute, when TRUE, indicates that the Beam Forming
	    option is enabled. The default value of this attribute is FALSE."
        DEFVAL { false }
    ::= { dot11PhyHTEntry 20 }

dot11HighestSupportedDataRate OBJECT-TYPE
	SYNTAX INTEGER (0..600)
	MAX-ACCESS read-write
	STATUS current
	DESCRIPTION
	    "This attribute shall specify the Highest Data Rate in Mb/s at
	    which the station may receive data. The default value of this attribute shall
	    be 0."
        DEFVAL { 0 }
    ::= { dot11PhyHTEntry 21 }

dot11TxMCSSetDefined OBJECT-TYPE
	SYNTAX TruthValue
	MAX-ACCESS read-write
	STATUS current
	DESCRIPTION
	    "This attribute, when TRUE, indicates that the Tx MCS set is
	    defined. The default value of this attribute is FALSE."
        DEFVAL { false }
    ::= { dot11PhyHTEntry 22 }

dot11TxRxMCSSetNotEqual OBJECT-TYPE
	SYNTAX TruthValue
	MAX-ACCESS read-write
	STATUS current
	DESCRIPTION
	    "This attribute, when TRUE, indicates that the supported Tx
	    and Rx MCS sets are not equal. The default value of this attribute is FALSE."
        DEFVAL { false }
    ::= { dot11PhyHTEntry 23 }

dot11TxMaximumNumberSpatialStreamsSupported OBJECT-TYPE
	SYNTAX INTEGER (0..3)
	MAX-ACCESS read-write
	STATUS current
	DESCRIPTION
	    "This attribute indicates the Tx maximum number of spatial
	    streams supported. The default value of this attribute is 0."
        DEFVAL { 0 }
    ::= { dot11PhyHTEntry 24 }

dot11TxUnequalModulationSupported OBJECT-TYPE
	SYNTAX TruthValue
	MAX-ACCESS read-write
	STATUS current
	DESCRIPTION
	    "This attribute, when TRUE, indicates that Tx unequal
	    modulation is supported. The default value of this attribute is FALSE."
        DEFVAL { false }
    ::= { dot11PhyHTEntry 25 }	     
	    
-- **********************************************************************
-- * End of dot11 PHY HT TABLE
-- **********************************************************************

-- **********************************************************************
-- * dot11 Supported MCS Tx TABLE
-- **********************************************************************
dot11SupportedMCSTxTable OBJECT-TYPE
	SYNTAX SEQUENCE OF Dot11SupportedMCSTxEntry
	MAX-ACCESS not-accessible
	STATUS current
	DESCRIPTION
	    "The Transmit MCS supported by the PLCP and PMD, represented by a
	    count from 1 to 127, subject to limitations of each individual PHY."
    ::= { dot11phy 16 }

dot11SupportedMCSTxEntry OBJECT-TYPE
	SYNTAX Dot11SupportedMCSTxEntry
	MAX-ACCESS not-accessible
	STATUS current
	DESCRIPTION
	    "An Entry (conceptual row) in the dot11SupportedMCSTx Table.
	    ifIndex - Each IEEE 802.11 interface is represented by an
	    ifEntry. Interface tables in this MIB module are indexed by
	    ifIndex."
	INDEX { ifIndex,
	    dot11SupportedMCSTxIndex }
    ::= { dot11SupportedMCSTxTable 1 }
		
Dot11SupportedMCSTxEntry ::= SEQUENCE {
	    dot11SupportedMCSTxIndex	Integer32,
	    dot11SupportedMCSTxValue	Integer32 }
	    
dot11SupportedMCSTxIndex OBJECT-TYPE
	SYNTAX Integer32 (1..255)
        MAX-ACCESS read-only
	STATUS current
	DESCRIPTION
	    "Index object that identifies which MCS to access. Range is
	    1..255."
    ::= { dot11SupportedMCSTxEntry 1 }

dot11SupportedMCSTxValue OBJECT-TYPE
	SYNTAX Integer32 (1..127)
	MAX-ACCESS read-only
	STATUS current
	DESCRIPTION
	    "The Transmit MCS supported by the PLCP and PMD, represented
	    by a count from 1 to 127, subject to limitations of each individual PHY."
    ::= { dot11SupportedMCSTxEntry 2 }
		
-- **********************************************************************
-- * End of dot11 Supported MCS Tx TABLE
-- **********************************************************************

-- **********************************************************************
-- * dot11 Supported MCS Rx TABLE
-- **********************************************************************

dot11SupportedMCSRxTable OBJECT-TYPE
	SYNTAX SEQUENCE OF Dot11SupportedMCSRxEntry
	MAX-ACCESS not-accessible
	STATUS current
	DESCRIPTION
	    "The receive MCS supported by the PLCP and PMD, represented by
	    a count from 1 to 127, subject to limitations of each individual PHY."
    ::= { dot11phy 17 }
		
dot11SupportedMCSRxEntry OBJECT-TYPE
	SYNTAX Dot11SupportedMCSRxEntry
	MAX-ACCESS not-accessible
	STATUS current
	DESCRIPTION
	    "An Entry (conceptual row) in the dot11SupportedMCSRx Table.
	    ifIndex - Each IEEE 802.11 interface is represented by an ifEntry. Interface
	    tables in this MIB module are indexed by ifIndex."
	INDEX {
	    ifIndex,
	    dot11SupportedMCSRxIndex }
    ::= { dot11SupportedMCSRxTable 1 }

Dot11SupportedMCSRxEntry ::= SEQUENCE {
	    dot11SupportedMCSRxIndex	Integer32,
	    dot11SupportedMCSRxValue	Integer32 }

dot11SupportedMCSRxIndex OBJECT-TYPE
	SYNTAX Integer32 (1..255)
        MAX-ACCESS read-only
	STATUS current
	DESCRIPTION
	    "Index object that identifies which MCS to access. Range is
	    1..255."
    ::= { dot11SupportedMCSRxEntry 1 }

dot11SupportedMCSRxValue OBJECT-TYPE
	SYNTAX Integer32 (1..127)
	MAX-ACCESS read-only
	STATUS current
	DESCRIPTION
	    "The receive MCS supported by the PLCP and PMD, represented by
	    a count from 1 to 127, subject to limitations of each individual PHY."
    ::= { dot11SupportedMCSRxEntry 2 }
		
-- **********************************************************************
-- * End of dot11 Supported MCS Rx TABLE
-- **********************************************************************

-- **********************************************************************
-- * dot11 Tx BF Config TABLE
-- **********************************************************************

dot11TxBFConfigTable OBJECT-TYPE
	SYNTAX SEQUENCE OF Dot11TxBFConfigEntry
	MAX-ACCESS not-accessible
	STATUS current
	DESCRIPTION
	    "Entry of attributes for dot11TxBFConfigTable. Implemented as
	    a table indexed on ifIndex to allow for multiple instances on an Agent."
    ::= { dot11phy 18 }

dot11TxBFConfigEntry OBJECT-TYPE
	SYNTAX Dot11TxBFConfigEntry
	MAX-ACCESS not-accessible
	STATUS current
	DESCRIPTION
	    "An entry in the dot11TxBFConfig Table.
	    ifIndex - Each 802.11 interface is represented by an ifEntry.
	    Interface tables in this MIB module are indexed by ifIndex."
	INDEX {ifIndex}
    ::= { dot11TxBFConfigTable 1 }

Dot11TxBFConfigEntry ::= SEQUENCE {
	    dot11ReceiveStaggerSoundingOptionImplemented			TruthValue,
	    dot11TransmitStaggerSoundingOptionImplemented 			TruthValue,
	    dot11ReceiveNDPOptionImplemented 	    				TruthValue,
	    dot11TransmitNDPOptionImplemented 	    				TruthValue,
	    dot11ImplicitTxBFOptionImplemented 	    				TruthValue,
	    dot11CalibrationOptionImplemented 	    				INTEGER,
	    dot11ExplicitCSITxBFOptionImplemented 				TruthValue,
	    dot11ExplicitNonCompressedbeamformingMatrixOptionImplemented	TruthValue,
	    dot11ExplicitBFCSIFeedbackOptionImplemented 			INTEGER,
	    dot11ExplicitNonCompressedbeamformingMatrixFeedbackOptionImplemented INTEGER,
	    dot11ExplicitCompressedbeamformingMatrixFeedbackOptionImplemented	INTEGER,
	    dot11NumberBeamFormingCSISupportAntenna 				INTEGER,
	    dot11NumberNonCompressedbeamformingMatrixSupportAntenna 		INTEGER,
	    dot11NumberCompressedbeamformingMatrixSupportAntenna 	    	INTEGER,
	    dot11MaxCSIFeedbackDelay 	    					Unsigned32 }

dot11ReceiveStaggerSoundingOptionImplemented OBJECT-TYPE
	SYNTAX TruthValue
	MAX-ACCESS read-only
	STATUS current
	DESCRIPTION
	    "This attribute, when TRUE, indicates that the STA
	    implementation supports the receiving of staggered sounding frames. The
	    default value of this attribute is FALSE."
        DEFVAL { false }
    ::= { dot11TxBFConfigEntry 1 }
		
dot11TransmitStaggerSoundingOptionImplemented OBJECT-TYPE
	SYNTAX TruthValue
	MAX-ACCESS read-only
	STATUS current
	DESCRIPTION
	    "This attribute, when TRUE, indicates that the STA
	    implementation supports the transmission of staggered sounding frames. The
	    default value of this attribute is FALSE."
        DEFVAL { false }
    ::= { dot11TxBFConfigEntry 2 }

dot11ReceiveNDPOptionImplemented OBJECT-TYPE
	SYNTAX TruthValue
	MAX-ACCESS read-only
	STATUS current
	DESCRIPTION
	    "This attribute, when TRUE, indicates that the STA
	    implementation is capable of receiving NDP as sounding frames. The default
	    value of this attribute is FALSE."
        DEFVAL { false }
    ::= { dot11TxBFConfigEntry 3 }

dot11TransmitNDPOptionImplemented OBJECT-TYPE
	SYNTAX TruthValue
	MAX-ACCESS read-only
	STATUS current
	DESCRIPTION
	    "This attribute, when TRUE, indicates that the STA
	    implementation is capable of transmitting NDP as sounding frames. The
	    default value of this attribute is FALSE."
        DEFVAL { false }
    ::= { dot11TxBFConfigEntry 4 }

dot11ImplicitTxBFOptionImplemented OBJECT-TYPE
	SYNTAX TruthValue
	MAX-ACCESS read-only
	STATUS current
	DESCRIPTION
	    "This attribute, when TRUE, indicates that STA implementation
	    is capable of applying implicit transmit beamforming. The default value of
	    this attribute is FALSE."
        DEFVAL { false }
    ::= { dot11TxBFConfigEntry 5 }

dot11CalibrationOptionImplemented OBJECT-TYPE
	SYNTAX INTEGER { inCapable (0), unableToInitiate (1),
		ableToInitiate (2), fullyCapable (3) }
	MAX-ACCESS read-only
	STATUS current
	DESCRIPTION
	    "This attribute indicates the level of calibration supported
	    by the STA implementation. The default value of this attribute is 0."
        DEFVAL { inCapable }
    ::= { dot11TxBFConfigEntry 6 }

dot11ExplicitCSITxBFOptionImplemented OBJECT-TYPE
	SYNTAX TruthValue
	MAX-ACCESS read-only
	STATUS current
	DESCRIPTION
	    "This attribute, when TRUE, indicates that STA implementation
	    is capable of applying transmit beamforming using CSI explicit feedback in
	    its transmission. The default value of this attribute is FALSE."
        DEFVAL { false }
    ::= { dot11TxBFConfigEntry 7 }

dot11ExplicitNonCompressedbeamformingMatrixOptionImplemented OBJECT-TYPE
	SYNTAX TruthValue
	MAX-ACCESS read-only
	STATUS current
	DESCRIPTION
	    "This attribute, when TRUE, indicates that STA implementation
	    is capable of applying transmit beamforming using non-compressed beamforming
	    matrix explicit feedback in its transmission. The default value of this
	    attribute is FALSE."
        DEFVAL { false }
    ::= { dot11TxBFConfigEntry 8 }

dot11ExplicitBFCSIFeedbackOptionImplemented OBJECT-TYPE
	SYNTAX INTEGER { inCapable (0), delayed (1), immediate (2),
	    unsolicitedImmediate (3), aggregated (4), delayedAggregated (5),
	    immediateAggregated(6), unsolicitedImmediateAggregated (7) }
	MAX-ACCESS read-only
	STATUS current
	DESCRIPTION
	    "This attribute indicates the level of CSI explicit feedback
	    returned by the STA implementation. The default value of this attribute is
	    0."
        DEFVAL { inCapable }
    ::= { dot11TxBFConfigEntry 9 }

dot11ExplicitNonCompressedbeamformingMatrixFeedbackOptionImplemented OBJECT-TYPE
	SYNTAX INTEGER { inCapable (0), delayed (1), immediate (2),
	    unsolicitedImmediate (3), aggregated (4), delayedAggregated (5),
	    immediateAggregated(6), unsolicitedImmediateAggregated (7) }
	MAX-ACCESS read-only
	STATUS current
	DESCRIPTION
	    "This attribute indicates the level of non-compressed
	    beamforming matrix explicit feedback returned by the STA implementation. The
	    default value of this attribute is 0."
        DEFVAL { inCapable }
    ::= { dot11TxBFConfigEntry 10 }

dot11ExplicitCompressedbeamformingMatrixFeedbackOptionImplemented OBJECT-TYPE
	SYNTAX INTEGER { inCapable (0), delayed (1), immediate (2),
	    unsolicitedImmediate (3), aggregated (4), delayedAggregated (5),
	    immediateAggregated(6), unsolicitedImmediateAggregated (7) }
	MAX-ACCESS read-only
	STATUS current
	DESCRIPTION
	    "This attribute indicates the level of non-compressed
	    beamforming matrix explicit feedback returned by the STA implementation. The
	    default value of this attribute is 0."
        DEFVAL { inCapable }
    ::= { dot11TxBFConfigEntry 11 }

dot11NumberBeamFormingCSISupportAntenna OBJECT-TYPE
	SYNTAX INTEGER (1..4)
	MAX-ACCESS read-only
	STATUS current
	DESCRIPTION
	    "This attribute indicates the maximum number of beamform
	    antennas the beamformee can support when CSI feedback is required."
    ::= { dot11TxBFConfigEntry 12 }

dot11NumberNonCompressedbeamformingMatrixSupportAntenna OBJECT-TYPE
	SYNTAX INTEGER (1..4)
	MAX-ACCESS read-only
	STATUS current
	DESCRIPTION
	    "This attribute indicates the maximum number of beamform
	    antennas the beamformee can support when non-compressed beamforming matrix
	    feedback is required."
    ::= { dot11TxBFConfigEntry 13 }

dot11NumberCompressedbeamformingMatrixSupportAntenna OBJECT-TYPE
	SYNTAX INTEGER (1..4)
	MAX-ACCESS read-only
	STATUS current
	DESCRIPTION
	    "This attribute indicates the maximum number of beamform
	    antennas the beamformee can support when compressed beamforming matrix
	    feedback is required."
    ::= { dot11TxBFConfigEntry 14 }

dot11MaxCSIFeedbackDelay OBJECT-TYPE
	SYNTAX Unsigned32 (1..4294967295)
	MAX-ACCESS read-only
	STATUS current
	DESCRIPTION
	    "This attribute indicates the maximum allowed delay in
	    microseconds between the transmission time of a sounding packet and the time
	    a feedback response arrives (9.17.3 (Explicit feedback beamforming))"
    ::= { dot11TxBFConfigEntry 15 }

-- **********************************************************************
-- * End of dot11 Tx BF Config TABLE
-- **********************************************************************

-- **********************************************************************
-- *    dot11PhyDSSSEntry  TABLE
-- **********************************************************************
dot11PhyDSSSTable OBJECT-TYPE
        SYNTAX SEQUENCE OF Dot11PhyDSSSEntry
        MAX-ACCESS not-accessible
        STATUS current
        DESCRIPTION

            "Entry of attributes for dot11PhyDSSSEntry.  Implemented as a
            table indexed on ifIndex allow for multiple instances on
            an Agent."

    ::= {  dot11phy 5 }

dot11PhyDSSSEntry OBJECT-TYPE
        SYNTAX Dot11PhyDSSSEntry
        MAX-ACCESS not-accessible
        STATUS current
        DESCRIPTION
            "An entry in the dot11PhyDSSSEntry Table.

            ifIndex - Each 802.11 interface is represented by an
            ifEntry.  Interface tables in this MIB module are indexed
            by ifIndex."
        INDEX {ifIndex}
    ::= {  dot11PhyDSSSTable 1 }

Dot11PhyDSSSEntry ::= SEQUENCE {
             dot11CurrentChannel    INTEGER,
             dot11CCAModeSupported  INTEGER,
             dot11CurrentCCAMode    INTEGER,
             dot11EDThreshold       Integer32}

dot11CurrentChannel OBJECT-TYPE
        SYNTAX INTEGER (1..14)
        MAX-ACCESS read-write
        STATUS current
        DESCRIPTION
            "The current operating frequency channel of the DSSS
            PHY. Valid channel numbers are as defined in 15.4.6.2"
    ::= {   dot11PhyDSSSEntry 1 }

dot11CCAModeSupported OBJECT-TYPE
        SYNTAX INTEGER (1..7)
        MAX-ACCESS read-only
        STATUS current
        DESCRIPTION
        "dot11CCAModeSupported is a bit-significant value, representing all of the CCA modes supported by the PHY.  Valid values are:
		energy detect only (ED-ONLY) = 01,
		carrier sense only (CS-ONLY) = 02,
		carrier sense and energy detect (ED-and-CS)= 04
	    or the logical sum of any of these values. This attribute shall
	    not be used to indicate the CCA modes supported by a higher rate
	    extension PHY. Rather, the dot11HRCCAModeSupported attribute shall
	    be used to indicate the CCA modes of the higher rate extension PHY."
    ::= {   dot11PhyDSSSEntry 2 }

dot11CurrentCCAMode OBJECT-TYPE
	SYNTAX INTEGER {edonly(1), csonly(2), edandcs(4), cswithtimer(8),
	hrcsanded(16) }
	MAX-ACCESS read-write
	STATUS current
	
	DESCRIPTION
	"The current CCA method in operation. Valid values are:
	    energy detect only (edonly) = 01,
	    carrier sense only (csonly) = 02,
	    carrier sense and energy detect (edandcs)= 04.
	    carrier sense with timer (cswithtimer)= 08
	    high rate carrier sense and energy detect (hrcsanded)= 16"
::= { dot11PhyDSSSEntry 3 }

dot11EDThreshold OBJECT-TYPE
        SYNTAX Integer32
        MAX-ACCESS read-write
        STATUS current
        DESCRIPTION
            "The current Energy Detect Threshold being used by the DSSS PHY."
    ::= {   dot11PhyDSSSEntry 4 }

-- **********************************************************************
-- * End of dot11PhyHRDSSSEntry TABLE
-- **********************************************************************

-- **********************************************************************
-- *    dot11PhyIR  TABLE
-- **********************************************************************

dot11PhyIRTable OBJECT-TYPE
        SYNTAX SEQUENCE OF Dot11PhyIREntry
        MAX-ACCESS not-accessible
        STATUS current
        DESCRIPTION

            "Group of attributes for dot11PhyIRTable.  Implemented as a
            table indexed on ifIndex to allow for multiple instances on
            an Agent."

    ::= {  dot11phy 6 }

dot11PhyIREntry OBJECT-TYPE
        SYNTAX Dot11PhyIREntry
        MAX-ACCESS not-accessible
        STATUS current
        DESCRIPTION
            "An entry in the dot11PhyIR Table.

            ifIndex - Each 802.11 interface is represented by an
            ifEntry.  Interface tables in this MIB module are indexed
            by ifIndex."
        INDEX {ifIndex}
    ::= {  dot11PhyIRTable 1 }

Dot11PhyIREntry ::= SEQUENCE {
             dot11CCAWatchdogTimerMax       Integer32,
             dot11CCAWatchdogCountMax       Integer32,
             dot11CCAWatchdogTimerMin       Integer32,
             dot11CCAWatchdogCountMin       Integer32}

dot11CCAWatchdogTimerMax OBJECT-TYPE
        SYNTAX Integer32
        MAX-ACCESS read-write
        STATUS current
        DESCRIPTION

            "This parameter, together with CCAWatchdogCountMax,
            determines when energy detected in the channel can be
            ignored."

    ::= {   dot11PhyIREntry 1 }

dot11CCAWatchdogCountMax OBJECT-TYPE
        SYNTAX Integer32
        MAX-ACCESS read-write
        STATUS current
        DESCRIPTION

            "This parameter, together with CCAWatchdogTimerMax,
            determines when energy detected in the channel can be
            ignored."

    ::= {   dot11PhyIREntry 2 }

dot11CCAWatchdogTimerMin OBJECT-TYPE
        SYNTAX Integer32
        MAX-ACCESS read-write
        STATUS current
        DESCRIPTION

            "The minimum value to which CCAWatchdogTimerMax can be
            set."

    ::= {   dot11PhyIREntry 3 }

dot11CCAWatchdogCountMin OBJECT-TYPE
        SYNTAX Integer32
        MAX-ACCESS read-write
        STATUS current
        DESCRIPTION
            "The minimum value to which CCAWatchdogCount can be set."
    ::= {   dot11PhyIREntry 4 }


-- **********************************************************************
-- *    End of dot11PhyIR  TABLE
-- **********************************************************************

-- **********************************************************************
-- *    dot11RegDomainsSupported  TABLE
-- **********************************************************************
dot11RegDomainsSupportedTable OBJECT-TYPE
        SYNTAX SEQUENCE OF Dot11RegDomainsSupportEntry
        MAX-ACCESS not-accessible
        STATUS current
        DESCRIPTION

            "There are different operational requirements dependent on
            the regulatory domain.  This attribute list describes the
            regulatory domains the PLCP and PMD support in this
            implementation.  Currently defined values and their
            corresponding Regulatory Domains are:

            FCC (USA) = X'10', DOC (Canada) = X'20', ETSI (most of
            Europe) = X'30', Spain = X'31', France = X'32', MKK
            (Japan) = X'40', Other=X'00' "

    ::= {   dot11phy 7}

dot11RegDomainsSupportEntry OBJECT-TYPE
        SYNTAX Dot11RegDomainsSupportEntry
        MAX-ACCESS not-accessible
        STATUS current
        DESCRIPTION
            "An entry in the dot11RegDomainsSupport Table.

            ifIndex - Each 802.11 interface is represented by an
            ifEntry.  Interface tables in this MIB module are indexed
            by ifIndex."
        INDEX {ifIndex, dot11RegDomainsSupportIndex}
    ::= {  dot11RegDomainsSupportedTable 1 }

Dot11RegDomainsSupportEntry ::= SEQUENCE {
             dot11RegDomainsSupportIndex    Integer32,
             dot11RegDomainsSupportValue    INTEGER}

dot11RegDomainsSupportIndex OBJECT-TYPE
        SYNTAX Integer32 (1..2147483647)
        MAX-ACCESS read-only
        STATUS current
        DESCRIPTION
            "The auxiliary variable used to identify instances
            of the columnar objects in the RegDomainsSupport Table."
    ::= {  dot11RegDomainsSupportEntry 1 }

dot11RegDomainsSupportValue OBJECT-TYPE

        SYNTAX INTEGER {fcc(16), doc(32), etsi(48), spain (49), france
        (50), mkk (64) }
        MAX-ACCESS read-only
        STATUS current
        DESCRIPTION
            "There are different operational requirements dependent on
            the regulatory domain.  This attribute list describes the
            regulatory domains the PLCP and PMD support in this
            implementation.  Currently de- fined values and their
            corresponding Regulatory Domains are:

            FCC (USA) = X'10', DOC (Canada) = X'20', ETSI (most of
            Europe) = X'30', Spain = X'31', France = X'32', MKK
            (Japan) = X'40' "
    ::= {  dot11RegDomainsSupportEntry 2 }

-- **********************************************************************
-- *    End of dot11RegDomainsSupported  TABLE
-- **********************************************************************

-- **********************************************************************
-- *    dot11AntennasList  TABLE
-- **********************************************************************
dot11AntennasListTable OBJECT-TYPE
        SYNTAX SEQUENCE OF Dot11AntennasListEntry
        MAX-ACCESS not-accessible
        STATUS current
        DESCRIPTION
"This table represents the list of antennae.  An antenna can be marked to be capable of transmitting, receiving, and/or for participation in receive diversity.  Each entry in this table represents a single antenna with its properties.  The maximum number of antennae that can be contained in this table is 255."
    ::= {   dot11phy 8 }

dot11AntennasListEntry OBJECT-TYPE
        SYNTAX Dot11AntennasListEntry
        MAX-ACCESS not-accessible
        STATUS current
        DESCRIPTION
            "An entry in the dot11AntennasListTable, representing the properties of a single antenna.

            ifIndex - Each 802.11 interface is represented by an
            ifEntry.  Interface tables in this MIB module are indexed
            by ifIndex."
        INDEX {ifIndex, dot11AntennaListIndex}
    ::= {  dot11AntennasListTable 1 }

Dot11AntennasListEntry ::= SEQUENCE {
             dot11AntennaListIndex     Integer32,
             dot11SupportedTxAntenna   TruthValue,
             dot11SupportedRxAntenna   TruthValue,
             dot11DiversitySelectionRx TruthValue }

dot11AntennaListIndex OBJECT-TYPE
        SYNTAX Integer32 (1..255)
        MAX-ACCESS read-only
        STATUS current
        DESCRIPTION
            "The unique index of an antenna which is used to identify the columnar objects in the dot11AntennasList Table."
    ::= {  dot11AntennasListEntry 1 }

dot11SupportedTxAntenna OBJECT-TYPE
        SYNTAX TruthValue
        MAX-ACCESS read-write
        STATUS current
        DESCRIPTION

            "When true, this object indicates that the antenna represented by dot11AntennaIndex can be used as a transmit antenna."

    ::= {  dot11AntennasListEntry 2 }

dot11SupportedRxAntenna OBJECT-TYPE
        SYNTAX TruthValue
        MAX-ACCESS read-write
        STATUS current
        DESCRIPTION

            "When true, this object indocates that the antenna represented by the dot11AntennaIndex xan be used as a receive antenna."

    ::= {  dot11AntennasListEntry 3 }

dot11DiversitySelectionRx OBJECT-TYPE
        SYNTAX TruthValue
        MAX-ACCESS read-write
        STATUS current
        DESCRIPTION

            "When true, this object indicates that the antenna represented by dot11AntennaIndex can be used for receive diversity.  This object may only be true if the antenna can be used as a receive antenna, as indicated by dot11SupportedRxAntenna."

    ::= {  dot11AntennasListEntry 4 }

-- **********************************************************************
-- *    End of dot11AntennasList  TABLE
-- **********************************************************************


-- **********************************************************************
-- *    SupportedDataRatesTx  TABLE
-- **********************************************************************
dot11SupportedDataRatesTxTable OBJECT-TYPE
        SYNTAX SEQUENCE OF Dot11SupportedDataRatesTxEntry
        MAX-ACCESS not-accessible
        STATUS current
        DESCRIPTION

            "The Transmit bit rates supported by the PLCP and PMD,
            represented by a count from X'02-X'7f, corresponding to data
            rates in increments of 500Kb/s from 1 Mb/s to 63.5 Mb/s subject
            to limitations of each individual PHY."

    ::= {  dot11phy 9 }

dot11SupportedDataRatesTxEntry OBJECT-TYPE
        SYNTAX Dot11SupportedDataRatesTxEntry
        MAX-ACCESS not-accessible
        STATUS current
        DESCRIPTION

            "An Entry (conceptual row) in the dot11SupportedDataRatesTx
            Table.

            ifIndex - Each 802.11 interface is represented by an
            ifEntry.  Interface tables in this MIB module are indexed
            by ifIndex."
        INDEX {ifIndex, dot11SupportedDataRatesTxIndex}
    ::= {  dot11SupportedDataRatesTxTable  1 }

Dot11SupportedDataRatesTxEntry ::= SEQUENCE {
            dot11SupportedDataRatesTxIndex  Integer32,
            dot11SupportedDataRatesTxValue  Integer32}

dot11SupportedDataRatesTxIndex OBJECT-TYPE
        SYNTAX Integer32 (1..255)
        MAX-ACCESS read-only
        STATUS current
        DESCRIPTION

            "Index object which identifies which data rate to access.
            Range is 1..255."

    ::= {  dot11SupportedDataRatesTxEntry 1 }

dot11SupportedDataRatesTxValue OBJECT-TYPE
        SYNTAX Integer32 (2..127)
        MAX-ACCESS read-only
        STATUS current
        DESCRIPTION

            "The Transmit bit rates supported by the PLCP and PMD,
            represented by a count from X'02-X'7f, corresponding to data
            rates in increments of 500Kb/s from 1 Mb/s to 63.5 Mb/s subject
            to limitations of each individual PHY."

    ::= {  dot11SupportedDataRatesTxEntry 2 }

-- **********************************************************************
-- *    End of dot11SupportedDataRatesTx  TABLE
-- **********************************************************************

-- **********************************************************************
-- *    SupportedDataRatesRx  TABLE
-- **********************************************************************
dot11SupportedDataRatesRxTable OBJECT-TYPE
        SYNTAX SEQUENCE OF Dot11SupportedDataRatesRxEntry
        MAX-ACCESS not-accessible
        STATUS current
        DESCRIPTION
            "The receive bit rates supported by the PLCP and PMD,
            represented by a count from X'002-X'7f, corresponding to data
            rates in increments of 500Kb/s from 1 Mb/s to 63.5 Mb/s."

    ::= {  dot11phy 10 }

dot11SupportedDataRatesRxEntry OBJECT-TYPE
        SYNTAX Dot11SupportedDataRatesRxEntry
        MAX-ACCESS not-accessible
        STATUS current
        DESCRIPTION

            "An Entry (conceptual row) in the
        dot11SupportedDataRatesRx Table.

            ifIndex - Each 802.11 interface is represented by an
            ifEntry.  Interface tables in this MIB module are indexed
            by ifIndex."
        INDEX {ifIndex, dot11SupportedDataRatesRxIndex}
    ::= {  dot11SupportedDataRatesRxTable  1 }

Dot11SupportedDataRatesRxEntry ::= SEQUENCE {
            dot11SupportedDataRatesRxIndex  Integer32,
            dot11SupportedDataRatesRxValue  Integer32}

dot11SupportedDataRatesRxIndex OBJECT-TYPE
        SYNTAX Integer32 (1..255)
        MAX-ACCESS read-only
        STATUS current
        DESCRIPTION
            "Index object which identifies which data rate to access.
            Range is 1..255."
    ::= {  dot11SupportedDataRatesRxEntry 1 }

dot11SupportedDataRatesRxValue OBJECT-TYPE
        SYNTAX Integer32 (2..127)
        MAX-ACCESS read-only
        STATUS current
        DESCRIPTION
            "The receive bit rates supported by the PLCP and PMD,
            represented by a count from X'02-X'7f, corresponding to data
            rates in increments of 500Kb/s from 1 Mb/s to 63.5 Mb/s."
    ::= {  dot11SupportedDataRatesRxEntry 2 }

-- **********************************************************************
-- *    End of dot11SupportedDataRatesRx  TABLE
-- **********************************************************************

--**********************************************************************
-- * dot11PhyOFDM TABLE
--**********************************************************************
dot11PhyOFDMTable OBJECT-TYPE
	SYNTAX SEQUENCE OF Dot11PhyOFDMEntry
	MAX-ACCESS not-accessible
	STATUS current
	
	DESCRIPTION
	    "Group of attributes for dot11PhyOFDMTable. Implemented as a
	    table indexed on ifindex to allow for multiple instances on
	    an Agent."
::= {dot11phy 11}

dot11PhyOFDMEntry OBJECT-TYPE
	SYNTAX Dot11PhyOFDMEntry
	MAX-ACCESS not-accessible
	STATUS current
	
	DESCRIPTION
	    "An entry in the dot11PhyOFDM Table.
	    ifIndex - Each IEEE 802.11 interface is represented by an
	    ifEntry. Interface tables in this MIB module are indexed
	    by ifIndex."
	INDEX {ifIndex}
::= {dot11PhyOFDMTable 1}

Dot11PhyOFDMEntry ::= SEQUENCE {
	    dot11CurrentFrequency		INTEGER,
	    dot11TIThreshold			Integer32,
	    dot11FrequencyBandsSupported INTEGER}
	    
dot11CurrentFrequency OBJECT-TYPE
	SYNTAX INTEGER (0..255)
	MAX-ACCESS read-write
	STATUS current
	
	DESCRIPTION
	    "The number of the current operating frequency channel of the OFDM PHY."
::= {dot11PhyOFDMEntry 1}

dot11TIThreshold OBJECT-TYPE
	SYNTAX Integer32
	MAX-ACCESS read-write
	STATUS current
	
	DESCRIPTION
	    "The Threshold being used to detect a busy medium (frequency).
	    CCA shall report a busy medium upon detecting the RSSI above this threshold."
::= {dot11PhyOFDMEntry 2}

dot11FrequencyBandsSupported OBJECT-TYPE
	SYNTAX INTEGER (1..7)
	MAX-ACCESS read-only
	STATUS current
	DESCRIPTION
	    "The capability of the OFDM PHY implementation to operate in the three U-NII
	    bands. Coded as an integer value of a three bit field as follows:
	    bit 0 .. capable of operating in the lower (5.15-5.25 GHz) U-NII band
	    bit 1 .. capable of operating in the middle (5.25-5.35 GHz) U-NII band
	    bit 2 .. capable of operating in the upper (5.725-5.825 GHz) U-NII band
	    For example, for an implementation capable of operating in the lower and mid
	    bands this attribute would take the value 3."
::= {dot11PhyOFDMEntry 3}

-- **********************************************************************
-- * End of dot11PhyOFDM TABLE
-- **********************************************************************

-- **********************************************************************
-- * dot11PhyHRDSSSEntry TABLE
-- **********************************************************************
dot11PhyHRDSSSTable OBJECT-TYPE
	SYNTAX SEQUENCE OF Dot11PhyHRDSSSEntry
	MAX-ACCESS not-accessible
	STATUS current
	
	DESCRIPTION
	    "Entry of attributes for dot11PhyHRDSSSEntry. Implemented as a
	    table indexed on ifIndex to allow for multiple instances on
	    an Agent."
::= { dot11phy 12 }

dot11PhyHRDSSSEntry OBJECT-TYPE
	SYNTAX Dot11PhyHRDSSSEntry
	MAX-ACCESS not-accessible
	STATUS current
	
	DESCRIPTION
	    "An entry in the dot11PhyHRDSSSEntry Table.
	    ifIndex - Each 802.11 interface is represented by an
	    ifEntry. Interface tables in this MIB module are indexed
	    by ifIndex."
	INDEX {ifIndex}
::= { dot11PhyHRDSSSTable 1 }

Dot11PhyHRDSSSEntry ::= SEQUENCE {
	    dot11ShortPreambleOptionImplemented	TruthValue,
	    dot11PBCCOptionImplemented		TruthValue,
	    dot11ChannelAgilityPresent		TruthValue,
	    dot11ChannelAgilityEnabled		TruthValue,
	    dot11HRCCAModeSupported		INTEGER }

dot11ChannelAgilityPresent OBJECT-TYPE
	SYNTAX TruthValue
	MAX-ACCESS read-only
	STATUS current
	DESCRIPTION
	    "This attribute indicates that the PHY is capable of channel agility."
    ::= { dot11PhyHRDSSSEntry 3}

dot11ChannelAgilityEnabled OBJECT-TYPE
	SYNTAX TruthValue
	MAX-ACCESS read-only
	STATUS current
	DESCRIPTION
	    "This attribute indicates that the PHY channel agility functionality
	    is enabled."
::= { dot11PhyHRDSSSEntry 4 }

dot11HRCCAModeSupported OBJECT-TYPE
	SYNTAX INTEGER (1..31)
	MAX-ACCESS read-only
	STATUS current
	DESCRIPTION
	    "dot11HRCCAModeSupported is a bit-significant value, representing all of
	    the CCA modes supported by the PHY. Valid values are:
	    energy detect only (ED_ONLY) = 01,
	    carrier sense only (CS_ONLY) = 02,
	    carrier sense and energy detect (ED_and_CS)= 04
	    carrier sense with timer (CS_and_Timer)= 08
	    high rate carrier sense and energy detect (HRCS_and_ED)= 16
	    or the logical sum of any of these values. In the high rate extension
	    PHY, this attribute shall be used in preference to the
	    dot11CCAModeSupported attribute."
::= { dot11PhyHRDSSSEntry 5 }

dot11ShortPreambleOptionImplemented OBJECT-TYPE
	SYNTAX TruthValue
	MAX-ACCESS read-only
	STATUS current
	DESCRIPTION
	    "This attribute, when true, shall indicate that the short preamble
	    option as defined in subclause 18.2.2.2 is implemented. The default
	    value of this attribute shall be false."
::= {dot11PhyHRDSSSEntry 16 }

dot11PBCCOptionImplemented OBJECT-TYPE
	SYNTAX TruthValue
	MAX-ACCESS read-only
	STATUS current
	DESCRIPTION
	    "This attribute, when true, shall indicate that the PBCC modulation
	    option as defined in subclause 18.4.6.6 is implemented. The default
	    value of this attribute shall be false."
::= {dot11PhyHRDSSSEntry 27 }

-- **********************************************************************
-- *   conformance information
-- **********************************************************************

dot11Conformance  OBJECT IDENTIFIER
    ::= { ieee802dot11 5 }
dot11Groups  OBJECT IDENTIFIER ::= { dot11Conformance 1 }
dot11Compliances  OBJECT IDENTIFIER ::= { dot11Conformance 2 }

-- **********************************************************************
-- *   compliance statements
-- **********************************************************************
dot11Compliance MODULE-COMPLIANCE
        STATUS  current
        DESCRIPTION
            "The compliance statement for SNMPv2 entities
            that implement the IEEE 802.11 MIB."

  MODULE  -- this module
	MANDATORY-GROUPS {
-- 	    dot11SMTbase8,
	    dot11MACbase3, dot11CountersGroup3,
	    dot11SmtAuthenticationAlgorithms, 
	    dot11ResourceTypeID, dot11PhyOperationComplianceGroup }

GROUP dot11PhyDSSSComplianceGroup
        DESCRIPTION
               "Implementation of this group is required when object
               dot11PHYType has the value of dsss.  This group is
               mutually exclusive with the groups
               dot11PhyIRComplianceGroup and
               dot11PhyFHSSComplianceGroup."

GROUP dot11PhyIRComplianceGroup
        DESCRIPTION
               "Implementation of this group is required when object
               dot11PHYType has the value of irbaseband.  This group is
               mutually exclusive with the groups
               dot11PhyDSSSComplianceGroup and
               dot11PhyFHSSComplianceGroup."


GROUP dot11PhyFHSSComplianceGroup
        DESCRIPTION
               "Implementation of this group is required when object
               dot11PHYType has the value of fhss.  This group is
               mutually exclusive with the groups
               dot11PhyDSSSComplianceGroup and
               dot11PhyIRComplianceGroup."

GROUP dot11PhyHRDSSSComplianceGroup
	DESCRIPTION
		"Implementation of this group is required when object
		dot11PHYType has the value of hrdsss. This group is
		mutually exclusive with the groups dot11PhyDSSSComplianceGroup,
		dot11PhyIRComplianceGroup and dot11PhyFHSSComplianceGroup."

-- GROUP dot11PhyHTComplianceGroup
-- 	DESCRIPTION
-- 	    	"Implementation of this group is required when object
-- 	    	dot11PHYType has the value of ht. This group is mutually exclusive with the
-- 	    	groups dot11PhyIRComplianceGroup and dot11PhyFHSSComplianceGroup"
-- 
    -- OPTIONAL-GROUPS { dot11SMTprivacy, dot11MACStatistics,
    --  dot11PhyAntennaComplianceGroup, dot11PhyTxPowerComplianceGroup,
    --  dot11PhyRegDomainsSupportGroup,
    --  dot11PhyAntennasListGroup, dot11PhyRateGroup,
    --  dot11SMTbase3, dot11MultiDomainCapabilityGroup,
    --  dot11PhyFHSSComplianceGroup2, dot11RSNAadditions,
    --  dot11RegulatoryClassesGroup, dot11Qosadditions,
    --  dot11FTComplianceGroup,
    -- 	dot11PhyAntennaComplianceGroup2,
    -- 	dot11SMTbase9,
    -- 	dot11HTMACadditions,
    -- 	dot11PhyMCSGroup,
    -- 	dot11TxBFGroup }

::= { dot11Compliances 1 }

-- **********************************************************************
-- *   Groups - units of conformance
-- **********************************************************************
dot11SMTbase OBJECT-GROUP
	OBJECTS { dot11StationID, dot11MediumOccupancyLimit, 
	    dot11CFPollable,
            dot11CFPPeriod,
            dot11CFPMaxDuration,
            dot11AuthenticationResponseTimeOut,
	    dot11PrivacyOptionImplemented,
	    dot11PowerManagementMode,
	    dot11DesiredSSID, dot11DesiredBSSType,
	    dot11OperationalRateSet,
	    dot11BeaconPeriod, dot11DTIMPeriod,
	 dot11AssociationResponseTimeOut 
             }
	STATUS deprecated
	DESCRIPTION
	     "The SMT object class provides the necessary support at the
	     STA to manage the processes in the STA such that the STA may
	     work cooperatively as a part of an IEEE 802.11 network."
    ::= {dot11Groups 1   }

dot11SMTprivacy OBJECT-GROUP
        OBJECTS { dot11PrivacyInvoked, 
	    dot11WEPKeyMappingLength, dot11ExcludeUnencrypted,
	    dot11WEPICVErrorCount , dot11WEPExcludedCount ,
	    dot11WEPDefaultKeyID,
	    dot11WEPDefaultKeyValue,
	    dot11WEPKeyMappingWEPOn,
	    dot11WEPKeyMappingValue , dot11WEPKeyMappingAddress,
	    dot11WEPKeyMappingStatus }

        STATUS current
        DESCRIPTION
            "The SMTPrivacy package is a set of attributes that shall be
            present if WEP is implemented in the STA."
    ::= {dot11Groups 2 }

dot11MACbase OBJECT-GROUP
        OBJECTS { dot11MACAddress, dot11Address,
	    dot11GroupAddressesStatus,
	    dot11RTSThreshold, dot11ShortRetryLimit,
	    dot11LongRetryLimit, dot11FragmentationThreshold,
	    dot11MaxTransmitMSDULifetime,
	    dot11MaxReceiveLifetime, dot11ManufacturerID,
                dot11ProductID
                }
        STATUS deprecated
        DESCRIPTION
	    "The MAC object class provides the necessary support for the
	    access control, generation, and verification of frame check
	    sequences, and proper delivery of valid data to upper
	    layers."
::= {dot11Groups 3 }


dot11MACStatistics OBJECT-GROUP

	OBJECTS { dot11RetryCount, dot11MultipleRetryCount,
            dot11RTSSuccessCount, dot11RTSFailureCount,
            dot11ACKFailureCount, dot11FrameDuplicateCount }

        STATUS current
        DESCRIPTION
            "The MACStatistics package provides extended statistical
            information on the operation of the MAC.  This 
            package is completely optional."
    ::= {dot11Groups 4 }

dot11ResourceTypeID OBJECT-GROUP
        OBJECTS { dot11ResourceTypeIDName, dot11manufacturerOUI,
            dot11manufacturerName, dot11manufacturerProductName,
            dot11manufacturerProductVersion }
        STATUS current
        DESCRIPTION

	    "Attributes used to identify a STA, its manufacturer,
	    and various product names and versions."

    ::= {dot11Groups 5  }

dot11SmtAuthenticationAlgorithms OBJECT-GROUP
        OBJECTS { dot11AuthenticationAlgorithm,
            dot11AuthenticationAlgorithmsEnable }
        STATUS current
        DESCRIPTION
            "Authentication Algorithm Table."
    ::= {dot11Groups 6 }


dot11PhyOperationComplianceGroup OBJECT-GROUP
        OBJECTS { dot11PHYType, dot11CurrentRegDomain, dot11TempType }
        STATUS current
        DESCRIPTION
            "PHY layer operations attributes."
    ::= { dot11Groups 7 }


dot11PhyAntennaComplianceGroup OBJECT-GROUP
        OBJECTS {dot11CurrentTxAntenna, dot11DiversitySupport,
dot11CurrentRxAntenna }
        STATUS deprecated
        DESCRIPTION
	    "Attributes for Data Rates for IEEE 802.11."
    ::= { dot11Groups 8 }

dot11PhyTxPowerComplianceGroup OBJECT-GROUP
        OBJECTS {dot11NumberSupportedPowerLevels, dot11TxPowerLevel1,
            dot11TxPowerLevel2, dot11TxPowerLevel3, dot11TxPowerLevel4,
            dot11TxPowerLevel5, dot11TxPowerLevel6, dot11TxPowerLevel7,
            dot11TxPowerLevel8, dot11CurrentTxPowerLevel }
        STATUS current
        DESCRIPTION
            "Attributes for Control and Management of transmit power."
    ::= { dot11Groups 9 }

dot11PhyFHSSComplianceGroup OBJECT-GROUP
        OBJECTS {dot11HopTime, dot11CurrentChannelNumber, dot11MaxDwellTime,
            dot11CurrentDwellTime, dot11CurrentSet, dot11CurrentPattern,
            dot11CurrentIndex}

        STATUS current
        DESCRIPTION

            "Attributes that configure the Frequency Hopping for IEEE
            802.11."

    ::= { dot11Groups 10 }

dot11PhyDSSSComplianceGroup OBJECT-GROUP

        OBJECTS {dot11CurrentChannel, dot11CCAModeSupported,
            dot11CurrentCCAMode, dot11EDThreshold}

        STATUS current
        DESCRIPTION
            "Attributes that configure the DSSS for IEEE 802.11."
    ::= { dot11Groups 11 }

dot11PhyIRComplianceGroup OBJECT-GROUP
        OBJECTS {dot11CCAWatchdogTimerMax, dot11CCAWatchdogCountMax,
        dot11CCAWatchdogTimerMin, dot11CCAWatchdogCountMin}
        STATUS current
        DESCRIPTION
            "Attributes that configure the baseband IR for IEEE 802.11."
    ::= { dot11Groups 12 }

dot11PhyRegDomainsSupportGroup OBJECT-GROUP
        OBJECTS { dot11RegDomainsSupportValue}
        STATUS current
        DESCRIPTION
            "Attributes that specify the supported Regulation Domains."
    ::= { dot11Groups 13}

dot11PhyAntennasListGroup OBJECT-GROUP
        OBJECTS { dot11SupportedTxAntenna,
             dot11SupportedRxAntenna, dot11DiversitySelectionRx }
        STATUS current
        DESCRIPTION
            "Attributes that specify the supported Regulation Domains."
    ::= { dot11Groups 14 }

dot11PhyRateGroup OBJECT-GROUP
        OBJECTS {dot11SupportedDataRatesTxValue,
            dot11SupportedDataRatesRxValue }
        STATUS current
        DESCRIPTION
            "Attributes for Data Rates for IEEE 802.11."
    ::= { dot11Groups 15 }


dot11CountersGroup OBJECT-GROUP
        OBJECTS {  
            dot11TransmittedFragmentCount   ,
            dot11MulticastTransmittedFrameCount ,
            dot11FailedCount, dot11ReceivedFragmentCount,
            dot11MulticastReceivedFrameCount    ,
            dot11FCSErrorCount,
	    dot11WEPUndecryptableCount,
	    dot11TransmittedFrameCount }

        STATUS deprecated
        DESCRIPTION
            "Attributes from the dot11CountersGroup that are not described
            in the dot11MACStatistics group.  These objects are
            mandatory."
    ::= {dot11Groups 16 }

dot11NotificationGroup NOTIFICATION-GROUP
	NOTIFICATIONS { dot11Disassociate, 
	    dot11Deauthenticate,
	    dot11AuthenticateFail }
	STATUS current
	DESCRIPTION
	    "IEEE 802.11 notifications"
    ::= { dot11Groups 17 }

dot11SMTbase2 OBJECT-GROUP
        OBJECTS { dot11MediumOccupancyLimit, 
             dot11CFPollable,
             dot11CFPPeriod,
             dot11CFPMaxDuration,
             dot11AuthenticationResponseTimeOut,
	     dot11PrivacyOptionImplemented,
	     dot11PowerManagementMode,
	     dot11DesiredSSID, dot11DesiredBSSType,
	     dot11OperationalRateSet,
	     dot11BeaconPeriod, dot11DTIMPeriod,
	     dot11AssociationResponseTimeOut,
	     dot11DisassociateReason,
             dot11DisassociateStation,
             dot11DeauthenticateReason,
             dot11DeauthenticateStation,
             dot11AuthenticateFailStatus,
             dot11AuthenticateFailStation 
             }
        STATUS deprecated
        DESCRIPTION
	     "The SMTbase2 object class provides the necessary support at the
	     STA to manage the processes in the STA such that the STA may
	     work cooperatively as a part of an IEEE 802.11 network."
::= {dot11Groups 18 }

dot11PhyHRDSSSComplianceGroup OBJECT-GROUP
	OBJECTS {dot11CurrentChannel,
	    dot11CCAModeSupported,
	    dot11CurrentCCAMode,
	    dot11EDThreshold,
	    dot11ShortPreambleOptionImplemented,
	    dot11PBCCOptionImplemented,
	    dot11ChannelAgilityPresent,
	    dot11ChannelAgilityEnabled,
	    dot11HRCCAModeSupported }
	STATUS current
	
	DESCRIPTION
	    "Attributes that configure the HRDSSS PHY for IEEE 802.11."
::= { dot11Groups 19 }

dot11SMTbase3 OBJECT-GROUP
	OBJECTS { dot11MediumOccupancyLimit,
	    dot11CFPollable,
	    dot11CFPPeriod,
	    dot11CFPMaxDuration,
	    dot11AuthenticationResponseTimeOut,
	    dot11PrivacyOptionImplemented,
	    dot11PowerManagementMode,
	    dot11DesiredSSID, dot11DesiredBSSType,
	    dot11OperationalRateSet,
	    dot11BeaconPeriod, dot11DTIMPeriod,
	    dot11AssociationResponseTimeOut,
	    dot11DisassociateReason,
	    dot11DisassociateStation,
	    dot11DeauthenticateReason,
	    dot11DeauthenticateStation,
	    dot11AuthenticateFailStatus,
	    dot11AuthenticateFailStation,
	    dot11MultiDomainCapabilityImplemented,
	    dot11MultiDomainCapabilityEnabled,
	    dot11CountryString
	    }
	STATUS current
	DESCRIPTION
	    "The SMTbase3 object class provides the necessary support at the
	    STA to manage the processes in the STA such that the STA may
	    work cooperatively as a part of an IEEE 802.11 network, when the STA
	    is capable of multi-domain operation. This object group should be
	    implemented when the multi-domain capability option is implemented."
::= {dot11Groups 20 }

dot11MultiDomainCapabilityGroup OBJECT-GROUP
	OBJECTS {
	    dot11FirstChannelNumber,
	    dot11NumberofChannels,
		dot11MaximumTransmitPowerLevel
	}
	STATUS current
	DESCRIPTION
	    "The dot11MultiDomainCapabilityGroup object class provides the objects
	    necessary to manage the channels usable by a STA, when the multi-domain
	    capability option is implemented."
::= {dot11Groups 21}

dot11PhyFHSSComplianceGroup2 OBJECT-GROUP
	OBJECTS {dot11HopTime, dot11CurrentChannelNumber, dot11MaxDwellTime,
	    dot11CurrentDwellTime, dot11CurrentSet, dot11CurrentPattern,
	    dot11CurrentIndex, dot11EHCCPrimeRadix,
	    dot11EHCCNumberofChannelsFamilyIndex,
	    dot11EHCCCapabilityImplemented, dot11EHCCCapabilityEnabled,
	    dot11HopAlgorithmAdopted, dot11RandomTableFlag,
	    dot11NumberofHoppingSets,
		dot11HopModulus, dot11HopOffset, dot11RandomTableFieldNumber}
	STATUS current
	
	DESCRIPTION
	    "Attributes that configure the Frequency Hopping for operation when
	    multi-domain capability option is implemented."
::= { dot11Groups 22 }

dot11PhyOFDMComplianceGroup OBJECT-GROUP
	OBJECTS {
	    dot11CurrentFrequency,
	    dot11TIThreshold,
	    dot11FrequencyBandsSupported}
	STATUS current
	
	DESCRIPTION
	    "Attributes that configure the OFDM for IEEE 802.11."
::= {dot11Groups 23}

dot11PhyERPComplianceGroup OBJECT-GROUP
	OBJECTS {dot11CurrentChannel,
	    dot11ShortPreambleOptionImplemented,
	    dot11ChannelAgilityPresent,
	    dot11ChannelAgilityEnabled,
	    dot11DSSSOFDMOptionImplemented,
	    dot11DSSSOFDMOptionEnabled,
	    dot11PBCCOptionImplemented,
	    dot11ERPPBCCOptionImplemented,
	    dot11ShortSlotTimeOptionImplemented,
	    dot11ShortSlotTimeOptionEnabled }
	STATUS current
	
	DESCRIPTION
	    "Attributes that configure the ERP."
::= { dot11Groups 24}

dot11RSNAadditions OBJECT-GROUP
	OBJECTS { dot11RSNAEnabled,
	    dot11RSNAPreAuthenticationEnabled }
	STATUS current
	DESCRIPTION
	    "This object class provides the objects from the IEEE 802.11 MIB
	    required to manage RSNA functionality. Note that additional objects
	    for managing this functionality are located in the IEEE 802.11 RSN
	    MIB."
::= { dot11Groups 25 }

dot11SMTbase4 OBJECT-GROUP
	OBJECTS { dot11MediumOccupancyLimit,
	    dot11CFPollable,
	    dot11CFPPeriod,
	    dot11CFPMaxDuration,
	    dot11AuthenticationResponseTimeOut,
	    dot11PrivacyOptionImplemented,
	    dot11PowerManagementMode,
	    dot11DesiredSSID, dot11DesiredBSSType,
	    dot11OperationalRateSet,
	    dot11BeaconPeriod, dot11DTIMPeriod,
	    dot11AssociationResponseTimeOut,
	    dot11DisassociateReason,
	    dot11DisassociateStation,
	    dot11DeauthenticateReason,
	    dot11DeauthenticateStation,
	    dot11AuthenticateFailStatus,
	    dot11AuthenticateFailStation,
	    dot11MultiDomainCapabilityImplemented,
	    dot11MultiDomainCapabilityEnabled,
	    dot11CountryString,
	    dot11RSNAOptionImplemented }
	STATUS deprecated
	DESCRIPTION
	    "The SMTbase4 object class provides the necessary support at the
	    IEEE STA to manage the processes in the STA so that the STA may work
	    cooperatively as a part of an IEEE 802.11 network."
::= { dot11Groups 26 }

dot11MACbase2 OBJECT-GROUP
	OBJECTS { dot11MACAddress, 
    	    dot11Address,
    	    dot11GroupAddressesStatus,
    	    dot11RTSThreshold, 
    	    dot11ShortRetryLimit,
    	    dot11LongRetryLimit, 
    	    dot11FragmentationThreshold,
    	    dot11MaxTransmitMSDULifetime,
    	    dot11MaxReceiveLifetime, 
    	    dot11ManufacturerID,
    	    dot11ProductID, 
    	    dot11CAPLimit, 
    	    dot11HCCWmin,
    	    dot11HCCWmax, 
    	    dot11HCCAIFSN,
    	    dot11ADDBAResponseTimeout, 
    	    dot11ADDTSResponseTimeout,
    	    dot11ChannelUtilizationBeaconInterval, 
    	    dot11ScheduleTimeout,
    	    dot11DLSResponseTimeout, 
    	    dot11QAPMissingAckRetryLimit,
    	    dot11EDCAAveragingPeriod }
	STATUS deprecated
	DESCRIPTION
	    "The MAC object class provides the necessary support for the
	    access control, generation, and verification of frame check sequences
	    (FCSs), and proper delivery of valid data to upper layers."
    ::= { dot11Groups 31 }

dot11CountersGroup2 OBJECT-GROUP
	OBJECTS { dot11TransmittedFragmentCount,
    	    dot11MulticastTransmittedFrameCount,
    	    dot11FailedCount, dot11ReceivedFragmentCount,
    	    dot11MulticastReceivedFrameCount,
    	    dot11FCSErrorCount,
    	    dot11WEPUndecryptableCount,
    	    dot11TransmittedFrameCount,
    	    dot11QosDiscardedFragmentCount,
    	    dot11AssociatedStationCount,
    	    dot11QosCFPollsReceivedCount,
    	    dot11QosCFPollsUnusedCount,
    	    dot11QosCFPollsUnusableCount }
	STATUS deprecated
	DESCRIPTION
	    "Attributes from the dot11CountersGroup that are not described
	    in the dot11MACStatistics group. These objects are mandatory."
    ::= { dot11Groups 32 }

dot11Qosadditions OBJECT-GROUP
	OBJECTS { dot11EDCATable, 
	    dot11QAPEDCATable --,
--	    dot11QosCounters
	}
	STATUS current
	DESCRIPTION
	    "This object class provides the objects from the IEEE 802.11 MIB required
	    to manage QoS functionality."
    ::= { dot11Groups 33 }

dot11SMTbase6 OBJECT-GROUP
	OBJECTS { dot11MediumOccupancyLimit,
    	    dot11CFPollable,
    	    dot11CFPPeriod,
    	    dot11CFPMaxDuration,
    	    dot11AuthenticationResponseTimeOut,
    	    dot11PrivacyOptionImplemented,
    	    dot11PowerManagementMode,
    	    dot11DesiredSSID, dot11DesiredBSSType,
    	    dot11OperationalRateSet,
    	    dot11BeaconPeriod, dot11DTIMPeriod,
    	    dot11AssociationResponseTimeOut,
    	    dot11DisassociateReason,
    	    dot11DisassociateStation,
    	    dot11DeauthenticateReason,
    	    dot11DeauthenticateStation,
    	    dot11AuthenticateFailStatus,
    	    dot11AuthenticateFailStation,
    	    dot11MultiDomainCapabilityImplemented,
    	    dot11MultiDomainCapabilityEnabled,
    	    dot11CountryString,
    	    dot11RSNAOptionImplemented,
--    	    dot11RegulatoryClassesImplemented,
--    	    dot11RegulatoryClassesRequired,
    	    dot11QosOptionImplemented,
    	    dot11ImmediateBlockAckOptionImplemented,
    	    dot11DelayedBlockAckOptionImplemented,
    	    dot11DirectOptionImplemented,
    	    dot11APSDOptionImplemented,
    	    dot11QAckOptionImplemented,
    	    dot11QBSSLoadOptionImplemented,
    	    dot11QueueRequestOptionImplemented,
    	    dot11TXOPRequestOptionImplemented,
    	    dot11MoreDataAckOptionImplemented,
    	    dot11AssociateinNQBSS,
    	    dot11DLSAllowedInQBSS,
    	    dot11DLSAllowed }
	STATUS current
	DESCRIPTION
	    "The SMTbase6 object class provides the necessary support at the
	    STA to manage the processes in the STA such that the STA may work
	    cooperatively as a part of an IEEE 802.11 network."
    ::= { dot11Groups 34 }

dot11PhyAntennaComplianceGroup2 OBJECT-GROUP
	OBJECTS {
    	    dot11CurrentTxAntenna,
    	    dot11DiversitySupport,
    	    dot11CurrentRxAntenna,
--    	    dot11AntennaSelectionOptionImpemented,
    	    dot11TransmitExplicitCSIFeedbackASOptionImplemented,
    	    dot11TransmitIndicesFeedbackASOptionImplemented,
    	    dot11ExplicitCSIFeedbackASOptionImplemented,
    	    dot11TransmitIndicesComputationFeedbackASOptionImplemented,
    	    dot11ReceiveAntennaSelectionOptionImplemented }
	STATUS current
	DESCRIPTION
	    "Attributes for Data Rates for IEEE 802.11."
    ::= { dot11Groups 41 }

dot11MACbase3 OBJECT-GROUP
	OBJECTS {
    	    dot11MACAddress,
    	    dot11Address,
    	    dot11GroupAddressesStatus,
    	    dot11RTSThreshold,
    	    dot11ShortRetryLimit,
    	    dot11LongRetryLimit,
    	    dot11FragmentationThreshold,
    	    dot11MaxTransmitMSDULifetime,
    	    dot11MaxReceiveLifetime,
    	    dot11ManufacturerID,
    	    dot11ProductID,
    	    dot11CAPLimit,
    	    dot11HCCWmin,
    	    dot11HCCWmax,
    	    dot11HCCAIFSN,
    	    dot11ADDBAResponseTimeout,
    	    dot11ADDTSResponseTimeout,
    	    dot11ChannelUtilizationBeaconInterval,
    	    dot11ScheduleTimeout,
    	    dot11DLSResponseTimeout,
    	    dot11QAPMissingAckRetryLimit,
    	    dot11EDCAAveragingPeriod,
    	    dot11HTOperatingMode,
    	    dot11RIFSMode,
    	    dot11PSMPControlledAccess,
    	    dot11ServiceIntervalGranularity,
    	    dot11DualCTSProtection,
    	    dot11LSigTxopFullProtectionEnabled,
    	    dot11NonGFEntitiesPresent, dot11PCOActivated,
    	    dot11PCO40MaxDuration,
    	    dot11PCO20MaxDuration,
    	    dot11PCO40MinDuration,
    	    dot11PCO20MinDuration }
	STATUS current
	DESCRIPTION
	    "The MAC object class provides the necessary support for the
	    access control, generation, and verification of frame check sequences
	    (FCSs), and proper delivery of valid data to upper layers."
    ::= { dot11Groups 42 }

dot11CountersGroup3 OBJECT-GROUP
	OBJECTS {
    	    dot11TransmittedFragmentCount,
    	    dot11MulticastTransmittedFrameCount,
    	    dot11FailedCount,
    	    dot11ReceivedFragmentCount,
    	    dot11MulticastReceivedFrameCount,
    	    dot11FCSErrorCount,
    	    dot11WEPUndecryptableCount,
    	    dot11TransmittedFrameCount,
    	    dot11QosDiscardedFragmentCount,
    	    dot11AssociatedStationCount,
    	    dot11QosCFPollsReceivedCount,
    	    dot11QosCFPollsUnusedCount,
    	    dot11QosCFPollsUnusableCount,
--    	    dot11QoSCFPollsLostCount,
    	    dot11TransmittedAMSDUCount,
    	    dot11FailedAMSDUCount,
    	    dot11RetryAMSDUCount,
    	    dot11MultipleRetryAMSDUCount,
--    	    dot1TransmittedOctetsInAMSDUCount,
    	    dot11AMSDUAckFailureCount,
    	    dot11ReceivedAMSDUCount,
--    	    dot1ReceivedOctetsInAMSDUCount,
    	    dot11TransmittedAMPDUCount,
    	    dot11TransmittedMPDUsInAMPDUCount,
    	    dot11TransmittedOctetsInAMPDUCount,
    	    dot11AMPDUReceivedCount,
    	    dot11MPDUInReceivedAMPDUCount,
    	    dot11ReceivedOctetsInAMPDUCount,
    	    dot11AMPDUDelimiterCRCErrorCount,
    	    dot11ImplicitBARFailureCount,
    	    dot11ExplicitBARFailureCount,
    	    dot11ChannelWidthSwitchCount,
    	    dot11TwentyMHzFrameTransmittedCount,
    	    dot11FortyMHzFrameTransmittedCount,
    	    dot11TwentyMHzFrameReceivedCount,
    	    dot11FortyMHzFrameReceivedCount,
    	    dot11PSMPSuccessCount,
    	    dot11PSMPFailureCount,
    	    dot11GrantedRDGUsedCount,
    	    dot11GrantedRDGUnusedCount,
    	    dot11TransmittedFramesInGrantedRDGCount,
    	    dot11TransmittedOctetsInGrantedRDGCount,
--    	    dot11BeamformingCount,
    	    dot11DualCTSSuccessCount,
    	    dot11DualCTSFailureCount,
    	    dot11STBCCTSSuccessCount,
    	    dot11STBCCTSFailureCount,
    	    dot11nonSTBCCTSSuccessCount,
    	    dot11nonSTBCCTSFailureCount,
    	    dot11RTSLSIGSuccessCount,
    	    dot11RTSLSIGFailureCount }
	STATUS current
	DESCRIPTION
	    "Attributes from the dot11CountersGroup that are not described
	    in the dot11MACStatistics group. These objects are mandatory."
    ::= { dot11Groups 43 }

dot11SMTbase9 OBJECT-GROUP
	OBJECTS {
    	    dot11MediumOccupancyLimit,
    	    dot11CFPollable,
    	    dot11CFPPeriod,
    	    dot11CFPMaxDuration,
    	    dot11AuthenticationResponseTimeOut,
    	    dot11PrivacyOptionImplemented,
    	    dot11PowerManagementMode,
    	    dot11DesiredSSID,
    	    dot11DesiredBSSType,
    	    dot11OperationalRateSet,
    	    dot11BeaconPeriod,
    	    dot11DTIMPeriod,
    	    dot11AssociationResponseTimeOut,
    	    dot11DisassociateReason,
    	    dot11DisassociateStation,
    	    dot11DeauthenticateReason,
    	    dot11DeauthenticateStation,
    	    dot11AuthenticateFailStatus,
    	    dot11AuthenticateFailStation,
    	    dot11MultiDomainCapabilityImplemented,
    	    dot11MultiDomainCapabilityEnabled,
    	    dot11CountryString,
    	    dot11RSNAOptionImplemented,
--    	    dot11RegulatoryClassesImplemented,
--    	    dot11RegulatoryClassesRequired,
    	    dot11QosOptionImplemented,
    	    dot11ImmediateBlockAckOptionImplemented,
    	    dot11DelayedBlockAckOptionImplemented,
    	    dot11DirectOptionImplemented,
    	    dot11APSDOptionImplemented,
    	    dot11QAckOptionImplemented,
    	    dot11QBSSLoadOptionImplemented,
    	    dot11QueueRequestOptionImplemented,
    	    dot11TXOPRequestOptionImplemented,
    	    dot11MoreDataAckOptionImplemented,
    	    dot11AssociateinNQBSS,
    	    dot11DLSAllowedInQBSS,
    	    dot11DLSAllowed --,
--	dot11FastBSSTransitionImplemented,
--	dot11HighThroughputOptionImpelemented
	}
	STATUS current
	DESCRIPTION
	    "The SMTbase9 object class provides the necessary support at
	    the STA to manage the processes in the STA such that the STA may work
	    cooperatively as a part of an IEEE 802.11 network."
    ::= { dot11Groups 44 }

dot11PhyMCSGroup OBJECT-GROUP
	OBJECTS {
    	    dot11SupportedMCSTxValue,
    	    dot11SupportedMCSRxValue }
	STATUS current
	DESCRIPTION
	    "Attributes for Modulation and Coding Schemes (MCS) for IEEE
	    802.11 HT."
    ::= { dot11Groups 45 }

dot1PhyHTComplianceGroup OBJECT-GROUP
	OBJECTS {
    	    dot11HighThroughputOptionImplemented,
    	    dot11FortyMHzOperationImplemented,
    	    dot11FortyMHzOperationEnabled,
    	    dot11CurrentPrimaryChannel,
    	    dot11CurrentSecondaryChannel,
    	    dot11GreenfieldOptionImplemented,
    	    dot11GreenfieldOptionEnabled,
    	    dot11ShortGIOptionInTwentyImplemented,
    	    dot11ShortGIOptionInTwentyEnabled,
    	    dot11ShortGIOptionInFortyImplemented,
    	    dot11ShortGIOptionInFortyEnabled,
    	    dot11LDPCCodingOptionImplemented,
    	    dot11LDPCCodingOptionEnabled,
    	    dot11TxSTBCOptionImplemented,
    	    dot11TxSTBCOptionEnabled,
    	    dot11RxSTBCOptionImplemented,
    	    dot11RxSTBCOptionEnabled,
    	    dot11BeamFormingOptionImplemented,
    	    dot11BeamFormingOptionImplemented }
	STATUS current
	DESCRIPTION
	    "Attributes that configure the HT for IEEE 802.11."
    ::= { dot11Groups 46 }

dot11HTMACAdditions OBJECT-GROUP
	OBJECTS {
    	    dot11HTOperationalMCSSet,
    	    dot11MIMOPowerSave,
    	    dot11NDelayedBlockAckOptionImplemented,
    	    dot11MaxAMSDULength,
    	    dot11PSMPOptionImplemented,
    	    dot11STBCControlFrameOptionImplemented,
    	    dot11LsigTxopProtectionOptionImplemented,
    	    dot11MaxRxAMPDUFactor,
    	    dot11MinimumMPDUStartSpacing,
    	    dot11PCOOptionImplemented,
    	    dot11TransitionTime,
    	    dot11MCSFeedbackOptionImplemented,
    	    dot11HTControlFieldSupported,dot11RDResponderOptionImplemented }
	STATUS current
	DESCRIPTION
	    "Attributes that configure the HT for IEEE 802.11."
    ::= { dot11Groups 47 }

dot11TxBFGroup OBJECT-GROUP
	OBJECTS {
    	    dot11ReceiveStaggerSoundingOptionImplemented,
    	    dot11TransmitStaggerSoundingOptionImplemented,
    	    dot11ReceiveNDPOptionImplemented,
    	    dot11TransmitNDPOptionImplemented,
    	    dot11ImplicitTxBFOptionImplemented,
    	    dot11CalibrationOptionImplemented,
    	    dot11ExplicitCSITxBFOptionImplemented,
    	    dot11ExplicitNonCompressedbeamformingMatrixOptionImplemented,
    	    dot11ExplicitBFCSIFeedbackOptionImplemented,
    	    dot11ExplicitNonCompressedbeamformingMatrixFeedbackOptionImplemented,
    	    dot11ExplicitCompressedbeamformingMatrixFeedbackOptionImplemented,
    	    dot11NumberBeamFormingCSISupportAntenna,
    	    dot11NumberNonCompressedbeamformingMatrixSupportAntenna,
    	    dot11NumberCompressedbeamformingMatrixSupportAntenna }
	STATUS current
	DESCRIPTION
	    "Attributes that configure the Beamforming for IEEE 802.11
	    HT."
    ::= { dot11Groups 48 }

-- ********************************************************************
-- * dot11RSNAConfig TABLE (RSNA and TSN)
-- ********************************************************************
dot11RSNAConfigTable OBJECT-TYPE
	SYNTAX	    SEQUENCE OF Dot11RSNAConfigEntry
	MAX-ACCESS  not-accessible
	STATUS	    current
	DESCRIPTION
	    "The table containing RSNA configuration objects."
::= { dot11smt 9 }

dot11RSNAConfigEntry OBJECT-TYPE
	SYNTAX	    Dot11RSNAConfigEntry
	MAX-ACCESS  not-accessible
	STATUS	    current
	DESCRIPTION
	    "An entry in the dot11RSNAConfigTable."
	INDEX { ifIndex }
::= { dot11RSNAConfigTable 1 }

Dot11RSNAConfigEntry ::=
	SEQUENCE {
	    dot11RSNAConfigVersion			Integer32,
	    dot11RSNAConfigPairwiseKeysSupported	Unsigned32,
	    dot11RSNAConfigGroupCipher			OCTET STRING,
	    dot11RSNAConfigGroupRekeyMethod		INTEGER,
	    dot11RSNAConfigGroupRekeyTime		Unsigned32,
	    dot11RSNAConfigGroupRekeyPackets		Unsigned32,
	    dot11RSNAConfigGroupRekeyStrict		TruthValue,
	    dot11RSNAConfigPSKValue			OCTET STRING,
	    dot11RSNAConfigPSKPassPhrase		DisplayString,
	    dot11RSNAConfigGroupUpdateCount		Unsigned32,
	    dot11RSNAConfigPairwiseUpdateCount		Unsigned32,
	    dot11RSNAConfigGroupCipherSize		Unsigned32,
	    dot11RSNAConfigPMKLifetime			Unsigned32,
	    dot11RSNAConfigPMKReauthThreshold		Unsigned32,
	    dot11RSNAConfigNumberOfPTKSAReplayCounters	INTEGER,
	    dot11RSNAConfigSATimeout			Unsigned32,
	    dot11RSNAAuthenticationSuiteSelected	OCTET STRING,
	    dot11RSNAPairwiseCipherSelected		OCTET STRING,
	    dot11RSNAGroupCipherSelected		OCTET STRING,
	    dot11RSNAPMKIDUsed				OCTET STRING,
	    dot11RSNAAuthenticationSuiteRequested	OCTET STRING,
	    dot11RSNAPairwiseCipherRequested		OCTET STRING,
	    dot11RSNAGroupCipherRequested		OCTET STRING,
	    dot11RSNATKIPCounterMeasuresInvoked		Unsigned32,
	    dot11RSNA4WayHandshakeFailures		Unsigned32,
	    dot11RSNAConfigNumberOfGTKSAReplayCounters  INTEGER }

-- dot11RSNAConfigEntry 1 has been deprecated.

dot11RSNAConfigVersion OBJECT-TYPE
	SYNTAX	    Integer32
	MAX-ACCESS  read-only
	STATUS	    current
	DESCRIPTION
	    "The highest RSNA version this entity supports. See 7.3.2.9."
::= { dot11RSNAConfigEntry 2 }

dot11RSNAConfigPairwiseKeysSupported OBJECT-TYPE
	SYNTAX	    Unsigned32
	MAX-ACCESS  read-only
	STATUS	    current
	DESCRIPTION
	    "This object indicates how many pairwise keys the entity supports
	    for RSNA."
::= { dot11RSNAConfigEntry 3 }

dot11RSNAConfigGroupCipher OBJECT-TYPE
	SYNTAX	    OCTET STRING (SIZE(4))
	MAX-ACCESS  read-write
	STATUS	    current
	DESCRIPTION
	    "This object indicates the group cipher suite selector the entity
	    must use. The group cipher suite in the RSN Information Element
	    shall take its value from this variable. It consists of an OUI (the
	    first 3 octets) and a cipher suite identifier (the last octet)."
::= { dot11RSNAConfigEntry 4 }

dot11RSNAConfigGroupRekeyMethod OBJECT-TYPE
	SYNTAX	    INTEGER { disabled(1), timeBased(2), packetBased(3), timepacket-Based(4) }
	MAX-ACCESS  read-write
	STATUS	    current
	DESCRIPTION
	    "This object selects a mechanism for rekeying the RSNA GTK. The
	    default is time-based, once per day. Rekeying the GTK is only
	    applicable to an entity acting in the Authenticator role (an AP in
	    an ESS)."
	DEFVAL { timeBased }
::= { dot11RSNAConfigEntry 5 }

dot11RSNAConfigGroupRekeyTime OBJECT-TYPE
	SYNTAX	    Unsigned32 (1..4294967295)
	UNITS	    "seconds"
	MAX-ACCESS  read-write
	STATUS	    current
	DESCRIPTION
	    "The time in seconds after which the RSNA GTK shall be refreshed.
	    The timer shall start at the moment the GTK was set using the MLMESETKEYS.
	    request primitive."
	DEFVAL { 86400 } -- once per day
::= { dot11RSNAConfigEntry 6 }

dot11RSNAConfigGroupRekeyPackets OBJECT-TYPE
	SYNTAX	    Unsigned32 (1..4294967295)
	UNITS	    "1000 packets"
	MAX-ACCESS  read-write
	STATUS	    current
	DESCRIPTION
	    "A packet count (in 1000s of packets) after which the RSNA GTK
	    shall be refreshed. The packet counter shall start at the moment
	    the GTK was set using the MLME-SETKEYS.request primitive and it
	    shall count all packets encrypted using the current GTK."
::= { dot11RSNAConfigEntry 7 }

dot11RSNAConfigGroupRekeyStrict OBJECT-TYPE
	SYNTAX	    TruthValue
	MAX-ACCESS  read-write
	STATUS	    current
	DESCRIPTION
	    "This object signals that the GTK shall be refreshed whenever a STA
	    leaves the BSS that possesses the GTK."
::= { dot11RSNAConfigEntry 8 }

dot11RSNAConfigPSKValue OBJECT-TYPE
	SYNTAX	    OCTET STRING (SIZE(32))
	MAX-ACCESS  read-write
	STATUS	    current
	DESCRIPTION
	    "The PSK for when RSNA in PSK mode is the selected AKM suite. In
	    that case, the PMK will obtain its value from this object.
	    This object is logically write-only. Reading this variable shall
	    return unsuccessful status or null or zero."
::= { dot11RSNAConfigEntry 9 }

dot11RSNAConfigPSKPassPhrase OBJECT-TYPE
	SYNTAX	    DisplayString
	MAX-ACCESS  read-write
	STATUS	    current
	DESCRIPTION
	    "The PSK, for when RSNA in PSK mode is the selected AKM suite, is
	    configured by dot11RSNAConfigPSKValue.
	    An alternative manner of setting the PSK uses the password-to-key
	    algorithm defined in H.4. This variable provides a means to enter a
	    pass-phrase. When this object is written, the RSNA entity shall use
	    the password-to-key algorithm specified in H.4 to derive a preshared
	    and populate dot11RSNAConfigPSKValue with this key.
	    This object is logically write-only. Reading this variable shall
	    return unsuccessful status or null or zero."
::= { dot11RSNAConfigEntry 10 }

-- dot11RSNAConfigEntry 11 and dot11RSNAConfigEntry 12 have been
-- deprecated.

dot11RSNAConfigGroupUpdateCount OBJECT-TYPE
	SYNTAX	    Unsigned32 (1..4294967295)
	MAX-ACCESS  read-write
	STATUS	    current
	DESCRIPTION
	    "The number of times Message 1 in the RSNA Group Key Handshake will
	    be retried per GTK Handshake attempt."
	DEFVAL { 3 } --
::= { dot11RSNAConfigEntry 13 }

dot11RSNAConfigPairwiseUpdateCount OBJECT-TYPE
	SYNTAX	    Unsigned32 (1..4294967295)
	MAX-ACCESS  read-write
	STATUS	    current
	DESCRIPTION
	    "The number of times Message 1 and Message 3 in the RSNA 4-Way Handshake
	    will be retried per 4-Way Handshake attempt."
	DEFVAL { 3 } --
::= { dot11RSNAConfigEntry 14 }

dot11RSNAConfigGroupCipherSize OBJECT-TYPE
	SYNTAX	    Unsigned32 (0..4294967295)
	MAX-ACCESS  read-only
	STATUS	    current
	DESCRIPTION
	    "This object indicates the length in bits of the group cipher key."
::= { dot11RSNAConfigEntry 15 }

dot11RSNAConfigPMKLifetime OBJECT-TYPE
	SYNTAX	    Unsigned32 (1..4294967295)
	UNITS	    "seconds"
	MAX-ACCESS  read-write
	STATUS	    current
	DESCRIPTION
	    "The maximum lifetime of a PMK in the PMK cache."
	DEFVAL { 43200 } --
::= { dot11RSNAConfigEntry 16 }

dot11RSNAConfigPMKReauthThreshold OBJECT-TYPE
	SYNTAX	    Unsigned32 (1..100)
	UNITS	    "percentage"
	MAX-ACCESS  read-write
	STATUS	    current
	DESCRIPTION
	    "The percentage of the PMK lifetime that should expire before an
	    IEEE 802.1X reauthentication occurs."
::= { dot11RSNAConfigEntry 17 }

dot11RSNAConfigNumberOfPTKSAReplayCounters OBJECT-TYPE
	SYNTAX	    INTEGER
	MAX-ACCESS  read-only
	STATUS	    current
	DESCRIPTION
	    "Specifies the number of PTKSA replay counters per association:
		  0 -> 1 replay counter,
		  1 -> 2 replay counters,
		  2 -> 4 replay counters,
		  3 -> 16 replay counters"
::= { dot11RSNAConfigEntry 18 }

dot11RSNAConfigSATimeout OBJECT-TYPE
	SYNTAX	    Unsigned32 (1..4294967295)
	UNITS	    "seconds"
	MAX-ACCESS  read-write
	STATUS	    current
	DESCRIPTION
	    "The maximum time a security association shall take to set up."
	DEFVAL { 60 } --
::= { dot11RSNAConfigEntry 19 }

dot11RSNAAuthenticationSuiteSelected OBJECT-TYPE
	SYNTAX	    OCTET STRING (SIZE(4))
	MAX-ACCESS  read-only
	STATUS	    current
	DESCRIPTION
	    "The selector of the last AKM suite negotiated."
::= { dot11RSNAConfigEntry 20 }

dot11RSNAPairwiseCipherSelected OBJECT-TYPE
	SYNTAX	    OCTET STRING (SIZE(4))
	MAX-ACCESS  read-only
	STATUS	    current
	DESCRIPTION
	    "The selector of the last pairwise cipher negotiated."
::= { dot11RSNAConfigEntry 21 }

dot11RSNAGroupCipherSelected OBJECT-TYPE
	SYNTAX	    OCTET STRING (SIZE(4))
	MAX-ACCESS  read-only
	STATUS	    current
	DESCRIPTION
	    "The selector of the last group cipher negotiated."
::= { dot11RSNAConfigEntry 22 }

dot11RSNAPMKIDUsed OBJECT-TYPE
	SYNTAX	    OCTET STRING (SIZE(16))
	MAX-ACCESS  read-only
	STATUS	    current
	DESCRIPTION
	    "The selector of the last PMKID used in the last 4-Way Handshake."
::= { dot11RSNAConfigEntry 23 }

dot11RSNAAuthenticationSuiteRequested OBJECT-TYPE
	SYNTAX	    OCTET STRING (SIZE(4))
	MAX-ACCESS  read-only
	STATUS	    current
	DESCRIPTION
	    "The selector of the last AKM suite requested."
::= { dot11RSNAConfigEntry 24 }

dot11RSNAPairwiseCipherRequested OBJECT-TYPE
	SYNTAX	    OCTET STRING (SIZE(4))
	MAX-ACCESS  read-only
	STATUS	    current
	DESCRIPTION
	    "The selector of the last pairwise cipher requested."
::= { dot11RSNAConfigEntry 25 }

dot11RSNAGroupCipherRequested OBJECT-TYPE
	SYNTAX	    OCTET STRING (SIZE(4))
	MAX-ACCESS  read-only
	STATUS	    current
	DESCRIPTION
	    "The selector of the last group cipher requested."
::= { dot11RSNAConfigEntry 26 }

dot11RSNATKIPCounterMeasuresInvoked OBJECT-TYPE
	SYNTAX	    Unsigned32 (1..4294967295)
	MAX-ACCESS  read-write
	STATUS	    current
	DESCRIPTION
	    "Counts the number of times that a TKIP MIC failure occurred two
	    times within 60 s and TKIP countermeasures were invoked. This
	    attribute counts both local and remote MIC failure events reported
	    to this STA. It increments every time TKIP countermeasures are
	    invoked"
::= { dot11RSNAConfigEntry 27 }

dot11RSNA4WayHandshakeFailures OBJECT-TYPE
	SYNTAX	    Unsigned32 (1..4294967295)
	MAX-ACCESS  read-write
	STATUS	    current
	DESCRIPTION
	    "Counts the number of 4-Way Handshake failures."
::= { dot11RSNAConfigEntry 28 }

dot11RSNAConfigNumberOfGTKSAReplayCounters OBJECT-TYPE
	SYNTAX	    INTEGER
	MAX-ACCESS  read-only
	STATUS	    current
	DESCRIPTION
	    "Specifies the number of GTKSA replay counters per association:
		   0 -> 1 replay counter,
		   1 -> 2 replay counters,
		   2 -> 4 replay counters,
		   3 -> 16 replay counters"
::= { dot11RSNAConfigEntry 29 }

-- ********************************************************************
-- * End of dot11RSNAConfig TABLE
-- ********************************************************************

-- ********************************************************************
-- * dot11RSNAConfigPairwiseCiphers TABLE
-- ********************************************************************
dot11RSNAConfigPairwiseCiphersTable OBJECT-TYPE
	SYNTAX	    SEQUENCE OF Dot11RSNAConfigPairwiseCiphersEntry
	MAX-ACCESS  not-accessible
	STATUS	    current
	DESCRIPTION
	    "This table lists the pairwise ciphers supported by this entity. It
	    allows enabling and disabling of each pairwise cipher by network
	    management. The pairwise cipher suite list in the RSN Information
	    Element is formed using the information in this table."
::= { dot11smt 10 }

dot11RSNAConfigPairwiseCiphersEntry OBJECT-TYPE
	SYNTAX	    Dot11RSNAConfigPairwiseCiphersEntry
	MAX-ACCESS  not-accessible
	STATUS	    current
	DESCRIPTION
	    "The table entry, indexed by the interface index (or all interfaces)
	    and the pairwise cipher."
--	INDEX { dot11RSNAConfigIndex, dot11RSNAConfigPairwiseCipherIndex }
	INDEX { ifIndex, dot11RSNAConfigPairwiseCipherIndex }
::= { dot11RSNAConfigPairwiseCiphersTable 1 }

Dot11RSNAConfigPairwiseCiphersEntry ::=
	SEQUENCE {
	    dot11RSNAConfigPairwiseCipherIndex		Unsigned32,
	    dot11RSNAConfigPairwiseCipher		OCTET STRING,
	    dot11RSNAConfigPairwiseCipherEnabled	TruthValue,
	    dot11RSNAConfigPairwiseCipherSize		Unsigned32 }

dot11RSNAConfigPairwiseCipherIndex OBJECT-TYPE
	SYNTAX	    Unsigned32 (1..4294967295)
        MAX-ACCESS read-only
	STATUS	    current
	DESCRIPTION
	    "The auxiliary index into the dot11RSNAConfigPairwiseCiphersTable."
::= { dot11RSNAConfigPairwiseCiphersEntry 1 }

dot11RSNAConfigPairwiseCipher OBJECT-TYPE
	SYNTAX	    OCTET STRING (SIZE(4))
	MAX-ACCESS  read-only
	STATUS	    current
	DESCRIPTION
	    "The selector of a supported pairwise cipher. It consists of an OUI
	    (the first 3 octets) and a cipher suite identifier (the last
	    octet)."
::= { dot11RSNAConfigPairwiseCiphersEntry 2 }

dot11RSNAConfigPairwiseCipherEnabled OBJECT-TYPE
	SYNTAX	    TruthValue
	MAX-ACCESS  read-write
	STATUS	    current
	DESCRIPTION
	    "This object enables or disables the pairwise cipher."
::= { dot11RSNAConfigPairwiseCiphersEntry 3 }

dot11RSNAConfigPairwiseCipherSize OBJECT-TYPE
	SYNTAX	    Unsigned32 (0..4294967295)
	MAX-ACCESS  read-only
	STATUS	    current
	DESCRIPTION
	    "This object indicates the length in bits of the pairwise cipher
	    key. This should be 256 for TKIP and 128 for CCMP."
::= { dot11RSNAConfigPairwiseCiphersEntry 4 }

-- ********************************************************************
-- * End of dot11RSNAConfigPairwiseCiphers TABLE
-- ********************************************************************

-- ********************************************************************
-- * dot11RSNAConfigAuthenticationSuites TABLE
-- ********************************************************************

dot11RSNAConfigAuthenticationSuitesTable OBJECT-TYPE
	SYNTAX	    SEQUENCE OF Dot11RSNAConfigAuthenticationSuitesEntry
	MAX-ACCESS  not-accessible
	STATUS	    current
	DESCRIPTION
	    "This table lists the AKM suites supported by this entity. Each AKM
	    suite can be individually enabled and disabled. The AKM suite list
	    in the RSN information element is formed using the information in
	    this table."
::= { dot11smt 11 }

dot11RSNAConfigAuthenticationSuitesEntry OBJECT-TYPE
	SYNTAX	    Dot11RSNAConfigAuthenticationSuitesEntry
	MAX-ACCESS  not-accessible
	STATUS	    current
	DESCRIPTION
	    "An entry (row) in the dot11RSNAConfigAuthenticationSuitesTable."
	    INDEX { dot11RSNAConfigAuthenticationSuiteIndex }
::= { dot11RSNAConfigAuthenticationSuitesTable 1 }

Dot11RSNAConfigAuthenticationSuitesEntry ::=
	SEQUENCE {
	    dot11RSNAConfigAuthenticationSuiteIndex	Unsigned32,
	    dot11RSNAConfigAuthenticationSuite		OCTET STRING,
	    dot11RSNAConfigAuthenticationSuiteEnabled	TruthValue }

dot11RSNAConfigAuthenticationSuiteIndex OBJECT-TYPE
	SYNTAX	    Unsigned32 (1..4294967295)
        MAX-ACCESS read-only
	STATUS	    current
	DESCRIPTION
	    "The auxiliary variable used as an index into the
	    dot11RSNAConfigAuthenticationSuitesTable."
::= { dot11RSNAConfigAuthenticationSuitesEntry 1 }

dot11RSNAConfigAuthenticationSuite OBJECT-TYPE
	SYNTAX	    OCTET STRING (SIZE(4))
	MAX-ACCESS  read-only
	STATUS	    current
	DESCRIPTION
	    "The selector of an AKM suite. It consists of an OUI (the first 3
	    octets) and a cipher suite identifier (the last octet)."
::= { dot11RSNAConfigAuthenticationSuitesEntry 2 }

dot11RSNAConfigAuthenticationSuiteEnabled OBJECT-TYPE
	SYNTAX	    TruthValue
	MAX-ACCESS  read-write
	STATUS	    current
	DESCRIPTION
	    "This variable indicates whether the corresponding AKM suite is
	    enabled/disabled."
::= { dot11RSNAConfigAuthenticationSuitesEntry 3 }

-- ********************************************************************
-- * End of dot11RSNAConfigAuthenticationSuites TABLE
-- ********************************************************************

-- ********************************************************************
-- * dot11RSNAStats TABLE
-- ********************************************************************

dot11RSNAStatsTable OBJECT-TYPE
	SYNTAX	    SEQUENCE OF Dot11RSNAStatsEntry
	MAX-ACCESS  not-accessible
	STATUS	    current
	DESCRIPTION
	    "This table maintains per-STA statistics in an RSN. The entry with
	    dot11RSNAStatsSTAAddress set to FF-FF-FF-FF-FF-FF shall contain
	    statistics for broadcast/multicast traffic."
::= { dot11smt 12 }

dot11RSNAStatsEntry OBJECT-TYPE
	SYNTAX	    Dot11RSNAStatsEntry
	MAX-ACCESS  not-accessible
	STATUS	    current
	DESCRIPTION
	    "An entry in the dot11RSNAStatsTable."
--	INDEX { dot11RSNAConfigIndex, dot11RSNAStatsIndex }
	INDEX { ifIndex, dot11RSNAStatsIndex }
::= { dot11RSNAStatsTable 1 }

Dot11RSNAStatsEntry ::=
	SEQUENCE {
	    dot11RSNAStatsIndex			    Unsigned32,
	    dot11RSNAStatsSTAAddress		    MacAddress,
	    dot11RSNAStatsVersion		    Unsigned32,
	    dot11RSNAStatsSelectedPairwiseCipher    OCTET STRING,
	    dot11RSNAStatsTKIPICVErrors		    Counter32,
	    dot11RSNAStatsTKIPLocalMICFailures	    Counter32,
	    dot11RSNAStatsTKIPRemoteMICFailures	    Counter32,
	    dot11RSNAStatsCCMPReplays		    Counter32,
	    dot11RSNAStatsCCMPDecryptErrors	    Counter32,
	    dot11RSNAStatsTKIPReplays		    Counter32 }

dot11RSNAStatsIndex OBJECT-TYPE
	SYNTAX	    Unsigned32 (1..4294967295)
        MAX-ACCESS read-only
	STATUS	    current
	DESCRIPTION
	    "An auxiliary index into the dot11RSNAStatsTable."
::= { dot11RSNAStatsEntry 1 }

dot11RSNAStatsSTAAddress OBJECT-TYPE
	SYNTAX	    MacAddress
	MAX-ACCESS  read-only
	STATUS	    current
	DESCRIPTION
	    "The MAC address of the STA to which the statistics in this
	    conceptual row belong."
::= { dot11RSNAStatsEntry 2 }

dot11RSNAStatsVersion OBJECT-TYPE
	SYNTAX	    Unsigned32 (1..4294967295)
	MAX-ACCESS  read-only
	STATUS	    current
	DESCRIPTION
	    "The RSNA version with which the STA associated."
::= { dot11RSNAStatsEntry 3 }

dot11RSNAStatsSelectedPairwiseCipher OBJECT-TYPE
	SYNTAX	    OCTET STRING (SIZE(4))
	MAX-ACCESS  read-only
	STATUS	    current
	DESCRIPTION
	    "The pairwise cipher suite Selector (as defined in 7.3.29.1) used
	    during association, in transmission order."
::= { dot11RSNAStatsEntry 4 }

dot11RSNAStatsTKIPICVErrors OBJECT-TYPE
	SYNTAX	    Counter32
	MAX-ACCESS  read-only
	STATUS	    current
	DESCRIPTION
	    "Counts the number of TKIP ICV errors encountered when decrypting
	    packets for the STA."
::= { dot11RSNAStatsEntry 5 }

dot11RSNAStatsTKIPLocalMICFailures OBJECT-TYPE
	SYNTAX	    Counter32
	MAX-ACCESS  read-only
	STATUS	    current
	DESCRIPTION
	    "Counts the number of MIC failures encountered when checking the
	    integrity of packets received from the STA at this entity."
::= { dot11RSNAStatsEntry 6 }

dot11RSNAStatsTKIPRemoteMICFailures OBJECT-TYPE
	SYNTAX	    Counter32
	MAX-ACCESS  read-only
	STATUS	    current
	DESCRIPTION
	    "Counts the number of MIC failures encountered by the STA identified
	    by dot11StatsSTAAddress and reported back to this entity."
::= { dot11RSNAStatsEntry 7 }

dot11RSNAStatsCCMPReplays OBJECT-TYPE
	SYNTAX	    Counter32
	MAX-ACCESS  read-only
	STATUS	    current
	DESCRIPTION
	    "The number of received CCMP MPDUs discarded by the replay
	    mechanism."
::= { dot11RSNAStatsEntry 8 }

dot11RSNAStatsCCMPDecryptErrors OBJECT-TYPE
	SYNTAX	    Counter32
	MAX-ACCESS  read-only
	STATUS	    current
	DESCRIPTION
	    "The number of received MPDUs discarded by the CCMP decryption
	    algorithm."
::= { dot11RSNAStatsEntry 9 }

dot11RSNAStatsTKIPReplays OBJECT-TYPE
	SYNTAX	    Counter32
	MAX-ACCESS  read-only
	STATUS	    current
	DESCRIPTION
	    "Counts the number of TKIP replay errors detected."
::= { dot11RSNAStatsEntry 10 }

-- ********************************************************************
-- * End of dot11RSNAStats TABLE
-- ********************************************************************

-- **********************************************************************
-- * dot11HTStationConfig TABLE
-- **********************************************************************
dot11HTStationConfigTable OBJECT-TYPE
	SYNTAX SEQUENCE OF Dot11HTStationConfigEntry
	MAX-ACCESS not-accessible
	STATUS current
	DESCRIPTION
	    "Station Configuration attributes. In tabular form to allow
	    for multiple instances on an agent."
    ::= { dot11smt 16 }

dot11HTStationConfigEntry OBJECT-TYPE
	SYNTAX Dot11HTStationConfigEntry
	MAX-ACCESS not-accessible
	STATUS current
	DESCRIPTION
	    "An entry (conceptual row) in the dot11HTStationConfig Table.
	    ifIndex - Each IEEE 802.11 interface is represented by an
	    ifEntry. Interface tables in this MIB module are indexed by ifIndex."
	INDEX { ifIndex }
    ::= { dot11HTStationConfigTable 1 }

Dot11HTStationConfigEntry ::= SEQUENCE {
	    dot11HTOperationalMCSSet 	    		OCTET STRING,
	    dot11MIMOPowerSave 	    	    		INTEGER,   
	    dot11NDelayedBlockAckOptionImplemented	TruthValue,
	    dot11MaxAMSDULength 	    		INTEGER,
	    dot11PSMPOptionImplemented 	    		TruthValue,
	    dot11STBCControlFrameOptionImplemented	TruthValue,
	    dot11LsigTxopProtectionOptionImplemented	TruthValue,
	    dot11MaxRxAMPDUFactor 	    		INTEGER,
	    dot11MinimumMPDUStartSpacing 	    	INTEGER,
	    dot11PCOOptionImplemented 	    		TruthValue,
	    dot11TransitionTime 	    		INTEGER,
	    dot11MCSFeedbackOptionImplemented 		INTEGER,
	    dot11HTControlFieldSupported 	    	TruthValue,
	    dot11RDResponderOptionImplemented 		TruthValue }
	    
dot11HTOperationalMCSSet OBJECT-TYPE
	SYNTAX OCTET STRING (SIZE(1..127))
	MAX-ACCESS read-write
	STATUS current
	DESCRIPTION
	    "This attribute shall specify the set of MCS at which the
	    station may transmit data. Each octet contains a value representing a rate.
	    Each MCS shall be within the range from 1 to 127, and shall be supported for
	    receiving data. This value is reported in transmitted Beacon, Probe Request,
	    Probe Response, Association Request, Association Response, Reassociation
	    Request, and Reassociation Response frames, and is used to determine whether
	    a BSS with which the station desires to synchronize is suitable. It is also
	    used when starting a BSS, as specified in 10.3."
    ::= { dot11HTStationConfigEntry 1 }

dot11MIMOPowerSave OBJECT-TYPE
	SYNTAX INTEGER { static(1), dynamic(2), mimo(3) }
	MAX-ACCESS read-only
	STATUS current
	DESCRIPTION
	    "This is an 8-bit integer value that identifies the configured
	    power save state of MIMO."
    ::= { dot11HTStationConfigEntry 2 }

dot11NDelayedBlockAckOptionImplemented OBJECT-TYPE
	SYNTAX TruthValue
	MAX-ACCESS read-only
	STATUS current
	DESCRIPTION
	    "This attribute, when TRUE, indicates that the station
	    implementation is capable of supporting the No ack option of the Delayed
	    Block Ack. The default value of this attribute is FALSE."
        DEFVAL { false }
    ::= { dot11HTStationConfigEntry 3 }

dot11MaxAMSDULength OBJECT-TYPE
	SYNTAX INTEGER (3839..7935)
	MAX-ACCESS read-only
	STATUS current
	DESCRIPTION
	    "This attribute indicates the supported maximum size of AMSDU.
	    The default value of this attribute is 3839."
        DEFVAL { 3839 }
    ::= { dot11HTStationConfigEntry 4 }
		
dot11PSMPOptionImplemented OBJECT-TYPE
	SYNTAX TruthValue
	MAX-ACCESS read-only
	STATUS current
	DESCRIPTION
	    "This attribute, when TRUE, indicates that the station
	    implementation is capable of supporting PSMP. The default value of this
	    attribute is FALSE."
        DEFVAL { false }
    ::= { dot11HTStationConfigEntry 5 }
		
dot11STBCControlFrameOptionImplemented OBJECT-TYPE
	SYNTAX TruthValue
	MAX-ACCESS read-only
	STATUS current
	DESCRIPTION
	    "This attribute, when TRUE, indicates that the station
	    implementation is capable of processing the received control frames that are
	    STBC frames. The default value of this attribute is FALSE."
        DEFVAL { false }
    ::= { dot11HTStationConfigEntry 6 }

dot11LsigTxopProtectionOptionImplemented OBJECT-TYPE
	SYNTAX TruthValue
	MAX-ACCESS read-only
	STATUS current
	DESCRIPTION
	    "This attribute, when TRUE, indicates that the station
	    implementation is capable of supporting L-SIG TXOP Protection option. The
	    default value of this attribute is FALSE."
        DEFVAL { false }
    ::= { dot11HTStationConfigEntry 7 }

dot11MaxRxAMPDUFactor OBJECT-TYPE
	SYNTAX INTEGER (0..3)
	MAX-ACCESS read-only
	STATUS current
	DESCRIPTION
	    "This attribute indicates the maximum length of A-MPDU that
	    the STA can receive. The Maximum Rx A-MPDU defined by this field is equal to
	    213+dot11MaxRxAMPDUFactor -1 octets. The default value of this attribute is 0."
        DEFVAL { 0 }
    ::= { dot11HTStationConfigEntry 8 }
		
dot11MinimumMPDUStartSpacing OBJECT-TYPE
	SYNTAX INTEGER (0..7)
	MAX-ACCESS read-only
	STATUS current
	DESCRIPTION
	    "This attribute indicates the minimum time between the start
	    of adjacent MPDUs within an A-MPDU. This time is measured at the PHY-SAP; the
	    number of octets between the start of two consecutive MPDUs in A-MPDU shall
	    be equal or greater than (dot11MinimumMPDUStartSpacing*PHY-bit-rate)/8. The
	    encoding of the minimum time to this attribute is:
	    0 no restriction
	    1 1/4 microsec
	    2 1/2 microsec
	    3 1 microsec
	    4 2 microsec
	    5 4 microsec
	    6 8 microsec
	    7 16 microsec
	    The default value of this attribute is 0."
        DEFVAL { 0 }
    ::= { dot11HTStationConfigEntry 9 }

dot11PCOOptionImplemented OBJECT-TYPE
	SYNTAX TruthValue
	MAX-ACCESS read-only
	STATUS current
	DESCRIPTION
	    "This attribute, when TRUE, indicates that the station
	    implementation is capable of supporting Phased Coexistence Operation. The
	    default value of this attribute is FALSE. "
        DEFVAL { false }
    ::= { dot11HTStationConfigEntry 10 }

dot11TransitionTime OBJECT-TYPE
	SYNTAX INTEGER (1..3)
	MAX-ACCESS read-only
	STATUS current
	DESCRIPTION
	    "This attribute indicates that the minimum transition time
	    within which the STA can switch between 20 MHz channel width and 40 MHz
	    channel width with a high probability. The encoding of the transition time to
	    this attribute is:
	    400 microsec
	    1500 microsec
	    5000 microsec
	    The default value of this attribute is 3. "
        DEFVAL { 3 }
    ::= { dot11HTStationConfigEntry 11 }

dot11MCSFeedbackOptionImplemented OBJECT-TYPE
	SYNTAX INTEGER { none(0), unsolicited (2), both (3) }
	MAX-ACCESS read-only
	STATUS current
	DESCRIPTION
	    "This attribute indicates the MCS feed back capability
	    supported by the station implementation. The default value of this attribute
	    is 0. "
        DEFVAL { none }
    ::= { dot11HTStationConfigEntry 12 }

dot11HTControlFieldSupported OBJECT-TYPE
	SYNTAX TruthValue
	MAX-ACCESS read-only
	STATUS current
	DESCRIPTION
	    "This attribute, when TRUE, indicates that the station
	    implementation is capable of receiving HT Control field. The default value
	    of this attribute is FALSE."
        DEFVAL { false }
    ::= { dot11HTStationConfigEntry 13 }

dot11RDResponderOptionImplemented OBJECT-TYPE
	SYNTAX TruthValue
	MAX-ACCESS read-only
	STATUS current
	DESCRIPTION
	    "This attribute, when TRUE, indicates that the station
	    implementation is capable operating as a RD responder. The default value of
	    this attribute is FALSE."
        DEFVAL { false }
    ::= { dot11HTStationConfigEntry 14 }

-- **********************************************************************
-- * End Of dot11HTStationConfig TABLE
-- **********************************************************************

-- ********************************************************************
-- * Conformance information - RSN
-- ********************************************************************

-- ********************************************************************
-- * Compliance Statements - RSN
-- ********************************************************************

dot11RSNCompliance MODULE-COMPLIANCE
	STATUS current
	DESCRIPTION
	    "The compliance statement for SNMPv2 entities that implement the
	    IEEE 802.11 RSN MIB."
	MODULE -- this module
	MANDATORY-GROUPS {
	    dot11RSNBase }
	    
-- OPTIONAL-GROUPS {dot11RSNPMKcachingGroup }
::= { dot11Compliances 2 }

-- ********************************************************************
-- * Groups - units of conformance - RSN
-- ********************************************************************

dot11RSNBase OBJECT-GROUP
	OBJECTS {
	    dot11RSNAConfigVersion,
	    dot11RSNAConfigPairwiseKeysSupported,
	    dot11RSNAConfigGroupCipher,
	    dot11RSNAConfigGroupRekeyMethod,
	    dot11RSNAConfigGroupRekeyTime,
	    dot11RSNAConfigGroupRekeyPackets,
	    dot11RSNAConfigGroupRekeyStrict,
	    dot11RSNAConfigPSKValue,
	    dot11RSNAConfigPSKPassPhrase,
	    dot11RSNAConfigGroupUpdateCount,
	    dot11RSNAConfigPairwiseUpdateCount,
	    dot11RSNAConfigGroupCipherSize,
	    dot11RSNAConfigPairwiseCipher,
	    dot11RSNAConfigPairwiseCipherEnabled,
	    dot11RSNAConfigPairwiseCipherSize,
	    dot11RSNAConfigAuthenticationSuite,
	    dot11RSNAConfigAuthenticationSuiteEnabled,
	    dot11RSNAConfigNumberOfPTKSAReplayCounters,
	    dot11RSNAConfigSATimeout,
	    dot11RSNAConfigNumberOfGTKSAReplayCounters,
	    dot11RSNAAuthenticationSuiteSelected,
	    dot11RSNAPairwiseCipherSelected,
	    dot11RSNAGroupCipherSelected,
	    dot11RSNAPMKIDUsed,
	    dot11RSNAAuthenticationSuiteRequested,
	    dot11RSNAPairwiseCipherRequested,
	    dot11RSNAGroupCipherRequested,
	    dot11RSNAStatsSTAAddress,
	    dot11RSNAStatsVersion,
	    dot11RSNAStatsSelectedPairwiseCipher,
	    dot11RSNAStatsTKIPICVErrors,
	    dot11RSNAStatsTKIPLocalMICFailures,
	    dot11RSNAStatsTKIPRemoteMICFailures,
--	    dot11RSNAStatsTKIPCounterMeasuresInvoked,
	    dot11RSNAStatsCCMPReplays,
	    dot11RSNAStatsCCMPDecryptErrors
--	    dot11RSNAStatsTKIPReplays,
--	    dot11RSNAStats4WayHandshakeFailures 
	    }
	STATUS current
	DESCRIPTION
	    "The dot11RSNBase object class provides the necessary support for
	    managing RSNA functionality in the STA."
::= { dot11Groups 126 }

dot11RSNPMKcachingGroup OBJECT-GROUP
	OBJECTS {
	    dot11RSNAConfigPMKLifetime,
		dot11RSNAConfigPMKReauthThreshold
		}
	STATUS current
	DESCRIPTION
	    "The dot11RSNPMKcachingGroup object class provides the necessary
	    support for managing PMK caching functionality in the STA"
::= { dot11Groups 27 }

-- **********************************************************************
-- *   End of 80211 MIB
-- **********************************************************************
END
