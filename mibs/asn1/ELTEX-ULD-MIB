-- -----------------------------------------------------------------------------
-- MIB NAME : Eltex ULD
-- FILE NAME: ELTEX-ULD-V2.mib
-- DATE     : 2013/01/28
-- VERSION  : 1.00
-- PURPOSE  : MIB structure of Unidirectional Link Detection
-- -----------------------------------------------------------------------------


ELTEX-ULD-MIB DEFINITIONS ::= BEGIN

        IMPORTS
            MODULE-IDENTITY,OBJECT-TYPE     FROM SNMPv2-SMI
            ifIndex                         FROM IF-MIB
            eltexLtd                        FROM ELTEX-SMI-ACTUAL
 			TruthValue                      FROM SNMPv2-TC;

        eltexULDMIB MODULE-IDENTITY
            LAST-UPDATED "201301280000Z"
            ORGANIZATION "Eltex Ltd."
            CONTACT-INFO
                "http://www.eltex.nsk.ru"
            DESCRIPTION
                "The unidirectioanl link detection module MIB."
           ::= { eltexLtd 34 }

eltexULDNotifications OBJECT IDENTIFIER ::= { eltexULDMIB 0 }
eltexULDMgmt OBJECT IDENTIFIER ::= {eltexULDMIB 1}

-- -----------------------------------------------------------------------------
-- eltexULDMgmt
-- -----------------------------------------------------------------------------

                eltexULDTable OBJECT-TYPE
                    SYNTAX  SEQUENCE OF EltexULDEntry
                    MAX-ACCESS not-accessible
                    STATUS current
                    DESCRIPTION
                        "The management information of the unidirectional link detection."
                    ::= { eltexULDMgmt 1 }

                eltexULDEntry OBJECT-TYPE
                        SYNTAX EltexULDEntry
                        MAX-ACCESS not-accessible
                        STATUS current
                        DESCRIPTION
                            "A list of information contained in eltexULDTable."
                        INDEX { ifIndex }
                        ::= { eltexULDTable 1 }

                EltexULDEntry ::=
                        SEQUENCE {
                                eltexULDAdminState
                                        INTEGER,
                                eltexULDOperStatus
                                        INTEGER,
                                   eltexULDMode
                                        INTEGER,
                                   eltexULDDiscoveryTime
                                        INTEGER,
                                   eltexULDIsAggressive
                                        TruthValue,
                                   eltexULDLinkStatus
                                        INTEGER
                        }


                eltexULDAdminState OBJECT-TYPE
                        SYNTAX INTEGER
                        {
                                 enabled(1),
                                disabled(2)
                        }
                        MAX-ACCESS  read-write
                        STATUS      current
                        DESCRIPTION
                                "This object indicates the unidirectional link detection configuration status."
                        DEFVAL   {disabled}
                        ::= { eltexULDEntry 1 }

                eltexULDOperStatus OBJECT-TYPE
                        SYNTAX INTEGER
                        {
                                 enabled(1),
                                disabled(2)
                        }
                        MAX-ACCESS  read-only
                        STATUS      current
                        DESCRIPTION
                                "This object is determined by local and remote port supporting OAM and unidirectional detection.
                                If both local and remote port support OAM and unidirectional detection, it is enabled(1),else it
                                is disabled(2)."
                        ::= { eltexULDEntry 2 }

                eltexULDMode OBJECT-TYPE
                        SYNTAX  INTEGER
                        {
                                log(1),
                                err-disable(2)
                        }
                        MAX-ACCESS   read-write
                        STATUS      current
                        DESCRIPTION
                                 "This object indicates the mode for unidirectional link detection.
                                  shutdown: if any unidirectional link is detected, disable the port and log an event.
                                  normal: only log an event when a unidirectional link is detected."
                        DEFVAL   {log}
                        ::= { eltexULDEntry 3 }

                eltexULDDiscoveryTime OBJECT-TYPE
                        SYNTAX INTEGER(5..300)
                        MAX-ACCESS   read-write
                        STATUS      current
                        DESCRIPTION
                                 "This object indicates the neighbor discovery time for unidirectional link detection.
                                 If the discovery time ends, the unidirectional link detection starts."
                        DEFVAL   { 5 }
                        ::= { eltexULDEntry 4 }

                eltexULDIsAggressive OBJECT-TYPE
                         SYNTAX  TruthValue
                         MAX-ACCESS   read-write
                         STATUS      current
                         DESCRIPTION
                                  "This object indicates the mode for
						 		   unidirectional link detection protocol.
                                   If true then port is considered to be
                                   UNIDIRECTIONAL if there is no answer
                                   from remote side during discovery
                                   timeout. If false then port is considered to be
                                   UNKNOWN."
                         DEFVAL   { false }
                         ::= { eltexULDEntry 5 }

                eltexULDLinkStatus OBJECT-TYPE
                        SYNTAX      INTEGER
                        {
                                unknown(1),
                                unidirectional(2),
                                bidirectional(3),
                                tx-rx-loop(4),
                                neighbor-mismatch(5)
                        }
                        MAX-ACCESS  read-only
                        STATUS      current
                        DESCRIPTION
                                "This object indicates the link status, which is a result of unidirectional link detection."
                        ::= {eltexULDEntry 6 }

-- -----------------------------------------------------------------------------
-- eltexULDNotifications
-- -----------------------------------------------------------------------------

   eltexULDLinkStatusChanged NOTIFICATION-TYPE
     OBJECTS { ifIndex,
               eltexULDLinkStatus
             }
     STATUS  current
     DESCRIPTION
       "A eltexULDLinkStatusChanged notification is sent when a local
       link status has been changed. This event should not be sent
       more then one per second."
    ::= { eltexULDNotifications 1 }
END
