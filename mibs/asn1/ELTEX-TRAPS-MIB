ELTEX-TRAPS-MIB DEFINITIONS ::= BEGIN

-- Title:                ELTEX MES-Series Wwitches
--                       Private TRAPS MIB
-- Version:              1.0
-- Date:                 1-Jan-2012

IMPORTS
    NOTIFICATION-TYPE                                   FROM SNMPv2-SMI
    elt                                                 FROM ELTEX-MIB
    rndErrorDesc, rndErrorSeverity                      FROM RADLAN-DEVICEPARAMS-MIB
    rldot1dStpTrapVrblifIndex, rldot1dStpTrapVrblVID    FROM RADLAN-BRIDGEMIBOBJECTS-MIB;

eltNotifications MODULE-IDENTITY
                LAST-UPDATED "201207130000Z"
                ORGANIZATION "Eltex Enterprise Co, Ltd."
                CONTACT-INFO
                      "www.eltex.nsk.ru"
                DESCRIPTION
                      "This private MIB module defines Eltex's private notifications"
                REVISION "201207130000Z"
                DESCRIPTION
                      "Initial revision."
        ::= { elt 0 }

-- Enterprise-specific traps for Eltex
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  eltNotifications
--       VARIABLES   { rndErrorDesc, rndErrorSeverity }
--       DESCRIPTION
--             ""
--       ::=
-- -------------

i2cBusFailure NOTIFICATION-TYPE
    OBJECTS   { rndErrorDesc, rndErrorSeverity }
    STATUS  current
    DESCRIPTION
        "An I2C bus malfunction detected. It means that a lot of I2C bus I/O
         transactions was completed unsuccessfully before and repairing efforts
         were vain. It is a critical event, all I2C-controllable HW nodes are
         unaccessible now."
    ::= { eltNotifications 3 }

i2cBusOperational NOTIFICATION-TYPE
    OBJECTS   { rndErrorDesc, rndErrorSeverity }
    STATUS  current
    DESCRIPTION
        "An I2C bus is now operational. Appearance of this trap means that bus
         operation was stick before and is repaired now."
    ::= { eltNotifications 4 }

END
