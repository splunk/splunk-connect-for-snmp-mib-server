Com-Server-Intern-MIB DEFINITIONS ::= BEGIN
----------------------------------------------------------------
-- Revison: 1.24
----------------------------------------------------------------
-- 29.10.2012
--
-- Added index entries for wtSeriTcpServerUrl, wtSeriUdpServerUrl, 
-- wtSeriTelnetServerUrl, wtSeriFtpServerUrl
-- 
-- Correction for wtUartFifo (underlines replaced)
--
----------------------------------------------------------------
-- Revison: 1.23
----------------------------------------------------------------
-- 08.10.2008
--
-- Correction for wtUartFifo (wrong values for UART FIFO)
-- 
-- New values for wtCableType: 
-- wtTwistedPair10FD
-- wtTwistedPair100HD
-- wtTwistedPair100FD
--
----------------------------------------------------------------
-- Revison: 1.22
----------------------------------------------------------------
-- 21.08.2007
--
-- Added new parameter to configure the range of the serial 
-- Receive Buffer for each port in
--  WtSeriPortEntry:
--    wtSeriInQueue   INTEGER
----------------------------------------------------------------
-- Revison: 1.21
----------------------------------------------------------------
-- 05.12.2007
--
-- 	New: In WtSeriPortEntry:
--    wtSeriPortState   INTEGER,
--    wtSeriRemotePort  INTEGER,
--    wtSeriRemoteIP    IpAddress,
----------------------------------------------------------------
-- Revison: 1.20
----------------------------------------------------------------
-- 27.09.2006
--
-- Table for wtCableType completed
-- Description for wtSeriTcpCAddress and wtSeriUdpCAddress completed
-- new: wtKeepAlive
--	wtRetransmTimeout
-- 	wtDhcpClient
-- 	wtWbmPort
-- 	wtDnsSrv
-- 	wtLinkSpeed
--	wtSeriControlPort
--	wtSeriTcpServerUrl
--	wtSeriUdpServerUrl
--	wtSeriTelnetServerUrl
--	wtSeriFtpServerUrl
----------------------------------------------------------------
-- Revison: 1.19
----------------------------------------------------------------
-- 18.10.2006
--
-- Correction: Table for wtBaudrate (58631,58431) and 
-- wtUartBaudrate (58031,58034,58231)
----------------------------------------------------------------
-- Revison: 1.18
----------------------------------------------------------------
-- 14.07.2004 	Separation into product families
--		
----------------------------------------------------------------
-- Revison: 1.17
----------------------------------------------------------------
-- 28.06.2004 	#57630/1/2, Webio Digital
--		New: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Puls filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		
-- This document describes the Management Information Base of the Com-Server with
-- which the current configuration can be read and written (analogous to
-- configuration via Telnet port 1111). For a complete explanation of all variables,
-- please refer also to the respective Com-Server manual.
--
-- IMPORTANT:
-- The variables for the branch .wut.wtComServer.wtComServerIntern.wtConfiguration
-- of the Com-Server-MIB can only be written if first the variable 
-- "wtComServer.wtComServerIntern.wtConfiguration.wtSystem.wtConfigMode" has been
-- written with value 2. Then the corresponding variables can be changed. To save the
-- changes in the Com-Server, the variable "...wtConfigMode" must be written with 
-- value 3. If the variable "...wtConfigMode" has a value of 1, all variable are then
-- read-only.
-- These variables cannot be not written if at the same time a connection to Telnet 
-- port 1111 on the Com-Server is open.
--
-- The variables of the branch .wut.wtComServer.wtComServerIntern.wtDigitalEaDriver can 
-- however always be read and written.

    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                		OBJECT IDENTIFIER ::= { enterprises 5040 }
    wtComServer        		OBJECT IDENTIFIER ::= { wut 1 }
    wtComServerIntern  		OBJECT IDENTIFIER ::= { wtComServer 1 }

--  comServer-Intern Tree

    wtConfiguration    		OBJECT IDENTIFIER ::= { wtComServerIntern 1 }
    wtDeaDriver        		OBJECT IDENTIFIER ::= { wtComServerIntern 2 }


--  wtConfiguration Tree

    wtSystem           		OBJECT IDENTIFIER ::= { wtConfiguration 1 }
    wtNetSetup         		OBJECT IDENTIFIER ::= { wtConfiguration 2 }
    wtSeriPortSetup    		OBJECT IDENTIFIER ::= { wtConfiguration 3 }
    wtDeaPortSetup     		OBJECT IDENTIFIER ::= { wtConfiguration 4 }

       
--  wtSystem Group
----------------------------

wtCableType OBJECT-TYPE
    SYNTAX INTEGER {
        wtCoax(1),
        wtTwistedPair(2),
        wtAui(3)
        wtTwistedPair10FD(4),
		wtTwistedPair100HD(8),
        wtTwistedPair100FD(16)
    }
    ACCESS read-only
    STATUS mandatory
    DESCRIPTION
        "Displays the Ethernet connection type used on the Com-Server."
    ::= { wtSystem 1 }

wtMacAddress OBJECT-TYPE
    SYNTAX PhysAddress
    ACCESS read-only
    STATUS mandatory
    DESCRIPTION
        "Displays the Ethernet address of the Com-Server."
    ::= { wtSystem 2 }

wtSwDate OBJECT-TYPE
    SYNTAX DisplayString
    ACCESS read-only
    STATUS mandatory
    DESCRIPTION
        "Displays the creation date 'month/year' of the firmware."
    ::= { wtSystem 3 }

wtSwRev OBJECT-TYPE
    SYNTAX DisplayString
    ACCESS read-only
    STATUS mandatory
    DESCRIPTION
        "Displays the revision number of the firmware."
    ::= { wtSystem 4 }

wtDevType OBJECT-TYPE
    SYNTAX DisplayString
    ACCESS read-only
    STATUS mandatory
    DESCRIPTION
        "Displays the Com-Server model."
    ::= { wtSystem 5 }

wtMibRev OBJECT-TYPE
    SYNTAX DisplayString
    ACCESS read-only
    STATUS mandatory
    DESCRIPTION
        "Displays the revision number of the Wiesemann & Theis MIB."
    ::= { wtSystem 6 }

wtRunTime OBJECT-TYPE
    SYNTAX TimeTicks
    ACCESS read-only
    STATUS mandatory
    DESCRIPTION
        "Displays the time since the last restart of the Com-Server in 1/100 seconds."
    ::= { wtSystem 7 }

wtPhysPorts OBJECT-TYPE
    SYNTAX INTEGER (1..4)
    ACCESS read-only
    STATUS mandatory
    DESCRIPTION
        "Displays the total number of ports available in the Com-Server 
        (RS232 port, digital I/O port, ...)."
    ::= { wtSystem 8 }

wtConfigMode OBJECT-TYPE
    SYNTAX INTEGER {
        wtConfigModeOff(1),
        wtConfigModeOn(2),
        wtSaveConfig(3)
    }
    ACCESS read-write
    STATUS mandatory
    DESCRIPTION
        "Defining this entry allows changing (wtConfigModeOn) and saving 
        (stSaveConfig) of all other entries in the Management Information Base 
        of the Com-Server. If the value is 1 (wtCOnfigModeOff), all other entries
        can be read only."
    ::= { wtSystem 16 }

wtPassword OBJECT-TYPE
    SYNTAX DisplayString (SIZE (8))
    ACCESS read-write
    STATUS mandatory
    DESCRIPTION
        "8-character Com-Server password for unrestricted access to the Com-Server
        configuration menu (Telnet port 1111). Only digits '0' to '9' and letters 'a' to 'f'
        may be used (e.g.: 'abcdef12')."
    ::= { wtSystem 17 }

wtSysPswd OBJECT-TYPE
    SYNTAX OCTET STRING
    ACCESS read-write
    STATUS mandatory
    DESCRIPTION
        "The system password, which may consist of maximum 32 characters and is terminated
		by a zero, is of a higher order than the Telnet password and protects all the
		following configuration and control accesses of the Com-Server:
		Port 1111: Telnet configuration menu
		Port 8003/8004: Reading/writing the configuration file
		Port 8888: Reset Com-Server
		Port 9084, 9184,9284, 9384: Reset Port Status A-D
		Port 9094, 9194,9294, 9394: Control port A-D
		Port 161: SNMP requests are only replied if the community corresponds to the 
		system password
		If the first character in the system password is a zero, this is deactivated."
    ::= { wtSystem 18 }

wtSysName OBJECT-TYPE
    SYNTAX OCTET STRING
    ACCESS read-write
    STATUS mandatory
    DESCRIPTION
        "The system name, which may consist of maximum 32 characters and is terminated
		by a zero, is used for identifying the Com-Server and is displayed as an opening 
		message for all Telnet connections.
		If the first character in the system password is a zero, this is deactivated."
    ::= { wtSystem 19 }



-- wtNetSetup Group
----------------------------

wtIpAddress OBJECT-TYPE
    SYNTAX NetworkAddress
    ACCESS read-write
    STATUS mandatory
    DESCRIPTION
        "IP address of the Com-Server."
    ::= { wtNetSetup 1 }

wtSubnetMask OBJECT-TYPE
    SYNTAX IpAddress
    ACCESS read-write
    STATUS mandatory
    DESCRIPTION
        "Subnet mask of the Com-Server."
    ::= { wtNetSetup 2 }

wtGateway OBJECT-TYPE
    SYNTAX IpAddress
    ACCESS read-write
    STATUS mandatory
    DESCRIPTION
        "IP address of the gateway for making the connections to other networks."
    ::= { wtNetSetup 3 }

wtMtu OBJECT-TYPE
    SYNTAX INTEGER (512..1024)
    ACCESS read-write
    STATUS mandatory
    DESCRIPTION
        "Maximum Transfer Unit of the Com-Server (maximum length of a datagram which the 
        Com-Server can send or receive)."
    ::= { wtNetSetup 4 }

wtBootpClient OBJECT-TYPE
    SYNTAX INTEGER {
        wtBootpClientOff(1),
        wtBootpClientOn(2)
    }
    ACCESS read-write
    STATUS mandatory
    DESCRIPTION
        "Activates and deactivates sending of a BOOTP request after the Com-Server is 
        restarted"
    ::= { wtNetSetup 5 }

wtKeepAlive OBJECT-TYPE
    SYNTAX INTEGER (2..65535)
    ACCESS read-write
    STATUS mandatory
    DESCRIPTION
        "Period of time without network traffic after the first Keep Alive Packet will be sent"
    ::= { wtNetSetup 6 }

wtRetransmTimeout OBJECT-TYPE
    SYNTAX INTEGER (1..65535)
    ACCESS read-write
    STATUS mandatory
    DESCRIPTION
        "Packet retransmission timeout in ms"
    ::= { wtNetSetup 7 }

wtDhcpClient OBJECT-TYPE
    SYNTAX INTEGER {
        wtDhcpClientOff(1),
        wtChcpClientOn(2)
    }
    ACCESS read-write
    STATUS mandatory
    DESCRIPTION
        "Activates/deactivates the DHCP client"
    ::= { wtNetSetup 8 }

wtWbmPort OBJECT-TYPE
    SYNTAX INTEGER (0..65535)
    ACCESS read-write
    STATUS mandatory
    DESCRIPTION
        "TCP port number for WebBasedManagement, 0=deactive"
    ::= { wtNetSetup 9 }

wtDnsSrv OBJECT-TYPE
    SYNTAX IpAddress
    ACCESS read-write
    STATUS mandatory
    DESCRIPTION
        "IP adress of DNS server."
    ::= { wtNetSetup 10 }

wtLinkSpeed OBJECT-TYPE
    SYNTAX INTEGER {
    	wtLinkSpeedAutonegotiation(1),
    	wtLinkSpeed10HD(2),
    	wtLinkSpeed10FD(3),
    	wtLinkSpeed100HD(4),
    	wtLinkSpeed100FD(5)
    }
    ACCESS read-write
    STATUS mandatory
    DESCRIPTION
        "Autonegotiation mode = ON or fix link speed"
    ::= { wtNetSetup 11 }



-- wtSeriPortSetup Group
----------------------------

wtSerialPorts OBJECT-TYPE
    SYNTAX INTEGER (1..4)
    ACCESS read-only
    STATUS mandatory
    DESCRIPTION
        "Number of serial ports on Com-Server"
    ::= { wtSeriPortSetup 1 }


-- Interface Table

wtSeriInterfaceTable OBJECT-TYPE
    SYNTAX SEQUENCE OF WtSeriInterfaceEntry
    ACCESS not-accessible
    STATUS mandatory
    DESCRIPTION
        "List of interface numbers for all serial ports."
    ::= { wtSeriPortSetup 2 }

wtSeriInterfaceEntry OBJECT-TYPE
    SYNTAX WtSeriInterfaceEntry
    ACCESS not-accessible
    STATUS mandatory
    DESCRIPTION
        "Interface number."
    INDEX  { wtSeriInterfaceNo }
    ::= { wtSeriInterfaceTable 1 }

WtSeriInterfaceEntry ::= SEQUENCE {
    wtSeriInterfaceNo INTEGER
}

wtSeriInterfaceNo OBJECT-TYPE
    SYNTAX INTEGER (1..4)
    ACCESS read-only
    STATUS mandatory
    DESCRIPTION
        "Interface number of the serial port."
    ::= { wtSeriInterfaceEntry 1 }


-- UART Table

wtSeriUartTable OBJECT-TYPE
    SYNTAX SEQUENCE OF WtSeriUartEntry
    ACCESS not-accessible
    STATUS mandatory
    DESCRIPTION
        "List of the UART configurations relevant to the interface number of
        the serial port."
    ::= { wtSeriPortSetup 3 }

wtSeriUartEntry OBJECT-TYPE
    SYNTAX WtSeriUartEntry
    ACCESS not-accessible
    STATUS mandatory
    DESCRIPTION
        "UART parameters for the serial port."
    INDEX  { wtSeriInterfaceNo }
    ::= { wtSeriUartTable 1 }

WtSeriUartEntry ::= SEQUENCE {
    wtBaudrate     INTEGER,
    wtParity       INTEGER,
    wtDatabits     INTEGER,
    wtStopbits     INTEGER,
    wtHsLines      OCTET STRING,
    wtHsFunctions  OCTET STRING,
    wtUartFifo     INTEGER,
    wtUartBaudrate INTEGER,
    wtBaudDivisor  INTEGER,
    wtSeriInQueue  INTEGER
}

wtBaudrate OBJECT-TYPE
    SYNTAX INTEGER {
        wtBaudrate-57600(1),
		wtBaudrate-38400(2),
		wtBaudrate-19200(3),
		wtBaudrate-14400(4),
		wtBaudrate-9600(5),
		wtBaudrate-4800(6),
		wtBaudrate-2400(7),
		wtBaudrate-1200(8),
		wtBaudrate-600(9),
		wtBaudrate-300(10),
		wtBaudrate-150(11),
		wtBaudrate-110(12),
		wtBaudrate-75(13),
		wtBaudrate-50(14),
		wtBaudrate-230400(15),
		wtBaudrate-115200(16),
		wtBaudrate-7200(17),
        wtBaudrate-special(18)
    }
    ACCESS read-write
    STATUS mandatory
    DESCRIPTION
        "Baud rate of the serial CPU port. wtBaudrate-special is read only.
        If wtBaudDivisor is >0 the value of wtBaudrate is 18
        wtBaudrate-14400 is on available with Com-Servers 58211,58411 and 58412.
        wtBaudrate=11 to wtBaudrate=18 are only available with Com-Servers 58631 and 58431"
    ::= { wtSeriUartEntry 1 }

wtParity OBJECT-TYPE
    SYNTAX INTEGER {
        wtNoParity(1),
        wtOddParity(2),
        wtEvenParity(3),
        wtMarkOddParity(4),
        wtMarkEvenParity(5)
    }
    ACCESS read-write
    STATUS mandatory
    DESCRIPTION
        "Parity"
    ::= { wtSeriUartEntry 2 }

wtDatabits OBJECT-TYPE
    SYNTAX INTEGER {
        wtDataBits-8(1),
        wtDataBits-7(2),
        wtDataBits-6(3),
        wtDataBits-5(4)
    }
    ACCESS read-write
    STATUS mandatory
    DESCRIPTION
        "Number of data bits"
    ::= { wtSeriUartEntry 3 }

wtStopbits OBJECT-TYPE
    SYNTAX INTEGER {
        wtStopBits-1(1),
        wtStopBits-2(2)
    }
    ACCESS read-write
    STATUS mandatory
    DESCRIPTION
        "Number of stop bits"
    ::= { wtSeriUartEntry 4 }

wtHsLines OBJECT-TYPE
    SYNTAX OCTET STRING (SIZE (2))
    ACCESS read-write
    STATUS mandatory
    DESCRIPTION
        "These two octets are interpreted bit-by-bit and describe individual values 
        for configuring the handshake procedure. Bit 0 corresponds to the LSB.

        Octet  Bit Name            Description
        ----  ---- ------------    ------------------------
        1      0,1,6,7             not used
               2   inxfilter       1: enable xon/xoff filter while receiving
               3   outxfilter      1: enable xon/xoff filter while sending
               4   rts-default     1: while RTS is not used, RTS is active
               5   dtr-default     1: while DTR is not used, DTR is active
        2      0   rts-disable     1: RTS will not change at LOCK/UNLOCK
               1   dtr-disable     1: DTR will not change at LOCK/UNLOCK
               2   outx            1: enable software handshake while sending
               3   inx             1: enable software handshake while receiving
               4   outx-cts        1: enable hardware handshake on CTS
               5   outx-dsr        1: enable hardware handshake on DSR
               6   inx-dtr         1: enable hardware handshake on DTR
               7   inx-rts         1: enable hardware handshake on RTS
        Standard default settings:
        OCTET 1  OCTET 2  Function
        -------- -------- ----------------
        30h      03h      No Handshake
        00h      91h      Hardware Handshake
        3Ch      0Fh      Software Handshake (Send/Receive Filter ON)"
    ::= { wtSeriUartEntry 5 }

wtHsFunctions OBJECT-TYPE
    SYNTAX OCTET STRING (SIZE (1))
    ACCESS read-write
    STATUS mandatory
    DESCRIPTION
        "This octet is interpreted bit-by-bit and describes functions which can be 
        assigned to the handshake lines. Bit 0 corresponds to the LSB.

        Octet  Bit Name            Description
        ----  ---- ------------    ------------------------
        1      0   cts-connect     1: connect/disconnect with CTS (HIGH/LOW)
               1   dsr-connect     1: connect/disconnect with DSR (HIGH/LOW)
               2   cts-accept      1: accept connection only by CTS=HIGH
               3   dsr-accept      1: accept connection only by DSR=HIGH
               4-7                 not used"
    ::= { wtSeriUartEntry 6 }

wtUartFifo OBJECT-TYPE
    SYNTAX INTEGER {
        wtUartFifo-disable(0),
	wtUartFifo-8-8(1),
	wtUartFifo-16-16(3),
	wtUartFifo-32-56(5),
        wtUartFifo-56-60(7)
    }
    ACCESS read-write
    STATUS mandatory
    DESCRIPTION
        "Send/Receive Fifo Trigger Level of the UART port"
    ::= { wtSeriUartEntry 7 }

wtUartBaudrate OBJECT-TYPE
    SYNTAX INTEGER {
        wtUartBaudrate-230400(1),
		wtUartBaudrate-153600(2),
		wtUartBaudrate-115200(3),
		wtUartBaudrate-57600(4),
		wtUartBaudrate-38400(5),
		wtUartBaudrate-19200(6),
		wtUartBaudrate-9600(7),
		wtUartBaudrate-7200(8),
		wtUartBaudrate-4800(9),
		wtUartBaudrate-2400(10),
		wtUartBaudrate-1200(11),
		wtUartBaudrate-600(12),
		wtUartBaudrate-300(13),
		wtUartBaudrate-150(14),
		wtUartBaudrate-75(15),
		wtUartBaudrate-50(16),
		wtUartBaudrate-110(17),
        wtUartBaudrate-special(18)
    }
    ACCESS read-write
    STATUS mandatory
    DESCRIPTION
        "Baud rate of the UART port. With Com-Server 58631 and 58431 wtBaudrate istead of 
        wtUartBaudrate must be used.
        wtUartBaudrate-special is read only. If wtUartBaudDivisor is >0 the value of 
        wtUartBaudrate is 18"
    ::= { wtSeriUartEntry 8 }

wtBaudDivisor OBJECT-TYPE
    SYNTAX INTEGER (0..32767)
    ACCESS read-write
    STATUS mandatory
    DESCRIPTION
        "Baud Divisor of the serial p ort (special baud rate)."
    ::= { wtSeriUartEntry 9 }
    
wtSeriInQueue OBJECT-TYPE
    SYNTAX INTEGER (32..4094)
    ACCESS read-write
    STATUS mandatory
    DESCRIPTION
        "Serial Receive Buffer in Bytes. The value must be even. The maximum value for all
        models with more than one serial port and also the Office, Compact and 19' versions
        is 3070 bytes. For all other Com-Server models the maximum value is 4094."
    ::= { wtSeriUartEntry 10 }


-- Serial Port Table

wtSeriPortTable OBJECT-TYPE
    SYNTAX SEQUENCE OF WtSeriPortEntry
    ACCESS not-accessible
    STATUS mandatory
    DESCRIPTION
        "List of the general port entries relevant to the interface number of the
        serial port."
    ::= { wtSeriPortSetup 4 }

wtSeriPortEntry OBJECT-TYPE
    SYNTAX WtSeriPortEntry
    ACCESS not-accessible
    STATUS mandatory
    DESCRIPTION
        "Port entries for the serial port."
    INDEX  { wtSeriInterfaceNo }
    ::= { wtSeriPortTable 1 }

WtSeriPortEntry ::= SEQUENCE {
    wtSeriLocalPort   INTEGER,
    wtSeriPortMode    INTEGER,
    wtSeriControlPort INTEGER,
    wtSeriPortState   INTEGER,
	wtSeriRemotePort  INTEGER,
    wtSeriRemoteIP    IpAddress,
    wtSeriNetPckDelay INTEGER,
    wtSeriFlushBuf    INTEGER,
    wtSeriTelnetEcho  INTEGER
}           


wtSeriLocalPort OBJECT-TYPE
    SYNTAX INTEGER (1..65535)
    ACCESS read-write
    STATUS mandatory
    DESCRIPTION
        "Local TCP/UDP port number of the Com-Server port on which the Com-Server 
        accepts a TCP connection or which it used in TCP client mode or UDP mode as a 
        local port."
    ::= { wtSeriPortEntry 1 }

wtSeriPortMode OBJECT-TYPE
    SYNTAX INTEGER {
        wtSeriServerMode(1),
        wtSeriTcpClient(2),
        wtSeriTelnetClient(3),
        wtSeriFtpClient(4),
        wtSeriBox2BoxMaster(5),
        wtSeriUdpMode(6),
        wtSeriMultiportProtokoll(7),
        wtSeriBox2BoxSlave(8),
        wtSeriSlipMode(9),
        wtSeriIpBusSlave(10),
        wtSeriIpBusMaster(11)
    }
    ACCESS read-write
    STATUS mandatory
    DESCRIPTION
        "This parameter specifies the mode of the Com-Server port. Depending 
        on which mode is set, the corresponding list of the relevant parameters
        is available. If for example Upd mode (wtSeriPortMode = 6) is
        configured, only the list wtSeriUdpClientTable is available. In Server 
        Mode (wtSeriPortMode = 1) no list of the port mode configuration is 
        available."
    ::= { wtSeriPortEntry 2 }

wtSeriControlPort OBJECT-TYPE
    SYNTAX INTEGER (0..65535)
    ACCESS read-write
    STATUS mandatory
    DESCRIPTION
        "TCP port number of the Com-Server's control port. In TCP client or TCP server 
        mode this port allows to change settings like baud rate, parity etc. of the serial 
        interface. The control port can be opened in addition to the data connection."
    ::= { wtSeriPortEntry 3 }

wtSeriPortState OBJECT-TYPE
    SYNTAX INTEGER {
        wtSeriPortFree(0),
        wtSeriPortInUse(1),
        wtSeriPortLockScanning(2),
        wtSeriPortLockConnected(3),
        wtSeriPortLockUnconnected(4)
    }
    ACCESS read-only
    STATUS mandatory
    DESCRIPTION
        "This value specifies the the connection state of the serial port.
        0=Server mode, no connection
        1=Server mode, active connection
        2=Special mode, attempting to establish a connection
        3=Special mode, active connection or special mode configured (e.g. SLIP router)
        4=Special mode, no connection
        The values wtSeriRemotePort and wtSeriRemoteIP includes the belonging connection parameters"
    ::= { wtSeriPortEntry 4 }

wtSeriRemotePort OBJECT-TYPE
    SYNTAX INTEGER  (0..65535)
    ACCESS read-only
    STATUS mandatory
    DESCRIPTION
        "If the serial port has an active TCP or UDP connection, this value shows 
        the port number of the remote host."
    ::= { wtSeriPortEntry 5 }

wtSeriRemoteIP OBJECT-TYPE
    SYNTAX IpAddress
    ACCESS read-only
    STATUS mandatory
    DESCRIPTION
        "If the serial port has an active TCP or UDP connection, this value shows 
        the IP address of the remote host."
    ::= { wtSeriPortEntry 6 }
    
wtSeriNetPckDelay OBJECT-TYPE
    SYNTAX INTEGER (0..65535)
    ACCESS read-write
    STATUS mandatory
    DESCRIPTION
        "This value indicates the minimum wait time in 10ms ticks of the Com-Server 
        after the arrival of serial data. After this time has expired, it packs the 
        data into a network packet and sends them to the respective communication 
        partner. Default setting 0 means an attempt is made to send the data as 
        quickly as possible. The resulting high time transparency comes with the 
        drawback of a higher number of network packets.
        If the serial transmission is done in predictable block sizes, adjusting this 
        value will optimize the network load. In addition, there is the advantage 
        that the serial blocks are sent within a network packet and thus reach the 
        recipient at the same time. 
        Please refer also to the Com-Server manual."
    ::= { wtSeriPortEntry 10 }

wtSeriFlushBuf OBJECT-TYPE
    SYNTAX INTEGER {
        wtSeriFlushBufOff(1),
        wtSeriFlushBufOn(2)
    }
    ACCESS read-write
    STATUS mandatory
    DESCRIPTION
        "If this switch is active (2), the serial buffer is flushed each time a 
        new connection is opened; any residual data which could not be sent (e.g., 
        handshake stop of the serial terminal device) are therefore lost. But if 
        you connect a terminal device to the Com-Server which for example requires 
        a longer handshake, you can prevent flushing of the buffer by deactivating 
        the switch (1). Then several connections can be opened in turn on the 
        network side and the data are accumulated in the buffer until they are 
        sent."
    ::= { wtSeriPortEntry 11 }

wtSeriTelnetEcho OBJECT-TYPE
    SYNTAX INTEGER {
        wtSeriTelnetEchoOff(1),
        wtSeriTelnetEchoOn(2)
    }
    ACCESS read-write
    STATUS mandatory
    DESCRIPTION
        "When opening a Telnet connection, there is negotiation on the network
        side to determine who generates the echo of the characters sent by the
        client. Either the client application generates a local echo, or the
        Telnet server generates a remote echo by immediately sending back all
        received characters. The Telnet echo option on the Com-Server is defined
        as follows:
        Telnet echo = active (2)
        The Com-Server negotiates a remote echo with the client application and
        local echo is deactivated. In this case the device serially connected to
        the Com-Server must generate the echo.
        Telnet echo = deactivated (1)
        The Com-Server tells the client application when the connection is opened
        that is not generating an echo, which results in activation of local
        echo. Local echo may have to be manually turned on on the Telnet client."
    ::= { wtSeriPortEntry 12 }


-- Lists of port mode configurations
-- These lists contain only entries of the serial ports configured in the
-- corresponding mode.

-- TCP-Client-Mode
--
-- This list contains entries for all serial ports whose port mode (variable:
-- ".wtConfiguration(1).wtSeriPortSetup(3).wtSeriPortTable(4).wtSeriPortEntry(1)
--  .wtSeriPortMode(2)" has the value wtSeriTcpClient(2).

wtSeriTcpClientTable OBJECT-TYPE
    SYNTAX SEQUENCE OF WtSeriTcpClientEntry
    ACCESS not-accessible
    STATUS mandatory
    DESCRIPTION
        "List of all serial ports in TCP client mode relevant to their
        interface number."
    ::= { wtSeriPortSetup 5 }

wtSeriTcpClientEntry OBJECT-TYPE
    SYNTAX WtSeriTcpClientEntry
    ACCESS not-accessible
    STATUS mandatory
    DESCRIPTION
        "TCP-Client-Mode parameters"
    INDEX  { wtSeriInterfaceNo }
    ::= { wtSeriTcpClientTable 1 }

WtSeriTcpClientEntry ::= SEQUENCE {
    wtSeriTcpServerPort      INTEGER,
    wtSeriTcpServerIp        IpAddress,
    wtSeriTcpInactTimeout    INTEGER,
    wtSeriTcpConnectTimeout  INTEGER,
    wtSeriTcpDisconnectChar  OCTET STRING,
    wtSeriTcpDispString1     OCTET STRING,
    wtSeriTcpDispString2     OCTET STRING,
    wtSeriTcpCAddress        INTEGER,
    wtSeriTcpResponseMode    INTEGER,
    wtSeriTcpServerUrl       OCTET STRING
}

wtSeriTcpServerPort OBJECT-TYPE
    SYNTAX INTEGER (0..65535)
    ACCESS read-write
    STATUS mandatory
    DESCRIPTION
        "Port number which the application (TCP server process) addresses on the computer."
    ::= { wtSeriTcpClientEntry 1 }

wtSeriTcpServerIp OBJECT-TYPE
    SYNTAX IpAddress
    ACCESS read-write
    STATUS mandatory
    DESCRIPTION
        "IP address of the computer on which the application (TCP server process) is active."
    ::= { wtSeriTcpClientEntry 2 }

wtSeriTcpInactTimeout OBJECT-TYPE
    SYNTAX INTEGER (0..65535)
    ACCESS read-write
    STATUS mandatory
    DESCRIPTION
        "Connection timeout in seconds. If no data are exchanged within the
        specified time, the Com-Server closes the connection to the server. The
        value 0 deactivates the timer."
    ::= { wtSeriTcpClientEntry 3 }

wtSeriTcpConnectTimeout OBJECT-TYPE
    SYNTAX INTEGER (0..65535)
    ACCESS read-write
    STATUS mandatory
    DESCRIPTION
        "Connection timeout in seconds. This value is only effective in
        conjunction with an activated Inactivity Timeout. After the Inactivity
        Timeout has expired, the Com-Server attempts for the duration of the
        Connection Timeout to transmit any user data not yet sent. If it does not
        receive a reply from the TCP server within this time, it may be assumed
        that the server is hung. The data are then rejected and the connection
        reset. To prevent unintended data loss, choose a value which is 
        appropriately large. Value 0 deactivates the timeout."
    ::= { wtSeriTcpClientEntry 4 }

wtSeriTcpDisconnectChar OBJECT-TYPE
    SYNTAX OCTET STRING (SIZE (1))
    ACCESS read-write
    STATUS mandatory
    DESCRIPTION
        "If the Com-Server receives the character set here on the serial port, the
        connection to the TCP server is closed. The character itself is not sent to the
        TCP server. The value 0 deactivates this mode."
    ::= { wtSeriTcpClientEntry 5 }

wtSeriTcpDispString1 OBJECT-TYPE
    SYNTAX OCTET STRING (SIZE (2))
    ACCESS read-write
    STATUS mandatory
    DESCRIPTION
        "These parameters allow compact sending of serial data to the network;
        the serial data stream is not broken up randomly, but rather serial 
        packets can be sent in their original context even over the network as 
        one packet.
        Enter in wtSeriTcpDispString1 and/or wtSeriTcpDispString2 two characters
        each that you want the serial data stream searched for. Only if one of the
        two strings is found are the data from the serial port packed into network 
        packets. If you only want to look for one character, set 
        wtSeriTcpDispString2 to 0. If for example you configure 
        wtSeriTcpDispString1 to 3100h and wtSeriTcpDispString2 to 0, only
        character 1 is searched for. Both Dispatch Strings = 0 deactivates the
        mode.
        IMPORTANT: These characters are sent to the TCP server!"
    ::= { wtSeriTcpClientEntry 6 }

wtSeriTcpDispString2 OBJECT-TYPE
    SYNTAX OCTET STRING (SIZE (2))
    ACCESS read-write
    STATUS mandatory
    DESCRIPTION
        "See DESCRIPTION of wtSeriTcpDispString1."
    ::= { wtSeriTcpClientEntry 7 }

wtSeriTcpCAddress OBJECT-TYPE
    SYNTAX INTEGER {
        wtSeriTcpCAddressOff(1),
        wtSeriTcpCAddressOn(2)
    }
    ACCESS read-write
    STATUS mandatory
    DESCRIPTION
        "Activating this switch activates TCP client mode for changing TCP 
        servers. The address of the TCP server does not have to be permanently
        configured, but rather is sent on the serial interface before the user 
        data as an ASCII string. The string for the addressing is not sent.
        There are two possibilities for string format:
        1. The parameters 'wtSeriTcpServerPort' and 'wtSeriTcpServerIp' are equal
           to zero. Format: 
           C IP address, Port number<CR> (e.g. 'C172.16.231.101,4800<CR>')
           C URL, Port number<CR>        (e.g. 'Cworkpc.homeip.net,4800<CR>')
        2. The parameter 'wtSeriTcpServerPort' contains the Default Port (e.g.,
           4800), 'wtSeriTcpServerIP' contains the first three bytes of the IP 
           address (e.g., 172.16.231.0)
           Format: C4.byte IP address (e.g., 'C101<CR>')
        The string is not allowed to contain any spaces!"
    ::= { wtSeriTcpClientEntry 8 }

wtSeriTcpResponseMode OBJECT-TYPE
    SYNTAX INTEGER {
        wtSeriTcpRespModeOff(1),
        wtSeriTcpRespModeOn(2)
    }
    ACCESS read-write
    STATUS mandatory
    DESCRIPTION
        "In Response Mode the application, special characters are output which 
        are used to inform the application in the serial terminal device about 
        the network-side connection status of the Com-Server This function is 
        only available in TCP client mode.
        The following messages are output on the serial port:
        C (connected):
           The connection was opened successfully. There is a TCP connection to the server.
        N (not connected):
           The connection was not opened successfully. The TCP server is not responding.
        D (disconnected):
           The connection query was rejected by the TCP server or a previously open 
           connection was properly ended by the TCP server or by the Com-Server.
        Ixxx.xxx.xxx.xxx (invoked by...): 
           A client application on the indicated station has successfully opened 
           a TCP connection to the Com-Server (e.g., I172.20.20.1)."
    ::= { wtSeriTcpClientEntry 10 }

wtSeriTcpServerUrl OBJECT-TYPE
    SYNTAX OCTET STRING
    ACCESS read-write
    STATUS mandatory
    DESCRIPTION
        "URL of the computer on which your application (TCP server process) is active. The URL
         can be used instead of an IP address and only in conjunction with a valid DNS server.
         The URL contains a maximum of 64 characters and is terminated with a 0x00. If the
         fist character is 0x00, the URL is empty."
    ::= { wtSeriTcpClientEntry 11 }


-- UDP-Mode
--
-- This list contains entries for all serial ports whose port mode (Variable:
-- ".wtConfiguration(1).wtSeriPortSetup(3).wtSeriPortTable(4).wtSeriPortEntry(1)
--  .wtSeriPortMode(2)" has the value wtSeriUdpMode(6).

wtSeriUdpClientTable OBJECT-TYPE
    SYNTAX SEQUENCE OF WtSeriUdpClientEntry
    ACCESS not-accessible
    STATUS mandatory
    DESCRIPTION
        "List of all serial ports in UDP mode relevant to their interface number"
    ::= { wtSeriPortSetup 6 }

wtSeriUdpClientEntry OBJECT-TYPE
    SYNTAX WtSeriUdpClientEntry
    ACCESS not-accessible
    STATUS mandatory
    DESCRIPTION
        "UDP mode parameters"
    INDEX  { wtSeriInterfaceNo }
    ::= { wtSeriUdpClientTable 1 }

WtSeriUdpClientEntry ::= SEQUENCE {
    wtSeriUdpServerPort      INTEGER,
    wtSeriUdpServerIp        IpAddress,
    wtSeriUdpDispString1     OCTET STRING,
    wtSeriUdpDispString2     OCTET STRING,
    wtSeriUdpSeriProtocol    INTEGER,
    wtSeriUdpSeriCoding      INTEGER,
    wtSeriUdpCAddress        INTEGER,
    wtSeriUdpWrCAddress      INTEGER,
    wtSeriUdpDisconnectChar  OCTET STRING,
    wtSeriUdpServerUrl       OCTET STRING
}

wtSeriUdpServerPort OBJECT-TYPE
    SYNTAX INTEGER (0..65535)
    ACCESS read-write
    STATUS mandatory
    DESCRIPTION
        "Port number which the application (UDP server process) addresses on the computer."
    ::= { wtSeriUdpClientEntry 1 }

wtSeriUdpServerIp OBJECT-TYPE
    SYNTAX IpAddress
    ACCESS read-write
    STATUS mandatory
    DESCRIPTION
        "IP address of the computer on which the application (UDP server process) is active."
    ::= { wtSeriUdpClientEntry 2 }

wtSeriUdpDispString1 OBJECT-TYPE
    SYNTAX OCTET STRING (SIZE (2))
    ACCESS read-write
    STATUS mandatory
    DESCRIPTION
        "These parameters allow compact sending of serial data to the network;
        the serial data stream is not broken up randomly, but rather serial
        packets can be sent in their original context even over the network as
        one packet.
        Enter in wtSeriUdpDispString1 and/or wtSeriUdpDispString2 two characters 
        each that you want the serial data stream searched for. Only if one of
        the two strings is found are the data from the serial port packed into 
        network packets. If you only want to look for one character, set
        wtSeriUdpDispString2 to 0. If for example you configure wtSeriTcpDispString1
        to 3100h and wtSeriUdpDispString2 to 0, only character 1 is searched for.
        Both Dispatch Strings = 0 deactivates the mode.
        IMPORTANT: These characters are sent to the UDP server!"
    ::= { wtSeriUdpClientEntry 3 }

wtSeriUdpDispString2 OBJECT-TYPE
    SYNTAX OCTET STRING (SIZE (2))
    ACCESS read-write
    STATUS mandatory
    DESCRIPTION
        "See DESCRIPTION of wtSeriUdpDispString1."
    ::= { wtSeriUdpClientEntry 4 }

wtSeriUdpSeriProtocol OBJECT-TYPE
    SYNTAX INTEGER {
        wtSeriUdpProtocolOff(1),
        wtSeriUdpProtocolOn(2)
    }
    ACCESS read-write
    STATUS mandatory
    DESCRIPTION
        "The protocol mode which can be activated here has been replaced by 
        the 'Serial Socket Interface' (Mode: Multiport Protocol). For reasons of downward
        compatibility the functions are still available, but for new projects you should 
        use the 'Serial Socket Interface'."
    ::= { wtSeriUdpClientEntry 5 }

wtSeriUdpSeriCoding OBJECT-TYPE
    SYNTAX INTEGER {
        wtSeriUdpSeriCodingOff(1),
        wtSeriUdpSeriCodingOn(2)
    }
    ACCESS read-write
    STATUS mandatory
    DESCRIPTION
        "See DESCRIPTION of wtSeriUdpSeriProtocol."
    ::= { wtSeriUdpClientEntry 6 }

wtSeriUdpCAddress OBJECT-TYPE
    SYNTAX INTEGER {
        wtSeriUdpCAddressOff(1),
        wtSeriUdpCAddressOn(2)
    }
    ACCESS read-write
    STATUS mandatory
    DESCRIPTION
        "Activating this option activates UDP client mode for changing UDP
        servers. The address of the UDP server does not have to be permanently  
        configured, but rather is sent on the serial interface before the user 
        data as an ASCII string. The string for the addressing is not sent. 
        There are two possibilities for string format:
        1. The parameters 'wtSeriUdpServerPort' and 'wtSeriUdpServerIp' are equal
        to zero. Format: 
           C IP address, Port number<CR> (e.g. 'C172.16.231.101,4800<CR>')
           C URL, Portnummer<CR>         (e.g. 'Cworkpc.homeip.net,4800<CR>') 
        2. The parameter 'wtSeriUdpServerPort' contains the Default Port (e.g., 
           4800), 'wtSeriUdpServerIP' contains the first three bytes of the IP 
           address (e.g., 172.16.231.0)
           Format: C4.byte IP address (e.g., 'C101<CR>')
        The string is not allowed to contain any spaces!"
    ::= { wtSeriUdpClientEntry 7 }

wtSeriUdpWrCAddress OBJECT-TYPE
    SYNTAX INTEGER {
        wtSeriUdpWrCAddressOff(1),
        wtSeriUdpWrCAddressOn(2)
    }
    ACCESS read-write
    STATUS mandatory
    DESCRIPTION
        "Set this switch to active (2) to output the address of the sender in ASCII format 
        before sending the data of a UDP datagram to the serial port. The string always 
        contains 22 characters.
        Format: C IP address, port number (e.g., 'C172.016.231.101,04800')"
    ::= { wtSeriUdpClientEntry 8 }

wtSeriUdpDisconnectChar OBJECT-TYPE
    SYNTAX OCTET STRING (SIZE (1))
    ACCESS read-write
    STATUS mandatory
    DESCRIPTION
        "This parameter is only evaluated if the variable wtSeriUdpCAddress is
        activated. If the Com-Server port on the serial interface receives the
        character configured here, it deletes the last serially received UDP
        server address. The character itself is not send. A value of 0
        deactivates this mode."
    ::= { wtSeriUdpClientEntry 9 }

wtSeriUdpServerUrl OBJECT-TYPE
    SYNTAX OCTET STRING
    ACCESS read-write
    STATUS mandatory
    DESCRIPTION
        "URL of the computer on which your application (UDP process) is active. The URL
         can be used instead of an IP address and only in conjunction with a valid DNS server.
         The URL contains a maximum of 64 characters and is terminated with a 0x00. If the
         fist character is 0x00, the URL is empty."
    ::= { wtSeriUdpClientEntry 10 }


-- Telnet-Client-Mode
--
-- This list contains entries for all serial ports whose port mode (Variable:
-- ".wtConfiguration(1).wtSeriPortSetup(3).wtSeriPortTable(4).wtSeriPortEntry(1)
--  .wtSeriPortMode(2)" has the value wtSeriTelnetClient(3).

wtSeriTelnetClientTable OBJECT-TYPE
    SYNTAX SEQUENCE OF WtSeriTelnetClientEntry
    ACCESS not-accessible
    STATUS mandatory
    DESCRIPTION
        "List of all serial ports in Telnet client mode relevant to their 
        interface number"
    ::= { wtSeriPortSetup 7 }

wtSeriTelnetClientEntry OBJECT-TYPE
    SYNTAX WtSeriTelnetClientEntry
    ACCESS not-accessible
    STATUS mandatory
    DESCRIPTION
        "Telnet client mode parameters"
    INDEX  { wtSeriInterfaceNo }
    ::= { wtSeriTelnetClientTable 1 }

WtSeriTelnetClientEntry ::= SEQUENCE {
    wtSeriTelnetServerPort     INTEGER,
    wtSeriTelnetServerIp       IpAddress,
    wtSeriTelnetInactTimeout   INTEGER,
    wtSeriTelnetDisconnectChar OCTET STRING,
    wtSeriTelnetChangeLineout  INTEGER,
    wtSeriTelnetServerUrl      OCTET STRING
}

wtSeriTelnetServerPort OBJECT-TYPE
    SYNTAX INTEGER (0..65535)
    ACCESS read-write
    STATUS mandatory
    DESCRIPTION
        "Port number addressed by the Telnet server (Standard Telnet-Port: 23)."
    ::= { wtSeriTelnetClientEntry 1 }

wtSeriTelnetServerIp OBJECT-TYPE
    SYNTAX IpAddress
    ACCESS read-write
    STATUS mandatory
    DESCRIPTION
        "IP address of the computer on which the Telnet server is active."
    ::= { wtSeriTelnetClientEntry 2 }

wtSeriTelnetInactTimeout OBJECT-TYPE
    SYNTAX INTEGER (0..65535)
    ACCESS read-write
    STATUS mandatory
    DESCRIPTION
        "Timeout in seconds after which the Com-Server port closes the connection. 
        The timer is reset when there is an active network connection if data are being 
        exchanged. If however no data are sent during the specified time, the Com-Server
        port closes the connection to the Telnet server."
    ::= { wtSeriTelnetClientEntry 3 }

wtSeriTelnetDisconnectChar OBJECT-TYPE
    SYNTAX OCTET STRING (SIZE (1))
    ACCESS read-write
    STATUS mandatory
    DESCRIPTION
        "If the Com-Server port receives the character configured here on the 
        serial port, the Com-Server port closes the connection to the Telnet 
        server. It is important that this value not be used within a Telnet 
        session, since this would result in premature closing of the connection. 
        The character itself is not sent."
    ::= { wtSeriTelnetClientEntry 4 }

wtSeriTelnetChangeLineout OBJECT-TYPE
    SYNTAX INTEGER {
        wtSeriTelnetChangeLineoutOff(1),
        wtSeriTelnetChangeLineoutOn(2)
    }
    ACCESS read-write
    STATUS mandatory
    DESCRIPTION
        "If this switch is activated, a 00H is appended to the serially received 
        character 0DH: 0DH 00H is thus sent over the network. This option may need to 
        be activated when sending binary data."
    ::= { wtSeriTelnetClientEntry 5 }

wtSeriTelnetServerUrl OBJECT-TYPE
    SYNTAX OCTET STRING
    ACCESS read-write
    STATUS mandatory
    DESCRIPTION
        "URL of the computer on which your application (Telnet server process) is active. The URL
         can be used instead of an IP address and only in conjunction with a valid DNS server.
         The URL contains a maximum of 64 characters and is terminated with a 0x00. If the
         fist character is 0x00, the URL is empty."
    ::= { wtSeriTelnetClientEntry 6 }


-- FTP-Client-Mode
--
-- This list contains entries for all serial ports whose port mode (variable:
-- ".wtConfiguration(1).wtSeriPortSetup(3).wtSeriPortTable(4).wtSeriPortEntry(1)
--  .wtSeriPortMode(2)" has the value wtSeriFtpClient(4).

wtSeriFtpClientTable OBJECT-TYPE
    SYNTAX SEQUENCE OF WtSeriFtpClientEntry
    ACCESS not-accessible
    STATUS mandatory
    DESCRIPTION
        "List of all serial ports in FTP client mode relevant to their interface number"
    ::= { wtSeriPortSetup 8 }

wtSeriFtpClientEntry OBJECT-TYPE
    SYNTAX WtSeriFtpClientEntry
    ACCESS not-accessible
    STATUS mandatory
    DESCRIPTION
        "FTP client mode parameters"
    INDEX  { wtSeriInterfaceNo }
    ::= { wtSeriFtpClientTable 1 }

WtSeriFtpClientEntry ::= SEQUENCE {
    wtSeriFtpServerPort      INTEGER,
    wtSeriFtpServerIp        IpAddress,
    wtSeriFtpAutoFtp         INTEGER,
    wtSeriFtpLoginString     OCTET STRING,
    wtSeriFtpInactTimeout    INTEGER,
    wtSeriFtpConnectTimeout  INTEGER,
    wtSeriFtpProtocolChar    OCTET STRING,
    wtSeriFtpServerUrl       OCTET STRING
}    

wtSeriFtpServerPort OBJECT-TYPE
    SYNTAX INTEGER (0..65535)
    ACCESS read-write
    STATUS mandatory
    DESCRIPTION
        "Port number which addresses the FTP server (Standard FTP-Port: 21)."
    ::= { wtSeriFtpClientEntry 1 }

wtSeriFtpServerIp OBJECT-TYPE
    SYNTAX IpAddress
    ACCESS read-write
    STATUS mandatory
    DESCRIPTION
        "IP address of the computer on which the FTP server is active."
    ::= { wtSeriFtpClientEntry 2 }

wtSeriFtpAutoFtp OBJECT-TYPE
    SYNTAX INTEGER {
        wtSeriAutoFtpOff(1),
        wtSeriAutoFtpOn(2)
    }
    ACCESS read-write
    STATUS mandatory
    DESCRIPTION
        "Set this switch to 2 to activate the automatic FTP client. This mode is
        recommended when the same command needs to be executed over and over. The 
        FTP commands are stored in the Com-Server. The latter opens a connection 
        to the FTP server when it receives data on the serial port. It sends the 
        login and runs the configured file command. Then the connection is closed
        again. Configure the command in the following parameter
        wtSeriFtpLoginString.
        Set this switch to 1 to activate the FTP client with serial protocol. 
        See section FTP client mode in the corresponding manual for the 
        Com-Server."
    ::= { wtSeriFtpClientEntry 3 }

wtSeriFtpLoginString OBJECT-TYPE
    SYNTAX OCTET STRING
    ACCESS read-write
    STATUS mandatory
    DESCRIPTION
        "Command sequence for the FTP login in 'Automatic FTP-Client' mode.
        FTP client commands:
        TYPE A or I     Activation of ASCII or binary mode
        STOR File       Saves all serially received data to a file
        APPE File       Appends all serially received data to the end of a file
        RETR File       Outputs file to the serial port
        DELE File       Deletes file
        LIST Directory  Lists the directory contents on the serial port
        RESET           Initiates a software reset of the Com-Server. This
                        command may only be used when there is no active
                        connection to the FTP server.
        Command sequence format:
        1. login<lf>
           password<lf>
           TYPE I or TYPE A<lf>
           STOR, RETR, APPE or LIST remote file/dir<lf>
           ProtocolChar<lf>

        3. login<lf>                        2. RESET<lf>                
           password<lf>                        ProtocolChar<lf>
           DELE remote file/dir <lf>
           ProtocolChar<lf>

        The character 'ProtocolChar' is configured in the variable wtSeriFtpProtocolChar.
        Ex.: egon<lf>happy<lf>TYPE A<lf>RETR /etc/hosts<lf><Ctrl C>
        For additional explanations, please see the chapter 'FTP client mode' in the 
        corresponding manual for the Com-Server."
    ::= { wtSeriFtpClientEntry 4 }

wtSeriFtpInactTimeout OBJECT-TYPE
    SYNTAX INTEGER (0..65535)
    ACCESS read-write
    STATUS mandatory
    DESCRIPTION
        "Configure the commands STOR and APPE(nd) with a timeout in seconds for closing 
        the connection. If during this time no serial data are received, the FTP client 
        closes the connection to the FTP server."
    ::= { wtSeriFtpClientEntry 5 }

wtSeriFtpConnectTimeout OBJECT-TYPE
    SYNTAX INTEGER (0..65535)
    ACCESS read-write
    STATUS mandatory
    DESCRIPTION
        "Connection timeout in seconds. This value is only effective in 
        conjunction with an activated Inactivity Timeout. After the Inactivity 
        Timeout has expired, the Com-Server attempts for the duration of the 
        Connection Timeout to transmit any user data not yet sent. If it does not 
        receive a reply from the FTP server within this time, it may be assumed 
        that the server is hung. The data are then rejected and the connection
        reset. To prevent unintended data loss, choose a value which is 
        appropriately large. Value 0 deactivates the timeout." 
    ::= { wtSeriFtpClientEntry 6 }

wtSeriFtpProtocolChar OBJECT-TYPE
    SYNTAX OCTET STRING (SIZE (1))
    ACCESS read-write
    STATUS mandatory
    DESCRIPTION
        "When the Com-Server receives the character configured here on its serial port, 
        the Com-Server port closes the connection to the FTP server. 
        This is also used as a final character for the login string
        (Variable wtSeriFtpLoginString)."
    ::= { wtSeriFtpClientEntry 7 }

wtSeriFtpServerUrl OBJECT-TYPE
    SYNTAX OCTET STRING
    ACCESS read-write
    STATUS mandatory
    DESCRIPTION
        "URL of the computer on which your application (FTP server process) is active. The URL
         can be used instead of an IP address and only in conjunction with a valid DNS server.
         The URL contains a maximum of 64 characters and is terminated with a 0x00. If the
         fist character is 0x00, the URL is empty."
    ::= { wtSeriFtpClientEntry 8 }


-- Serial Multiport Protocol
--
-- This list contains entries for all serial interfaces whose port mode (Variable:
-- ".wtConfiguration(1).wtSeriPortSetup(3).wtSeriPortTable(4).wtSeriPortEntry(1)
--  .wtSeriPortMode(2)" has the value wtSeriMultiportProtokoll(7).

wtSeriMultiPortPrtTable OBJECT-TYPE
    SYNTAX SEQUENCE OF WtSeriMultiPortPrtEntry
    ACCESS not-accessible
    STATUS mandatory
    DESCRIPTION
        "List of all serial ports in multiport protocol mode relevant to their interface
        number"
    ::= { wtSeriPortSetup 9 }

wtSeriMultiPortPrtEntry OBJECT-TYPE
    SYNTAX WtSeriMultiPortPrtEntry
    ACCESS not-accessible
    STATUS mandatory
    DESCRIPTION
        "Multiport-Protocol-Mode parameters"
    INDEX  { wtSeriInterfaceNo }
    ::= { wtSeriMultiPortPrtTable 1 }

WtSeriMultiPortPrtEntry ::= SEQUENCE {
    wtSeriPrtSeriProtocol    INTEGER,
    wtSeriPrtSeriCoding      INTEGER,
    wtSeriPrtProtocolChar    OCTET STRING
}

wtSeriPrtSeriProtocol OBJECT-TYPE
    SYNTAX INTEGER {
        wtSeriPrtSeriProtocolOff(1),
        wtSeriPrtSeriProtocolOn(2)
    }
    ACCESS read-write
    STATUS mandatory
    DESCRIPTION
        "This switch activates/deactivates the Serial Socket Interface. 
        Detailed protocol documentation is available on our Web site 
        (http://www.wut.de) for downloading."
    ::= { wtSeriMultiPortPrtEntry 1 }

wtSeriPrtSeriCoding OBJECT-TYPE
    SYNTAX INTEGER {
        wtSeriPrtSeriCodingOff(1),
        wtSeriPrtSeriCodingOn(2)
    }
    ACCESS read-write
    STATUS mandatory
    DESCRIPTION
        "This switch activated character doubling. It ensures reliable packet 
        frame detection when transmitting binary data, without having to exclude 
        certain characters."
    ::= { wtSeriMultiPortPrtEntry 2 }

wtSeriPrtProtocolChar OBJECT-TYPE
    SYNTAX OCTET STRING (SIZE (1))
    ACCESS read-write
    STATUS mandatory
    DESCRIPTION
        "If character doubling is not used, configure here a packet frame 
        character. This character is not allowed to be used in the data 
        stream."
    ::= { wtSeriMultiPortPrtEntry 3 }


-- Box-to-Box-Master-Mode
--
-- This list contains entries for all serial ports (Variable:
-- ".wtConfiguration(1).wtSeriPortSetup(3).wtSeriPortTable(4).wtSeriPortEntry(1)
--  .wtSeriPortMode(2)" having the value wtSeriBox2BoxMaster(5).

wtSeriB2bMasterTable OBJECT-TYPE
    SYNTAX SEQUENCE OF WtSeriB2bMasterEntry
    ACCESS not-accessible
    STATUS mandatory
    DESCRIPTION
        "List of all serial ports in Box-to-Box Master Mode relevant to their interface 
        number."
    ::= { wtSeriPortSetup 10 }

wtSeriB2bMasterEntry OBJECT-TYPE
    SYNTAX WtSeriB2bMasterEntry
    ACCESS not-accessible
    STATUS mandatory
    DESCRIPTION
        "Box-to-Box-Master-Mode parameters."
    INDEX  { wtSeriInterfaceNo }
    ::= { wtSeriB2bMasterTable 1 }

WtSeriB2bMasterEntry ::= SEQUENCE {
    wtSeriB2bMaster-SlavePort       INTEGER,
    wtSeriB2bMaster-SlaveIp         IpAddress,
    wtSeriB2bMaster-DispString1     OCTET STRING,
    wtSeriB2bMaster-DispString2     OCTET STRING
}

wtSeriB2bMaster-SlavePort OBJECT-TYPE
    SYNTAX INTEGER (1..65535)
    ACCESS read-write
    STATUS mandatory
    DESCRIPTION
        "Port number of the serial Com-Server-Slave port."
    ::= { wtSeriB2bMasterEntry 1 }

wtSeriB2bMaster-SlaveIp OBJECT-TYPE
    SYNTAX IpAddress
    ACCESS read-write
    STATUS mandatory
    DESCRIPTION
        "IP address of the Com-Server in which the slave port is located."
    ::= { wtSeriB2bMasterEntry 2 }

wtSeriB2bMaster-DispString1 OBJECT-TYPE
    SYNTAX OCTET STRING (SIZE (2))
    ACCESS read-write
    STATUS mandatory
    DESCRIPTION
        "This mode allows compact sending of serial data to the network; the 
        serial data stream is not broken up randomly, but rather serial packets 
        can be sent in their original context even over the network as one 
        packet.
        Enter in wtSeriB2bMaster-DispString1 and/or wtSeriB2bMaster-DispString2 two
        characters each that you want the serial data stream searched for. Only if
        one of the two strings is found are the data from the serial port packed 
        into network packets. If you only want to look for one character, set 
        wtSeriB2bMaster-DispString2 to 0. If for example you configure 
        wtSeriB2bMaster-DispString1 to 3100h and wtSeriB2bMaster-DispString2 to 0,
        only character 1 is searched for. Both Dispatch Strings = 0 deactivates the
        mode.
        IMPORTANT: These characters are sent over the network!" 
    ::= { wtSeriB2bMasterEntry 3 }

wtSeriB2bMaster-DispString2 OBJECT-TYPE
    SYNTAX OCTET STRING (SIZE (2))
    ACCESS read-write
    STATUS mandatory
    DESCRIPTION
        "See DESCRIPTION for wtSeriB2bMaster-DispString1."
    ::= { wtSeriB2bMasterEntry 4 }

-- Box-to-Box-Slave-Mode
--
-- This list contains entries for all serial ports whose port mode (Variable:
-- ".wtConfiguration(1).wtSeriPortSetup(3).wtSeriPortTable(4).wtSeriPortEntry(1)
--  .wtSeriPortMode(2)" has the value wtSeriBox2BoxSlave(8).

wtSeriB2bSlaveTable OBJECT-TYPE
    SYNTAX SEQUENCE OF WtSeriB2bSlaveEntry
    ACCESS not-accessible
    STATUS mandatory
    DESCRIPTION
        "List of all serial ports in Box-to-Box-Slave-Mode relevant to their 
        interface number"
    ::= { wtSeriPortSetup 11 }

wtSeriB2bSlaveEntry OBJECT-TYPE
    SYNTAX WtSeriB2bSlaveEntry
    ACCESS not-accessible
    STATUS mandatory
    DESCRIPTION
        "Box-to-Box-Slave-Mode parameters."
    INDEX  { wtSeriInterfaceNo }
    ::= { wtSeriB2bSlaveTable 1 }

WtSeriB2bSlaveEntry ::= SEQUENCE {
    wtSeriB2bSlave-MasterPort       INTEGER,
    wtSeriB2bSlave-MasterIp         IpAddress,
    wtSeriB2bSlave-DispString1     OCTET STRING,
    wtSeriB2bSlave-DispString2     OCTET STRING
}

wtSeriB2bSlave-MasterPort OBJECT-TYPE
    SYNTAX INTEGER (1..65535)
    ACCESS read-only
    STATUS mandatory
    DESCRIPTION
        "Port number of the serial Com-Server Master port."
    ::= { wtSeriB2bSlaveEntry 1 }

wtSeriB2bSlave-MasterIp OBJECT-TYPE
    SYNTAX IpAddress
    ACCESS read-only
    STATUS mandatory
    DESCRIPTION
        "IP address of the Com-Server in which the Master port is located."
    ::= { wtSeriB2bSlaveEntry 2 }

wtSeriB2bSlave-DispString1 OBJECT-TYPE
    SYNTAX OCTET STRING (SIZE (2))
    ACCESS read-write
    STATUS mandatory
    DESCRIPTION
        "This mode allow compact sending of serial data to the network; the 
        serial data stream is not broken up randomly, but rather serial packets 
        can be sent in their original context even over the network as one 
        packet.
        Enter two characters each in wtSeriB2bSlave-DispString1 and/or
        wtSeriB2bSlave-DispString2 to search for in the serial data stream.
        Only when one of the two strings has been found does the serial port pack 
        the data into network packets. To search for only one character, set 
        wtSeriB2bSlave-DispString2 to 0. If for example you configure 
        wtSeriB2bSlave-DispString1 to 3100h and wtSeriB2bSlave-DispString2 to 0,
        only the character 1 is searched for. Both Dispatch Strings = 0 deactivates 
        this mode.
        IMPORTANT: These characters are sent over the network!" 
    ::= { wtSeriB2bSlaveEntry 3 }

wtSeriB2bSlave-DispString2 OBJECT-TYPE
    SYNTAX OCTET STRING (SIZE (2))
    ACCESS read-write
    STATUS mandatory
    DESCRIPTION
        "See DESCRIPTION of wtSeriB2bSlave-DispString1."
    ::= { wtSeriB2bSlaveEntry 4 }

-- IP-Bus-Mode
--
-- This list contains entries for all serial ports whose port mode (Variable:
-- ".wtConfiguration(1).wtSeriPortSetup(3).wtSeriPortTable(4).wtSeriPortEntry(1)
--  .wtSeriPortMode(2)" has the value wtSeriIpBusMaster(10) or wtSeriIpBusSlave(11).

wtSeriIpBusTable OBJECT-TYPE
    SYNTAX SEQUENCE OF WtSeriIpBusEntry
    ACCESS not-accessible
    STATUS mandatory
    DESCRIPTION
        "List of all serial ports in IP-Bus-Mode relevant to their interface number"
    ::= { wtSeriPortSetup 12 }

wtSeriIpBusEntry OBJECT-TYPE
    SYNTAX WtSeriIpBusEntry
    ACCESS not-accessible
    STATUS mandatory
    DESCRIPTION
        "IP-Bus-Mode parameters."
    INDEX  { wtSeriInterfaceNo }
    ::= { wtSeriIpBusTable 1 }

WtSeriIpBusEntry ::= SEQUENCE {
    wtSeriBusSlave-MasterIp IpAddress,
    wtSeriBusMaster-SubnetIp IpAddress
}

wtSeriBusSlave-MasterIp OBJECT-TYPE
    SYNTAX IpAddress
    ACCESS read-write
    STATUS mandatory
    DESCRIPTION
        "Setting on Com-Server ports connected to Slaves: Set here the complete IP address 
        of the Com-Server with the Master port."
    ::= { wtSeriIpBusEntry 1 }

wtSeriBusMaster-SubnetIp OBJECT-TYPE
    SYNTAX IpAddress
    ACCESS read-write
    STATUS mandatory
    DESCRIPTION
        "Setting on a Com-Server port connected to the Master: Enter here the network 
        address of the Subnet in which the Master and Slaves are located. It is sufficient 
        to entry any value not equal to zero (e.g., 1.0.0.0); the Com-Server itself will 
        calculate the Subnet IP address from its own IP number and the Subnet mask 
        (binary AND-operation) and enter it."
    ::= { wtSeriIpBusEntry 2 }


-- SLIP Mode
--
-- This list contains entries for all serial ports whose port mode (Variable:
-- ".wtConfiguration(1).wtSeriPortSetup(3).wtSeriPortTable(4).wtSeriPortEntry(1)
--  .wtSeriPortMode(2)" has the value wtSeriSlipMode(9).

wtSeriSlipTable OBJECT-TYPE
    SYNTAX SEQUENCE OF WtSeriSlipEntry
    ACCESS not-accessible
    STATUS mandatory
    DESCRIPTION
        "List of all ports in SLIP-Mode relevant to their interface number"
    ::= { wtSeriPortSetup 13 }

wtSeriSlipEntry OBJECT-TYPE
    SYNTAX WtSeriSlipEntry
    ACCESS not-accessible
    STATUS mandatory
    DESCRIPTION
        "SLIP-Mode parameters."
    INDEX  { wtSeriInterfaceNo }
    ::= { wtSeriSlipTable 1 }

WtSeriSlipEntry ::= SEQUENCE {
    wtSeriSlipNetAddress IpAddress,
    wtSeriSlipNetRouting INTEGER
}

wtSeriSlipNetAddress OBJECT-TYPE
    SYNTAX IpAddress
    ACCESS read-write
    STATUS mandatory
    DESCRIPTION
        "Enter here the network address of the serially connected Subnet to which you 
        want to route using SLIP."
    ::= { wtSeriSlipEntry 1 }

wtSeriSlipNetRouting OBJECT-TYPE
    SYNTAX INTEGER {
        wtSeriSlipNetRoutingOff(1),
        wtSeriSlipNetRoutingOn(2)
    }
    ACCESS read-write
    STATUS mandatory
    DESCRIPTION
        "If this parameter has a value of 2, the Com-Server operates as a router for 
        the Subnet specified under wtSeriSlipNetAddress. If the parameter has a value 
        of 1, the Com-Server is transparent, i.e. all packets sent to the IP address of 
        the Com-Server are passed on as SLIP packets to the serial port. The destination
        IP address (IP address of the Com-Server) is replaced by the parameter 
        wtSeriSlipNetAddress. This allows assigning of individual IP addresses to the 
        connected SLIP computers (=wtSeriSlipNetAddress), without having to assign an 
        individual Subnet for each connection." 
    ::= { wtSeriSlipEntry 2 }






--
-- Below are parameters and traps which are available only in PC-104 Com-Servers!
--
-- wtDeaPortSetup Group
----------------------------

wtDeaPorts OBJECT-TYPE
    SYNTAX INTEGER (1..4)
    ACCESS read-only
    STATUS mandatory
    DESCRIPTION
        "Number of Com-Server digital I/O ports"
    ::= { wtDeaPortSetup 1 }

-- Digital I/O Interface Table

wtDeaInterfaceTable OBJECT-TYPE
    SYNTAX SEQUENCE OF WtDeaInterfaceEntry
    ACCESS not-accessible
    STATUS mandatory
    DESCRIPTION
        "List of interface numbers of all digital I/O ports."
    ::= { wtDeaPortSetup 2 }

wtDeaInterfaceEntry OBJECT-TYPE
    SYNTAX WtDeaInterfaceEntry
    ACCESS not-accessible
    STATUS mandatory
    DESCRIPTION
        "Interface number"
    INDEX  { wtDeaInterfaceNo }
    ::= { wtDeaInterfaceTable 1 }

WtDeaInterfaceEntry ::= SEQUENCE {
    wtDeaInterfaceNo INTEGER
}

wtDeaInterfaceNo OBJECT-TYPE
    SYNTAX INTEGER (1..4)
    ACCESS read-only
    STATUS mandatory
    DESCRIPTION
        "Interface number of the digital I/O ports."
    ::= { wtDeaInterfaceEntry 1 }



-- Digital I/O Port Table

wtDeaPortTable OBJECT-TYPE
    SYNTAX SEQUENCE OF WtDeaPortEntry
    ACCESS not-accessible
    STATUS mandatory
    DESCRIPTION
        "List of the general port entries relevant to the interface number of the digital
        I/O ports."
    ::= { wtDeaPortSetup 3 }

wtDeaPortEntry OBJECT-TYPE
    SYNTAX WtDeaPortEntry
    ACCESS not-accessible
    STATUS mandatory
    DESCRIPTION
        "Port entries of the digital I/O ports."
    INDEX  { wtDeaInterfaceNo }
    ::= { wtDeaPortTable 1 }

WtDeaPortEntry ::= SEQUENCE {
    wtDeaLocalPort   INTEGER,
    wtDeaPortMode    INTEGER,
    wtDeaDrvWatchdog INTEGER
}           

wtDeaLocalPort OBJECT-TYPE
    SYNTAX INTEGER (49152..65535)
    ACCESS read-write
    STATUS mandatory
    DESCRIPTION
        "Local TCP/UDP port number of the Com-Server port. Port number on which the 
        Com-Server accepts a TCP connection or which it uses as a local port in TCP client 
        mode or UDP mode."
    ::= { wtDeaPortEntry 1}

wtDeaPortMode OBJECT-TYPE
    SYNTAX INTEGER {
        wtDeaServerMode(1),
        wtDeaTcpClient(2),
        wtDeaBox2BoxMaster(3),
        wtDeaUdpMode(4),
        wtDeaSnmpAgent(5),
        wtDeaBox2BoxSlave(6)
    }
    ACCESS read-write
    STATUS mandatory
    DESCRIPTION
        "This parameter specifies the mode for the Com-Server port. Depending on 
        which mode is set, the corresponding list of the relevant parameters is
        available. If for example UDP mode (wtDeaPortMode = 4) is configured,
        only the list wtDeaUdpClientTable is available. In Server Mode
        (wtDeaPortMode = 1) no list of the port mode configurations is 
        available."
    ::= { wtDeaPortEntry 2}

wtDeaDrvWatchdog OBJECT-TYPE
    SYNTAX INTEGER
    ACCESS read-write
    STATUS mandatory
    DESCRIPTION
        "This parameter allows control of all instances which are active between
        the card driver in the Com-Server and the application on the computer, 
        including the computer itself (e.g., TCP/IP stack in the computer, 
        network card, network, ..). If one of these instances drops out, i.e., 
        communication between the application and the card driver is no longer 
        ensured, the card driver switches all outputs off after expiration of the 
        driver watchdog (in 100ms ticks). 
        IMPORTANT: If this parameter is activated, the application must poll the 
        card driver regularly by sending an I/O structure. The value of the 
        variable wtDeaDrvWatchdog should be a multiple of the poll rate. Monitoring 
        is always active. If a TCP connection is closed without deactivating the 
        outputs, this is done after expiration of the driver watchdog."
    ::= { wtDeaPortEntry 3}



-- TCP-Client-Mode
--
-- This list contains entries for all digital I/O ports whose port mode (Variable:
-- ".wtConfiguration(1).wtDeaPortSetup(3).wtDeaPortTable(4).wtDeaPortEntry(1)
--  .wtDeaPortMode(2)" has the value wtDeaTcpClient(2).

wtDeaTcpClientTable OBJECT-TYPE
    SYNTAX SEQUENCE OF WtDeaTcpClientEntry
    ACCESS not-accessible
    STATUS mandatory
    DESCRIPTION
        "List of all digital I/O ports in TCP-Client-Mode relevant to their 
        interface number"
    ::= { wtDeaPortSetup 4 }

wtDeaTcpClientEntry OBJECT-TYPE
    SYNTAX WtDeaTcpClientEntry
    ACCESS not-accessible
    STATUS mandatory
    DESCRIPTION
        "TCP-Client-Mode parameters"
    INDEX  { wtDeaInterfaceNo }
    ::= { wtDeaTcpClientTable 1 }

WtDeaTcpClientEntry ::= SEQUENCE {
    wtDeaTcpServerPort      INTEGER,
    wtDeaTcpServerIp        IpAddress,
    wtDeaTcpInactTimeout    INTEGER,
    wtDeaTcpConnectTimeout  INTEGER,
    wtDeaTcpInputMask       OCTET STRING
}

wtDeaTcpServerPort OBJECT-TYPE
    SYNTAX INTEGER (0..65535)
    ACCESS read-write
    STATUS mandatory
    DESCRIPTION
        "Port number which the application (TCP server process) addresses on the computer."
    ::= { wtDeaTcpClientEntry 1 }

wtDeaTcpServerIp OBJECT-TYPE
    SYNTAX IpAddress
    ACCESS read-write
    STATUS mandatory
    DESCRIPTION
        "IP address of the computer on which the application (TCP server process) is active."
    ::= { wtDeaTcpClientEntry 2 }

wtDeaTcpInactTimeout OBJECT-TYPE
    SYNTAX INTEGER (0..65535)
    ACCESS read-write
    STATUS mandatory
    DESCRIPTION
        "Connection timeout in seconds. If no data are exchanged within the specified time,  
        the Com-Server closes the connection to the TCP server.
        The value 0 deactivates the timer."
    ::= { wtDeaTcpClientEntry 3 }

wtDeaTcpConnectTimeout OBJECT-TYPE
    SYNTAX INTEGER (0..65535)
    ACCESS read-write
    STATUS mandatory
    DESCRIPTION
        "Connection timeout in seconds. This value is only effective in 
        conjunction with an activated inactivity timeout. After the inactivity 
        timeout has expired, the Com-Server attempts to send any remaining unsent 
        user data for the duration of the connection timeout. If it does not 
        receive a reply from the TCP server within this time, it assumes the 
        server is hung. The data are the rejected and the connection reset. To
        prevent unintended data loss, select a sufficiently high value. The value 
        0 deactivates the timeout." 
    ::= { wtDeaTcpClientEntry 4 }

wtDeaTcpInputMask OBJECT-TYPE
    SYNTAX OCTET STRING (SIZE (2))
    ACCESS read-write
    STATUS mandatory
    DESCRIPTION
        "Here the inputs to be polled by the card driver are configured. When a 
        level change occurs on one or more inputs, the TCP connection to the 
        application (TCP server) is opened and the I/O structure 'Write Register' 
        is sent.
        The OCTETS are interpreted bit-by-bit, with each bit corresponding to an 
        input. Bit 0 corresponds to the LSB.
        OCTET 1, Bit 0-3: Digital inputs 8-11
                 Bit 4-7: unused
        OCTET 2, Bit 0-7: Digital inputs 0-7"
    ::= { wtDeaTcpClientEntry 5 }


-- UDP-Mode
--
-- This list contains entries for all digital I/O ports whose port mode (Variable:
-- ".wtConfiguration(1).wtDeaPortSetup(3).wtDeaPortTable(4).wtDeaPortEntry(1)
--  .wtDeaPortMode(2)" has the value wtDeaUdpMode(4).

wtDeaUdpClientTable OBJECT-TYPE
    SYNTAX SEQUENCE OF WtDeaUdpClientEntry
    ACCESS not-accessible
    STATUS mandatory
    DESCRIPTION
        "List of all digital I/O ports in UDP-Mode relevant to their interface number"
    ::= { wtDeaPortSetup 5 }

wtDeaUdpClientEntry OBJECT-TYPE
    SYNTAX WtDeaUdpClientEntry
    ACCESS not-accessible
    STATUS mandatory
    DESCRIPTION
            "UDP-Mode parameters"
    INDEX  { wtDeaInterfaceNo }
    ::= { wtDeaUdpClientTable 1 }

WtDeaUdpClientEntry ::= SEQUENCE {
    wtDeaUdpServerPort      INTEGER,
    wtDeaUdpServerIp        IpAddress,
    wtDeaUdpPacketProtocol  INTEGER,
    wtDeaUdpInputMask       OCTET STRING,
    wtDeaUdpSendInterval    INTEGER
}

wtDeaUdpServerPort OBJECT-TYPE
    SYNTAX INTEGER (0..65535)
    ACCESS read-write
    STATUS mandatory
    DESCRIPTION
        "Port number which the application (UPD server process) on the computer addresses."
    ::= { wtDeaUdpClientEntry 1 }

wtDeaUdpServerIp OBJECT-TYPE
    SYNTAX IpAddress
    ACCESS read-write
    STATUS mandatory
    DESCRIPTION
        "IP address of the computer on which the application (UDP server process) is active."
    ::= { wtDeaUdpClientEntry 2 }

wtDeaUdpPacketProtocol OBJECT-TYPE
    SYNTAX INTEGER {
        wtDeaUdpPacketProtocolOff(1),
        wtDeaUdpPacketProtocolOn(2)
    }
    ACCESS read-write
    STATUS mandatory
    DESCRIPTION
        "This switch activates (2) or deactivates (1) of the control procedure for the 
        packet sequence in UDP mode (see also manual for I/O Com-Server."
    ::= { wtDeaUdpClientEntry 3 }

wtDeaUdpInputMask OBJECT-TYPE
    SYNTAX OCTET STRING (SIZE (2))
    ACCESS read-write
    STATUS mandatory
    DESCRIPTION
        "Here the inputs to be polled by the card driver are configured. When a 
        level change occurs on one or more inputs, the TCP connection to the 
        application (TCP server) is opened and the I/O structure 'Write Register' 
        is sent. 
        The OCTETS are interpreted bit-by-bit, with each bit corresponding to an
        input. Bit 0 corresponds to the LSB.
        OCTET 1, Bit 0-3: Digital inputs 8-11
                 Bit 4-7: unused
        OCTET 2, Bit 0-7: Digital inputs 0-7"
    ::= { wtDeaUdpClientEntry 4 }

wtDeaUdpSendInterval OBJECT-TYPE
    SYNTAX INTEGER (0..65535)
    ACCESS read-write
    STATUS mandatory
    DESCRIPTION
        "Configurable interval with a 100ms base, in which the card driver sends the 
        I/O structure 'Write Register' with the contents of the input register to the 
        configured application (UDP server). The value 0 deactivates this mode."
    ::= { wtDeaUdpClientEntry 5 }



-- SNMP-Agent-Mode
--
-- This list contains entries for all Digital I/O ports whose port mode (Variable:
-- ".wtConfiguration(1).wtDeaPortSetup(3).wtDeaPortTable(4).wtDeaPortEntry(1)
--  .wtDeaPortMode(2)" has the value wtDeaSnmpAgent(5).

wtDeaSnmpAgentTable OBJECT-TYPE
    SYNTAX SEQUENCE OF WtDeaSnmpAgentEntry
    ACCESS not-accessible
    STATUS mandatory
    DESCRIPTION
        "List of all digital I/O ports in Snmp-Agent-Mode relevant to their 
        interface number"
    ::= { wtDeaPortSetup 6 }

wtDeaSnmpAgentEntry OBJECT-TYPE
    SYNTAX WtDeaSnmpAgentEntry
    ACCESS not-accessible
    STATUS mandatory
    DESCRIPTION
            "Snmp-Agent-Mode parameters"
    INDEX  { wtDeaInterfaceNo }
    ::= { wtDeaSnmpAgentTable 1 }

WtDeaSnmpAgentEntry ::= SEQUENCE {
    wtDeaSnmpManagerIp    IpAddress,
    wtDeaSnmpInputMask    OCTET STRING,
    wtDeaSnmpSendInterval INTEGER
}

wtDeaSnmpManagerIp OBJECT-TYPE
    SYNTAX IpAddress
    ACCESS read-write
    STATUS mandatory
    DESCRIPTION
        "IP address of the computer on which the SNMP Manager is located to which the 
        Com-Server should send SNMP traps."
    ::= { wtDeaSnmpAgentEntry 1 }

wtDeaSnmpInputMask OBJECT-TYPE
    SYNTAX OCTET STRING (SIZE (2))
    ACCESS read-write
    STATUS mandatory
    DESCRIPTION
        "Here the inputs to be polled by the card driver are configured. When a 
        level change occurs on one or more inputs, an SNMP trap with the variable 
        dDrvInputRegister (see TRAP-DEFINITIONS) is sent to the configured SNMP 
        Manager.
        The OCTETS are interpreted bit-by-bit, with each bit corresponding to an
        input. Bit 0 corresponds to the LSB.
        OCTET 1, Bit 0-3: Digital inputs 8-11
                 Bit 4-7: unused
        OCTET 2, Bit 0-7: Digital inputs 0-7"
    ::= { wtDeaSnmpAgentEntry 2 }

wtDeaSnmpSendInterval OBJECT-TYPE
    SYNTAX INTEGER (0..65535)
    ACCESS read-write
    STATUS mandatory
    DESCRIPTION
        "Configurable interval with a 100ms base, in which the card driver reads the 
        input register and sends an SNMP trap with the variable dDrvInputRegister 
        (see TRAP-DEFINITIONS) to the configured SNMP Manager. A value of 0 deactivates 
        this mode."
    ::= { wtDeaSnmpAgentEntry 3 }


-- Box-to-Box-Master-Mode
--
-- This list contains entries for all Digital I/O ports whose port mode (Variable:
-- ".wtConfiguration(1).wtDeaPortSetup(3).wtDeaPortTable(4).wtDeaPortEntry(1)
--  .wtDeaPortMode(2)" has the value wtDeaBox2BoxMaster(3).

wtDeaB2bMasterTable OBJECT-TYPE
    SYNTAX SEQUENCE OF WtDeaB2bMasterEntry
    ACCESS not-accessible
    STATUS mandatory
    DESCRIPTION
        "List of all digital I/O ports in Box-to-Box-Master-Mode relevant to their
        interface number"
    ::= { wtDeaPortSetup 7 }

wtDeaB2bMasterEntry OBJECT-TYPE
    SYNTAX WtDeaB2bMasterEntry
    ACCESS not-accessible
    STATUS mandatory
    DESCRIPTION
        "Box-to-Box-Master-Mode parameters"
    INDEX  { wtDeaInterfaceNo }
    ::= { wtDeaB2bMasterTable 1 }

WtDeaB2bMasterEntry ::= SEQUENCE {
    wtDeaB2bMaster-SlavePort       INTEGER,
    wtDeaB2bMaster-SlaveIp         IpAddress,
    wtDeaB2bMaster-InputMask       OCTET STRING,
    wtDeaB2bMaster-SendInterval    INTEGER
}

wtDeaB2bMaster-SlavePort OBJECT-TYPE
    SYNTAX INTEGER (0..65535)
    ACCESS read-write
    STATUS mandatory
    DESCRIPTION
        "Port number of the digital I/O Com-Server-Slave port."
    ::= { wtDeaB2bMasterEntry 1 }

wtDeaB2bMaster-SlaveIp OBJECT-TYPE
    SYNTAX IpAddress
    ACCESS read-write
    STATUS mandatory
    DESCRIPTION
        "IP address of the I/O Com-Server in which the Slave port is located."
    ::= { wtDeaB2bMasterEntry 2 }

wtDeaB2bMaster-InputMask OBJECT-TYPE
    SYNTAX OCTET STRING (SIZE (2))
    ACCESS read-write
    STATUS mandatory
    DESCRIPTION
        "Here the inputs to be polled by the card drive are configured. When a 
        level change occurs on one or more inputs, the entire input register is 
        sent over the network and mapped in the output register of the other Com- 
        Server I/O port.
        The OCTETS are interpreted bit-by-bit, with each bit corresponding to an
        input. Bit 0 corresponds to the LSB.
        OCTET 1, Bit 0-3: Digital inputs 8-11
                 Bit 4-7: unused
        OCTET 2, Bit 0-7: Digital inputs 0-7"
    ::= { wtDeaB2bMasterEntry 3 }

wtDeaB2bMaster-SendInterval OBJECT-TYPE
    SYNTAX INTEGER (0..65535)
    ACCESS read-write
    STATUS mandatory
    DESCRIPTION
        "Configurable interval with a 100ms base, in which the card driver maps the 
        input register to the output register of the other I/O port. 
        A value of 0 deactivates this mode."
    ::= { wtDeaB2bMasterEntry 4 }


-- Box-to-Box-Slave-Mode
--
-- This list contains entries for all digital I/O ports whose port mode (Variable:
-- ".wtConfiguration(1).wtDeaPortSetup(3).wtDeaPortTable(4).wtDeaPortEntry(1)
--  .wtDeaPortMode(2)" has the value wtDeaBox2BoxSlave(6).

wtDeaB2bSlaveTable OBJECT-TYPE
    SYNTAX SEQUENCE OF WtDeaB2bSlaveEntry
    ACCESS not-accessible
    STATUS mandatory
    DESCRIPTION
        "List of all digital I/O ports in Box-to-Box-Slave-Mode relevant to their
        interface number"
    ::= { wtDeaPortSetup 8 }

wtDeaB2bSlaveEntry OBJECT-TYPE
    SYNTAX WtDeaB2bSlaveEntry
    ACCESS not-accessible
    STATUS mandatory
    DESCRIPTION
        "Box-to-Box-Slave-Mode parameters"
    INDEX  { wtDeaInterfaceNo }
    ::= { wtDeaB2bSlaveTable 1 }

WtDeaB2bSlaveEntry ::= SEQUENCE {
    wtDeaB2bSlave-MasterPort       INTEGER,
    wtDeaB2bSlave-MasterIp         IpAddress,
    wtDeaB2bSlave-InputMask       OCTET STRING,
    wtDeaB2bSlave-SendInterval    INTEGER
}

wtDeaB2bSlave-MasterPort OBJECT-TYPE
    SYNTAX INTEGER (0..65535)
    ACCESS read-only
    STATUS mandatory
    DESCRIPTION
        "Port number of the digital I/O Com-Server-Master port."
    ::= { wtDeaB2bSlaveEntry 1 }

wtDeaB2bSlave-MasterIp OBJECT-TYPE
    SYNTAX IpAddress
    ACCESS read-only
    STATUS mandatory
    DESCRIPTION
        "IP address of the I/O Com-Server in which the Master port is located."
    ::= { wtDeaB2bSlaveEntry 2 }

wtDeaB2bSlave-InputMask OBJECT-TYPE
    SYNTAX OCTET STRING (SIZE (2))
    ACCESS read-write
    STATUS mandatory
    DESCRIPTION
        "Here the inputs to be polled by the card driver are configured. When a 
        level change occurs on one or more inputs, the entire input register is 
        sent over the network and mapped in the output register of the other Com- 
        Server I/O port.
        The OCTETS are interpreted bit-by-bit, with each bit corresponding to an
        input. Bit 0 corresponds to the LSB.
        OCTET 1, Bit 0-3: Digital inputs 8-11
                 Bit 4-7: unused
        OCTET 2, Bit 0-7: Digital inputs 0-7"
    ::= { wtDeaB2bSlaveEntry 3 }

wtDeaB2bSlave-SendInterval OBJECT-TYPE
    SYNTAX INTEGER (0..65535)
    ACCESS read-write
    STATUS mandatory
    DESCRIPTION
        "Configurable interval with a 100ms base, in which the card driver maps the 
        input register to the output register of the other I/O port. 
        The value 0 deactivates this mode."
    ::= { wtDeaB2bSlaveEntry 4 }



--
-- Digital I/O-Driver Group
--
-- The following variables are only available if the corresponding I/O port 
-- of the Com-Server is configured forSNMP AGent mode (wtDeaPortMode = 5)
-- 
-- Digital I/O Port Table
--

wtDeaDrvTable OBJECT-TYPE
    SYNTAX SEQUENCE OF WtDeaDrvEntry
    ACCESS not-accessible
    STATUS mandatory
    DESCRIPTION
        "List of all functions for managing the digital I/O port relevant to their 
        interface number."
    ::= { wtDeaDriver 1 }

wtDeaDrvEntry OBJECT-TYPE
    SYNTAX WtDeaDrvEntry
    ACCESS not-accessible
    STATUS mandatory
    DESCRIPTION
        "Functions for managing a digital I/O port."
    INDEX  { wtDeaDrvInterfaceNo }
    ::= { wtDeaDrvTable 1 }

WtDeaDrvEntry ::= SEQUENCE {
    wtDeaDrvInterfaceNo   INTEGER,
    wtDeaDrvInputRegister   OCTET STRING,
    wtDeaDrvOutputRegister  OCTET STRING,
    wtDeaDrvSetBit          OCTET STRING,
    wtDeaDrvTrapInputMask   OCTET STRING,
    wtDeaDrvTrapInterval    INTEGER
}           

wtDeaDrvInterfaceNo OBJECT-TYPE
    SYNTAX INTEGER (1..4)
    ACCESS read-only
    STATUS mandatory
    DESCRIPTION
        "Interface number of the digital I/O port."
    ::= { wtDeaDrvEntry 1 }

wtDeaDrvInputRegister OBJECT-TYPE
    SYNTAX OCTET STRING (SIZE (2))
    ACCESS read-only
    STATUS mandatory
    DESCRIPTION
        "This variable is used to read the outputs of the digital I/O port.
        The OCTETS are interpreted bit-by-bit, with each bit corresponding to an output.
        Bit 0 corresponds to the LSB.
        OCTET 1, Bit 0-3: Digital outputs 8-11
                 Bit 4-7: unused
        OCTET 2, Bit 0-7: Digital outputs 0-7"
    ::= { wtDeaDrvEntry 2 }

wtDeaDrvOutputRegister OBJECT-TYPE
    SYNTAX OCTET STRING (SIZE (2))
    ACCESS read-write
    STATUS mandatory
    DESCRIPTION
        "This variable is used to read and write the outputs of the digital I/O port. 
        The OCTETS are interpreted bit-by-bit, with each bit corresponding to an output. 
        Bit 0 corresponds to the LSB.
        OCTET 1, Bit 0-3: Digital outputs 8-11
                 Bit 4-7: unused
        OCTET 2, Bit 0-7: Digital outputs 0-7"
    ::= { wtDeaDrvEntry 3 }

wtDeaDrvSetBit OBJECT-TYPE
    SYNTAX OCTET STRING (SIZE (4))
    ACCESS read-write				-- write-only
    STATUS mandatory
    DESCRIPTION
        "This variable allows setting of individual digital outputs. The OCTETS are 
        interpreted bit-by-bit, with each bit corresponding to an output. Bit 0 corresponds 
        to the LSB.
        The first two OCTETS contain the mask which determines which of the outputs are to 
        be set (corresponding bit = 1) and which outputs are to remain unchanged 
        (corresponding bit = 0):
        OCTET 1, Bit 0-3: Mask for digital outputs 8-11
                 Bit 4-7: unused
        OCTET 2, Bit 0-7: Mask for digital outputs 0-7
        OCTETS 3 and 4 contain the level (1=HIGH, 0=LOW) which the outputs to be changed 
        should assume:
        OCTET 3, Bit 0-3: Level of digital outputs 8-11
                 Bit 4-7: unused
        OCTET 4, Bit 0-7: Level of digital outputs 0-7"
    ::= { wtDeaDrvEntry 4 }

wtDeaDrvTrapInputMask OBJECT-TYPE
    SYNTAX OCTET STRING (SIZE (2))
    ACCESS read-write
    STATUS mandatory
    DESCRIPTION
        "Here the inputs to be polled by the card driver are configured. When a 
        level change occurs on one or more inputs, an SNMP trap is sent to the 
        configured SNMP 
        Manager with the variable wtDeaDrvInputRegister (see TRAP-DEFINITIONS).
        The OCTETS are interpreted bit-by-bit, with each bit corresponding to an
        input. Bit 0 corresponds to the LSB.
        OCTET 1, Bit 4-7: unused
                 Bit 0-3: Digital inputs 8-11
        OCTET 2, Bit 0-7: Digital inputs 0-7
        This setting is no longer valid after a Com-Server restart. If you want the 
        setting to be permanent, configure the variable wtDeaSnmpInputMask in the list
        wtDeaSnmpAgentTable."
    ::= { wtDeaDrvEntry 5 }

wtDeaDrvTrapInterval OBJECT-TYPE
    SYNTAX INTEGER (0..65535)
    ACCESS read-write
    STATUS mandatory
    DESCRIPTION
        "Configurable variable with a 100ms basis, in which the card driver reads the 
        input register and sends an SNMP trap to the configured SNMP Manager with the
        variable wtDeaSnmpSendInterval.
        This setting is no longer valid after a Com-Server restart If you want the 
        setting to be permanent, configure the variable wtDeaSnmpSendInterval in the list 
        wtDeaSnmpAgentTable."
    ::= { wtDeaDrvEntry 6 }



-- TRAP DEFINITIONS

-- This SNMP trap is sent when the variable 
-- .wtDeaDriver.wtDeaDrvTable.wtDeaDrvEntry.wtDeaDrvTrapInputMask or variable
-- .wtConfiguration.wtDeaPortSetup.wtDeaSnmpAgentTable.wtDeaSnmpAgentEntry
-- .wtDeaSnmpInputMask has a contents not equal to 0.

deaInputChangedAlert TRAP-TYPE
    ENTERPRISE  wtDeaDrvEntry
    VARIABLES   { wtDeaDrvInputRegister }
    DESCRIPTION
        "This SNMP trap is generated when the level of an input on the digital I/O port
        has changed."
    ::= 1

-- This SNMP trap is sent when the variable 
-- .wtDeaDriver.wtDeaDrvTable.wtDeaDrvEntry.wtDeaDrvTrapInterval or variable
-- .wtConfiguration.wtDeaPortSetup.wtDeaSnmpAgentTable.wtDeaSnmpAgentEntry
-- .wtDeaSnmpSendInterval has a contents not equal to zero.

deaIntervalExpiredAlert TRAP-TYPE
    ENTERPRISE  wtDeaDrvEntry
    VARIABLES   { wtDeaDrvInputRegister }
    DESCRIPTION
        "This SNMP trap is generated in the interval configured in the variable 
        wtDeaDrvTrapInterval or variable wtDeaSnmpSendInterval."
    ::= 2


END
