ELTEX-ENDOFMIB-MIB DEFINITIONS ::= BEGIN

-- Title:                ELTEX MES-Series Wwitches
--                       Private TRAPS MIB
-- Version:              1.0
-- Date:                 1-Jan-2012

IMPORTS
    elt                                                     FROM ELTEX-MIB
    OBJECT-TYPE, MODULE-IDENTITY                            FROM SNMPv2-SMI;

eltEndOfMibGroup MODULE-IDENTITY
                LAST-UPDATED "201207130000Z"
                ORGANIZATION "Eltex Enterprise Co, Ltd."
                CONTACT-INFO
                      "www.eltex.nsk.ru"
                DESCRIPTION
                      "This private MIB module defines End of Eltex private MIBs."
                REVISION "201207130000Z"
                DESCRIPTION
                      "Initial revision."
        ::= { elt 1000 }

eltEndOfMib OBJECT-TYPE
      SYNTAX  INTEGER
      MAX-ACCESS   read-only
      STATUS   current
      DESCRIPTION
        " This variable indicates this is the end of Eltex MIB."
      ::= {  eltEndOfMibGroup 1  }

END
