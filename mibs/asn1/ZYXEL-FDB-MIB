-- ZyXEL Communications Corporation
-- Private Enterprise MIB definition 
  
-- This file describes the ZyXEL Communications Corporation Enterprise MIB.
-- It contains ZyXEL products OIDs, and common managed objects.

-- $Log: ZYXEL-FDB-MIB.mib $ 
-- Revision 1.5  2013/12/06 07:04:49  ccho 
-- remove uncessary imports 
-- Revision 1.4  2013/06/26 07:14:01  Mandy 
-- Support notified trap for error recovered 
-- Revision 1.3  2012/09/19 07:33:10  Kevin 
-- if it's leaf node, revise the vender name from zyxel to zy 
-- Revision 1.2  2012/07/05 06:22:43  Kevin 
-- 1. upgrade from SNMP to SNMPv2  
-- 2. clean warning 
-- Revision 1.1  2012/05/30 07:48:49  Kevin 
-- Initial revision 

ZYXEL-FDB-MIB DEFINITIONS ::= BEGIN
    
    IMPORTS
	OBJECT-TYPE
		FROM SNMPv2-SMI			-- RFC2578	
		
	MODULE-IDENTITY
		FROM SNMPv2-SMI
	
	EnabledStatus
		FROM  P-BRIDGE-MIB

	NOTIFICATION-TYPE
		FROM SNMPv2-SMI

	esMgmt			
		FROM ZYXEL-ES-SMI;

	zyxelFdb MODULE-IDENTITY
		LAST-UPDATED	"201207010000Z"    
		ORGANIZATION "Enterprise Solution ZyXEL"     
		CONTACT-INFO
			""	   
		DESCRIPTION
			"The subtree for forwarding and/or filtering database"
		::= { esMgmt 48 }
		
	zyxelMacStatus	     		OBJECT IDENTIFIER ::= { zyxelFdb 1 }
	zyxelMacStatusNotifications	OBJECT IDENTIFIER ::= { zyxelFdb 2 }

	                     
        
        zyMacFlush OBJECT-TYPE
        SYNTAX  EnabledStatus
        MAX-ACCESS  read-write
        STATUS  current
        DESCRIPTION
			"Active to clear the MAC address table."
        ::= { zyxelMacStatus 1 }

        zyMacFlushPort OBJECT-TYPE
        SYNTAX  INTEGER
        MAX-ACCESS  read-write
        STATUS  current
        DESCRIPTION
			"Clear all learned MAC address on the specified port."
        ::= { zyxelMacStatus 2 }

        zyMacFlushVlan OBJECT-TYPE
        SYNTAX  INTEGER
        MAX-ACCESS  read-write
        STATUS  current
        DESCRIPTION
			"Clear all learned MAC address on the specified VLAN."
        ::= { zyxelMacStatus 3 }  
        
	   zyMacForwardingTableFull NOTIFICATION-TYPE
	   STATUS  current
       DESCRIPTION
               "MAC address switching table has become full."
       ::= { zyxelMacStatusNotifications 1 }        
        
	   zyMacForwardingTableFullRecovered NOTIFICATION-TYPE
	   STATUS  current
       DESCRIPTION
               "MAC address switching table has recovered from full."
       ::= { zyxelMacStatusNotifications 2 }        
                                             
END
