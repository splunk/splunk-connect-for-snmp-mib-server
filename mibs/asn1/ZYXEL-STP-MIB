-- ZyXEL Communications Corporation
-- Private Enterprise MIB definition 
  
-- This file describes the ZyXEL Communications Corporation Enterprise MIB.
-- It contains ZyXEL products OIDs, and common managed objects.

-- $Log: ZYXEL-STP-MIB.mib $ 
-- Revision 1.5  2013/12/06 07:08:52  ccho 
-- remove uncessary imports 
-- Revision 1.4  2012/09/19 07:46:59  Kevin 
-- if it's leaf node, revise the vender name from zyxel to zy 
-- Revision 1.3  2012/08/22 09:49:30  Kevin 
-- clean warning for SNMPc 
-- Revision 1.2  2012/07/05 06:24:42  Kevin 
-- 1. upgrade from SNMP to SNMPv2  
-- 2. clean warning 
-- Revision 1.1  2012/05/30 07:50:47  Kevin 
-- Initial revision 

ZYXEL-STP-MIB DEFINITIONS ::= BEGIN

    IMPORTS
	OBJECT-TYPE
		FROM SNMPv2-SMI			-- RFC2578	
		
	MODULE-IDENTITY
		FROM SNMPv2-SMI
	
	EnabledStatus
		FROM  P-BRIDGE-MIB

	esMgmt			
		FROM ZYXEL-ES-SMI;

	zyxelStp MODULE-IDENTITY
		LAST-UPDATED	"201207010000Z"    
		ORGANIZATION "Enterprise Solution ZyXEL"     
		CONTACT-INFO
			""	   
		DESCRIPTION
			"The subtree for Spanning Tree Protocol (STP)"
		::= { esMgmt 79 }

	zyxelStpSetup     			OBJECT IDENTIFIER ::= { zyxelStp 1 }
  
-- *******************************************************************
-- *
-- * zyxelStpSetup
-- *
-- *******************************************************************

-- zyxelStpMode
		zyStpMode OBJECT-TYPE
        SYNTAX  INTEGER{
			rstp(1),
			mrstp(2),
			mstp (3)
		}
        MAX-ACCESS  read-write
        STATUS  current
        DESCRIPTION
                    "Activate one of the spanning tree protocol modes on the Switch. "
        ::= { zyxelStpSetup 1 }
		
-- zyxelStpRstpState
		zyStpRstpState	OBJECT-TYPE
		SYNTAX			EnabledStatus
        MAX-ACCESS  		read-write
        STATUS  		current
        DESCRIPTION
                    "Enable/Disable rapid spanning tree protocol. 
					You must also activate rapid spanning tree protocol mode on the switch."
        ::= { zyxelStpSetup 2}	

END
