Dell-STACK-MIB DEFINITIONS ::= BEGIN

-- Title:               Dell LOCALIZATION ROS
--                      This Private MIB supports the unit id configuration for stack of ROS products
-- Version:             7.40
-- Date:                21 Nov 2005
--
-- 01-Nov-2005 Add rlStackUnitMacAddressAfterReset
-- 21-Nov-2005 Change range of rlStackActiveUnitIdAfterReset

IMPORTS
    MacAddress      FROM BRIDGE-MIB
    rnd             FROM Dell-MIB OBJECT-TYPE,
    MODULE-IDENTITY FROM SNMPv2-SMI
    TruthValue, TEXTUAL-CONVENTION FROM SNMPv2-TC;


rlStack MODULE-IDENTITY
         LAST-UPDATED "200504140000Z"
         ORGANIZATION "Dell"
         CONTACT-INFO
                "www.dell.com"
         DESCRIPTION
                "The private MIB module definition for stack."
         REVISION "200504140000Z"
         DESCRIPTION
                "Initial revision."
        ::= { rnd 107 }

rlStackActiveUnitIdTable OBJECT-TYPE
    SYNTAX SEQUENCE OF RlStackActiveUnitIdEntry
    MAX-ACCESS not-accessible
    STATUS     current
    DESCRIPTION
        " The table listing the active unit id of the requested unit."
    ::= {rlStack 1 }

rlStackActiveUnitIdEntry  OBJECT-TYPE
    SYNTAX      RlStackActiveUnitIdEntry
    MAX-ACCESS  not-accessible
    STATUS      current
    DESCRIPTION
        " An entry in the rlStackActiveUnitIdTable."
    INDEX {rlStackCurrentUnitId }
    ::= {rlStackActiveUnitIdTable  1 }

RlStackActiveUnitIdEntry ::= SEQUENCE {
    rlStackCurrentUnitId             INTEGER,
    rlStackActiveUnitIdAfterReset    INTEGER
}

rlStackCurrentUnitId OBJECT-TYPE
    SYNTAX      INTEGER
    MAX-ACCESS  not-accessible
    STATUS      current
    DESCRIPTION
        "The unit number device, which is the active unit id"
    ::= {rlStackActiveUnitIdEntry 1 }


rlStackActiveUnitIdAfterReset OBJECT-TYPE
    SYNTAX      INTEGER (0..255)
    MAX-ACCESS  read-write
    STATUS      current
    DESCRIPTION
        "Indicates the unit id that will be after reset."
    ::= {rlStackActiveUnitIdEntry 2 }

rlStackUnitModeAfterReset OBJECT-TYPE
    SYNTAX  INTEGER {
                    standalone(1),
                    stack(2)
                    }
    MAX-ACCESS  read-write
    STATUS      current
    DESCRIPTION
        "set unit type that will be after reset, standalone or stack."
    ::= {rlStack 2 }

rlStackUnitMode OBJECT-TYPE
    SYNTAX  INTEGER {
                    standalone(1),
                    stack(2)
                    }
    MAX-ACCESS  read-only
    STATUS      current
    DESCRIPTION
        "show unit type standalone or stack."
    ::= {rlStack 3 }

rlStackUnitMacAddressAfterReset OBJECT-TYPE
    SYNTAX  MacAddress
    MAX-ACCESS  read-write
    STATUS  current
    DESCRIPTION
            "The MAC address used by this bridge after rest."
    REFERENCE
            "IEEE 802.1D-1990: Sections 6.4.1.1.3 and 3.12.5"
    ::= { rlStack 4 }


rlStackTopology OBJECT-TYPE
    SYNTAX  INTEGER {
                    topology-chain(1),
                    topology-ring(2),
                    topology-star(3)
                    }
    MAX-ACCESS  read-only
    STATUS      current
    DESCRIPTION
        "show stack topology type"
    ::= {rlStack 6 }

END
