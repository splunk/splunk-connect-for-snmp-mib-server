ZXR10-T128-MIB DEFINITIONS ::= BEGIN
    -- Created by Tao wen-qiang 2003-7-21 17:32

    IMPORTS
       MODULE-IDENTITY, OBJECT-TYPE, Counter32, Gauge32,
       Integer32, TimeTicks, Counter64,
       NOTIFICATION-TYPE,
       enterprises                      FROM SNMPv2-SMI
                  mgmt, NetworkAddress, IpAddress, Counter, Gauge
                         FROM RFC1155-SMI
      --         Counter, TimeTicks     FROM RFC1155-SMI
      -- IpAddress,DisplayString, mib-2   FROM RFC1213-MIB
      --            OBJECT-TYPE            FROM RFC-1212
                  TRAP-TYPE              FROM RFC-1215
      DisplayString,AvailStatus,OperStatus,PortType,
      MasterStatus,UnitRunStatus,PidUsedStatus,BoardType,NpcType,
      BoolStatus                       FROM ZXR10-MIB
      zxr10,zxr10rack,zxr10RackNo,zxr10PosInRack,PortWorkingType,ShelfAttrib          FROM ZXR10-MIB;






     AlarmType ::= INTEGER
                  {
                    hardware-environment(1),
                    hardware-board(2),
                    hardware-port(3),
                    softprotocol-ros(65),
                    softprotocol-database(66),
                    softprotocol-oam(67),
                    softprotocol-security(68),
                    softprotocol-ospf(69),
                    softprotocol-rip(70),
                    softprotocol-bgp(71),
                    softprotocol-drp(72),
                    softprotocol-tcp-udp(73),
                    softprotocol-ip(74),
                    softprotocol-igmp(75),
                    softprotocol-telnet(76),
                    softprotocol-udp(77),
                    softprotocol-arp(78),
                    softprotocol-isis(79),
                    softprotocol-icmp(80),
                    softprotocol-snmp(81),
                    softprotocol-rmon(82),
                    statistics-microcode(129),
                    statistics-ip(130),
                    statistics-tcp(131),
                    statistics-udp(132),
                    statistics-icmp(133),
                    statistics-bgp(134)
                  }
     --added by chenwei 2002-6-13 15:01
     --need update when new type alarm added





    -- shelf mib object
    zxr10shelfTable OBJECT-TYPE
              SYNTAX  SEQUENCE OF Zxr10ShelfEntry
              MAX-ACCESS  not-accessible
              STATUS  current
              DESCRIPTION
                      "the description of zxr10 shelf infomation
                       it is a list of shelf entries."
               ::= { zxr10rack 2 }

    zxr10shelfEntry  OBJECT-TYPE
              SYNTAX  Zxr10ShelfEntry
              MAX-ACCESS  not-accessible
              STATUS  current
              DESCRIPTION
                      "A shelf entry containing objects that
                       descript the shelf infomation,such as:
                       zxr10ShelfRackNo,zxr10ShelfNo ,
                       zxr10ShelfAttrib,zxr10ShelfAvailStatus."
              INDEX  { zxr10RackNo,
                       zxr10ShelfNo }
              ::= { zxr10shelfTable 1 }

    Zxr10ShelfEntry ::=
              SEQUENCE {
                zxr10ShelfNo
                    INTEGER,
                zxr10ShelfAttrib
                    ShelfAttrib,
                zxr10ShelfAvailStatus
                    AvailStatus
              }

   zxr10ShelfNo  OBJECT-TYPE
              SYNTAX  INTEGER
              MAX-ACCESS  read-only
              STATUS  current
              DESCRIPTION
                      "the no. of the special shelf."
              ::= { zxr10shelfEntry 1 }


   zxr10ShelfAttrib  OBJECT-TYPE
              SYNTAX  ShelfAttrib
              MAX-ACCESS  read-only
              STATUS  current
              DESCRIPTION
                      "the attribute. of the special rack.
                       eg ,the current shelf is a working shelf,
                       we use 1,else if the shelf  is a fan shelf
                       we use 2 ,etc."
              ::= { zxr10shelfEntry 2 }

   zxr10ShelfAvailStatus  OBJECT-TYPE
              SYNTAX  AvailStatus
              MAX-ACCESS  read-only
              STATUS  current
              DESCRIPTION
                      "the status. of the special shelf.
                       eg ,the current shelf is in use,
                       we use 1,else if the shelfis unuse,
                       we use 0 ."
              ::= { zxr10shelfEntry 3 }

    -- mib object in zxr10slot group



    -- mib object in ZXR10 CARD-PORT  group

    zxr10portTable OBJECT-TYPE
              SYNTAX  SEQUENCE OF Zxr10PortEntry
              MAX-ACCESS  not-accessible
              STATUS  current
              DESCRIPTION
                      "the description of port infomation
                       in the zxr10 card .
                       it is a list of port entries."
               ::= { zxr10rack 4 }

    zxr10portEntry  OBJECT-TYPE
              SYNTAX  Zxr10PortEntry
              MAX-ACCESS  not-accessible
              STATUS  current
              DESCRIPTION
                      "A port entry containing objects that
                       descript the port infomation,such as:
                       zxr10PortNo
                       zxr10PortType
                       zxr10PortWorkingType
                       zxr10PortMTU
                       zxr10PortSpeed
                       zxr10PortAvailStatus
                       zxr10PortOperStatus."
              INDEX  { zxr10RackNo,
                       zxr10ShelfNo,
                       zxr10PosInRack,
                       zxr10PortNo }
              ::= { zxr10portTable 1 }

    Zxr10PortEntry ::=
              SEQUENCE {
                zxr10PortIfIndex
                    INTEGER,
                zxr10PortNo
                    INTEGER,
                zxr10PortType
                    PortType,
                zxr10PortWorkingType
                    PortWorkingType,
                zxr10PortMTU
                    INTEGER,
                zxr10PortSpeed
                    DisplayString,
                zxr10PortAvailStatus
                    AvailStatus,
                zxr10PortOperStatus
                    OperStatus }

  zxr10PortIfIndex  OBJECT-TYPE
              SYNTAX  INTEGER
              MAX-ACCESS  read-only
              STATUS  current
              DESCRIPTION
                      "the IfIndex of the port on the card."
              ::= { zxr10portEntry 1 }
  
   
   zxr10PortNo  OBJECT-TYPE
              SYNTAX  INTEGER
              MAX-ACCESS  read-only
              STATUS  current
              DESCRIPTION
                      "the no. of the port on the card,
                       which contains several ports ."
              ::= { zxr10portEntry 2 }

   zxr10PortType  OBJECT-TYPE
              SYNTAX  PortType
              MAX-ACCESS  read-only
              STATUS  current
              DESCRIPTION
                      "the type of the port.such as:
                       fei  : Fast Ethernet Interface
                       gei  : Gigabit Ethernet Interface card
                       oc3  : Optic Cable 3 interface card
                       oc12 : Optic Cable 12 interface card
                       oc48 : Optic Cable 48 interface card
                       atm155 : atm155 interface card ."
              ::= { zxr10portEntry 3 }


   zxr10PortWorkingType  OBJECT-TYPE
              SYNTAX  PortWorkingType
              MAX-ACCESS  read-only
              STATUS  current
              DESCRIPTION
                      "
                       auto-config(0) indicate the port working type is auto-config,
                       full-duplex(1) indicate the port working type is full duplex,
                       half-duplex(2) indicate the port working type is half duplex."
              ::= { zxr10portEntry 4 }

   zxr10PortMTU OBJECT-TYPE
              SYNTAX  INTEGER
              MAX-ACCESS  read-only
              STATUS  current
              DESCRIPTION
                      "the mtu of this port ."
              ::= { zxr10portEntry 5 }

   zxr10PortSpeed OBJECT-TYPE
              SYNTAX  DisplayString(SIZE(0..16))
              MAX-ACCESS  read-only
              STATUS  current
              DESCRIPTION
                      "the transmit speed of this port, unit is Mbps."
              ::= { zxr10portEntry 6 }

   zxr10PortAvailStatus  OBJECT-TYPE
              SYNTAX  AvailStatus
              MAX-ACCESS  read-only
              STATUS  current
              DESCRIPTION
                      "the status. of the special port.
                       eg ,the current port is running,
                       we use 1,else if the card is down,
                       we use 0 .
                       1 indicate physical level initialize ok
                       0 indicate physical level initialize not ok "
              ::= { zxr10portEntry 7 }

   zxr10PortOperStatus  OBJECT-TYPE
              SYNTAX  OperStatus
              MAX-ACCESS  read-only
              STATUS  current
              DESCRIPTION
                      "the operstatus. of the special card.
                       eg ,the current card  can work, we use 1,
                       else if the card can't,we use 0 .
                       for upc board:
                       1 indicate mpu and rpu both run normally,
                       0 indicate error,
                       for sfc npc board:
                       1 indicate upc communicate with them(sfc,upc) normally,
                       0 indicate error."

              ::= { zxr10portEntry 8}



 END
