-- ZyXEL Communications Corporation
-- Private Enterprise MIB definition 
  
-- This file describes the ZyXEL Communications Corporation Enterprise MIB.
-- It contains ZyXEL products OIDs, and common managed objects.

-- $Log: ZYXEL-L2PT-MIB.mib $ 
-- Revision 1.5  2013/12/06 07:06:28  ccho 
-- remove uncessary imports 
-- Revision 1.4  2013/11/06 05:41:48  ccho 
-- fix mib style 
-- Revision 1.3  2012/09/19 07:39:20  Kevin 
-- if it's leaf node, revise the vender name from zyxel to zy 
-- Revision 1.2  2012/07/05 06:23:15  Kevin 
-- 1. upgrade from SNMP to SNMPv2  
-- 2. clean warning 
-- Revision 1.1  2012/05/30 07:49:42  Kevin 
-- Initial revision 

ZYXEL-L2PT-MIB DEFINITIONS ::= BEGIN

    IMPORTS
	OBJECT-TYPE
		FROM SNMPv2-SMI			-- RFC2578	
		
	MODULE-IDENTITY
		FROM SNMPv2-SMI
	
	RowStatus,  MacAddress
		FROM SNMPv2-TC			-- RFC2579

	EnabledStatus
		FROM  P-BRIDGE-MIB

	dot1dBasePort
       	FROM BRIDGE-MIB

	esMgmt			
		FROM ZYXEL-ES-SMI;

	zyxelL2pt MODULE-IDENTITY
		LAST-UPDATED	"201207010000Z"    
		ORGANIZATION "Enterprise Solution ZyXEL"     
		CONTACT-INFO
			""	   
		DESCRIPTION
			"The subtree for Layer 2 Protocol Tunneling (L2PT)"
		::= { esMgmt 39 }	

	zyxelL2ptSetup      	OBJECT IDENTIFIER ::= { zyxelL2pt 1 }
		
--
--
--  39.Layer 2 Protocol Tunneling
--
--
--  zyxelL2ptState                               
        zyL2ptState OBJECT-TYPE
        SYNTAX  EnabledStatus
        MAX-ACCESS  read-write
        STATUS  current
        DESCRIPTION
        "Enable/disable L2PT (Layer 2 protocol tunneling) feature on the switch.  
		 L2PT is used on the service provider's edge devices. L2PT allows edge switches 
		 to tunnel layer 2 STP (Spanning Tree Protocol), CDP (Cisco Discovery Protocol) 
		 and VTP (VLAN Trunking Protocol) packets between customer switches connected 
		 through the service provider's network. The edge switch encapsulates layer 2 
		 protocol packets with a specific MAC address before sending them across the 
		 service provider's network to other edge switches."
        ::= { zyxelL2ptSetup 1 }
                                
        zyL2ptMacAddress OBJECT-TYPE
        SYNTAX  MacAddress
        MAX-ACCESS  read-write
        STATUS  current
        DESCRIPTION
        "Specify an MAC address with which the switch uses to encapsulate the layer 2 protocol 
		 packets by replacing the destination MAC address in the packets."
        ::= { zyxelL2ptSetup 2 }
                                
-- 		zyxelL2ptTable
 
        zyxelL2ptTable OBJECT-TYPE
        SYNTAX SEQUENCE OF ZyxelL2ptEntry
        MAX-ACCESS  not-accessible
        STATUS  current
        DESCRIPTION
        "The table contains L2PT configuration."
        ::= { zyxelL2ptSetup 3 }
        
 		zyxelL2ptEntry OBJECT-TYPE
        SYNTAX ZyxelL2ptEntry
        MAX-ACCESS not-accessible
        STATUS current
        DESCRIPTION     
		"An entry contains L2PT configuration."
        INDEX           { dot1dBasePort }
        ::= { zyxelL2ptTable 1 }
 
        ZyxelL2ptEntry ::=
           SEQUENCE {
         zyL2ptProtocolGroup  BITS,
         zyL2ptPointToPointProtocolGroup BITS,
         zyL2ptMode   INTEGER
           }
 
     	zyL2ptProtocolGroup OBJECT-TYPE
        SYNTAX BITS {
		  cdp(0),
		  stp(1),
		  vtp(2)
		 }
        MAX-ACCESS  read-write
        STATUS  current
        DESCRIPTION
        "Enable/disable L2PT protocols on the port. Select this option to have the Switch tunnel CDP 
         (Cisco Discovery Protocol) packets so that other Cisco devices can be discovered through the 
         service provider's network. Select this option to have the Switch tunnel STP (Spanning Tree Protocol) 
         packets so that STP can run properly across the service provider's network and spanning trees 
         can be set up based on bridge information from all (local and remote) networks. Select this option 
         to have the Switch tunnel VTP (VLAN Trunking Protocol) packets so that all customer switches can 
         use consistent VLAN configuration through the service provider's network."
        ::= { zyxelL2ptEntry 1 }
 
     	zyL2ptPointToPointProtocolGroup OBJECT-TYPE
        SYNTAX BITS {
		  pagp(0),
		  lacp(1),
		  udld(2)
		 }
        MAX-ACCESS  read-write
        STATUS  current
        DESCRIPTION
        "Enable/Disable L2PT point-to-point protocols on the port. The switch supports PAgP (Port Aggregation Protocol),
		 LACP (Link Aggregation Control Protocol) and UDLD (UniDirectional Link Detection) tunneling for a point-to-point topology.
		 Both PAgP and UDLD are Cisco's proprietary data link layer protocols. PAgP is similar to LACP and used to set up a logical 
		 aggregation of Ethernet ports automatically. UDLD is to determine the link's physical status and detect a unidirectional link."
        ::= { zyxelL2ptEntry 2 }
                
        zyL2ptMode OBJECT-TYPE
        SYNTAX  INTEGER {
         access(1),
         tunnel(2)
        }
        MAX-ACCESS  read-write
        STATUS  current
        DESCRIPTION
        "Select access to have the switch encapsulate the incoming layer 2 protocol packets and forward them to the tunnel port(s). 
		 Select access for ingress ports at the edge of the service provider's network. Select Tunnel for egress ports at the edge 
		 of the service provider's network."
        ::= { zyxelL2ptEntry 3 }   


END
