ELTEX-MES-COPY-MIB DEFINITIONS ::= BEGIN

IMPORTS
    eltMesCopy                                              FROM ELTEX-MES
    TruthValue,DisplayString,RowStatus                      FROM SNMPv2-TC
    MODULE-IDENTITY, OBJECT-TYPE,Unsigned32                 FROM SNMPv2-SMI
    InetAddressType, InetAddress                            FROM INET-ADDRESS-MIB -- RFC2851
    RlCopyLocationType                                      FROM RADLAN-COPY-MIB;

eltCopyAutoBackupEnable  OBJECT-TYPE
    SYNTAX TruthValue
    MAX-ACCESS read-write
    STATUS current
    DESCRIPTION
        "Enabling on automatic backup configuration."
    DEFVAL { false }
    ::= { eltMesCopy 1 }

eltCopyAutoBackupTimeout  OBJECT-TYPE
    SYNTAX  Unsigned32
    MAX-ACCESS  read-write
    STATUS  current
    DESCRIPTION
        " This MIB should be used in order to change the time-interval of automatic copy of
          running-config to external server. The value should be the number of minutes for
          the interval of time from the backup."
    ::= { eltMesCopy 2 }

eltCopyAutoBackupFilePath OBJECT-TYPE
    SYNTAX        DisplayString
    MAX-ACCESS    read-write
    STATUS        current
    DESCRIPTION
        "The name of the destination file."
    ::= { eltMesCopy 3 }

eltCopyAutoBackupServerAddress OBJECT-TYPE
    SYNTAX       DisplayString
    MAX-ACCESS   read-write
    STATUS current
    DESCRIPTION
        "The Inet address of the destination remote host"
    ::= { eltMesCopy 4 }

eltCopyAutoBackupOnWrite OBJECT-TYPE
    SYNTAX TruthValue
    MAX-ACCESS read-write
    STATUS current
    DESCRIPTION
        "Performing automatic backups every time
        you write configuration in memory."
    DEFVAL { false }
    ::= { eltMesCopy 5 }


EltCopyUserBackupStatus ::= TEXTUAL-CONVENTION
    STATUS       current
    DESCRIPTION
            "Starting backup manually."
    SYNTAX INTEGER {
        starting(1),
        stopped(2)
    }

eltCopyUserBackupStart OBJECT-TYPE
    SYNTAX EltCopyUserBackupStatus
    MAX-ACCESS read-write
    STATUS current
    DESCRIPTION
        "Starting backup manually."
    DEFVAL { stopped }
    ::= { eltMesCopy 6 }



eltCopyBackupHistoryEnable OBJECT-TYPE
    SYNTAX TruthValue
    MAX-ACCESS read-write
    STATUS current
    DESCRIPTION
        "Performing automatic backups every time
        you write configuration in memory."
    DEFVAL { false }
    ::= { eltMesCopy 7 }

eltCopyBackupHistoryTable  OBJECT-TYPE
    SYNTAX  SEQUENCE OF EltCopyBackupHistoryEntry
    MAX-ACCESS  not-accessible
    STATUS      current
    DESCRIPTION      "A DHCP interface configuration table."
    ::= { eltMesCopy 8 }

eltCopyBackupHistoryEntry OBJECT-TYPE
   SYNTAX      EltCopyBackupHistoryEntry
   MAX-ACCESS  not-accessible
   STATUS      current
   DESCRIPTION        "A DHCP interface configuration entry."
   INDEX {eltCopyBackupHistoryIndex}
::= { eltCopyBackupHistoryTable 1 }

EltCopyBackupHistoryEntry ::= SEQUENCE {
   eltCopyBackupHistoryIndex                  INTEGER,
   eltCopyBackupHistoryDateTime               DisplayString,
   eltCopyBackupHistoryDstLocation            RlCopyLocationType,
   eltCopyBackupHistoryServerAddr             DisplayString,
   eltCopyBackupHistoryFilePath               DisplayString,
   eltCopyBackupHistoryStatus                 RowStatus
}

eltCopyBackupHistoryIndex OBJECT-TYPE
    SYNTAX INTEGER
    MAX-ACCESS not-accessible
    STATUS current
    DESCRIPTION
        "An arbitrary incremental index for the profiles table. Zero for next free index."
    ::= { eltCopyBackupHistoryEntry 1 }

eltCopyBackupHistoryDateTime OBJECT-TYPE
    SYNTAX DisplayString
    MAX-ACCESS read-write
    STATUS current
    DESCRIPTION
        "Name of profile."
    ::= { eltCopyBackupHistoryEntry 2 }

eltCopyBackupHistoryDstLocation OBJECT-TYPE
   SYNTAX RlCopyLocationType
    MAX-ACCESS read-write
    STATUS current
    DESCRIPTION
        "Destination File Location"
    ::=  { eltCopyBackupHistoryEntry 3 }

eltCopyBackupHistoryServerAddr OBJECT-TYPE
    SYNTAX DisplayString
    MAX-ACCESS read-write
    STATUS current
    DESCRIPTION
        "Name of profile."
    ::= { eltCopyBackupHistoryEntry 4 }

eltCopyBackupHistoryFilePath OBJECT-TYPE
    SYNTAX DisplayString
    MAX-ACCESS read-write
    STATUS current
    DESCRIPTION
        "Name of profile."
    ::= { eltCopyBackupHistoryEntry 5 }

eltCopyBackupHistoryStatus OBJECT-TYPE
    SYNTAX  RowStatus
    MAX-ACCESS  read-write
    STATUS  current
    DESCRIPTION
       "The status of a table entry.
        Only three statuses are aceptable: CreateAndGo to create,
        Active to update,Destroy to delete. All other values cause error."
    ::= { eltCopyBackupHistoryEntry 6 }

eltCopyBackupHistoryAction OBJECT-TYPE
    SYNTAX      INTEGER {
       noAction(1),  -- for get only
       clearNow(2)
     }
    MAX-ACCESS  read-write
    STATUS      current
    DESCRIPTION
        "Used to clear backup Table."
    ::= { eltMesCopy 9 }

END
