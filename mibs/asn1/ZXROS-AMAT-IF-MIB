--  ************************************************
--  $Id: ZXROS-AMAT-IF.mib 13 2006-06-01 09:46:26 zhongyan $
--
--  ZXROS-AMAT-IF.mib: ZXROS AMAT Interface Configuration MIB file
--  
--  May. 2006, Zhong yan
--   
--  Copyright(c) 2006 by ZTE Corporaton
--  All rights reservered
--
--  ************************************************

ZXROS-AMAT-IF-MIB DEFINITIONS ::= BEGIN

IMPORTS
     
    OBJECT-TYPE, 
    Integer32,
    Counter64 
        FROM SNMPv2-SMI      
    enterprises                      
        FROM SNMPv2-SMI;        
    
    zte OBJECT IDENTIFIER ::= { enterprises 3902 }
    zxros  OBJECT IDENTIFIER ::= { zte 100 }
    zxrosAMATIF OBJECT IDENTIFIER ::= { zxros 1001 }
    
    --  This data type is used to model textual information taken
    --  from the NVT ASCII character set.  By convention, objects
    --  with this syntax are declared as having
    --  SIZE (0..255)

 zxrosAMATInterfaceEnableTable OBJECT-TYPE
        SYNTAX  SEQUENCE OF ZxrosAMATInterfaceEnableEntry
        MAX-ACCESS  not-accessible
        STATUS  current
        DESCRIPTION
            "AMAT interface enable or disable table"
        ::= { zxrosAMATIF 1 }

 zxrosAMATInterfaceEnableEntry OBJECT-TYPE
        SYNTAX  ZxrosAMATInterfaceEnableEntry
        MAX-ACCESS  not-accessible
        STATUS  current
        DESCRIPTION
            "AMAT interface enable entry"
        INDEX  { zxrosAMATInterfaceEnableIfIndex }
        ::= { zxrosAMATInterfaceEnableTable 1 }
        
 ZxrosAMATInterfaceEnableEntry ::=
     SEQUENCE {
         zxrosAMATInterfaceEnableIfIndex
             Integer32,
         zxrosAMATInterfaceInAmatEnable
             INTEGER,
         zxrosAMATInterfaceOutAmatEnable
             INTEGER                                  
 }       
 
 zxrosAMATInterfaceEnableIfIndex  OBJECT-TYPE
        SYNTAX   Integer32
        MAX-ACCESS  read-only
        STATUS  current
        DESCRIPTION
            "Interface index"
        ::= { zxrosAMATInterfaceEnableEntry 1 }       
 
 zxrosAMATInterfaceInAmatEnable OBJECT-TYPE
        SYNTAX  INTEGER{enable(1),disable(2)}
        MAX-ACCESS  read-write
        STATUS  current
        DESCRIPTION
            "Using enable and disable to describe interface inside amat state"
        ::= { zxrosAMATInterfaceEnableEntry 2 }
        
 zxrosAMATInterfaceOutAmatEnable OBJECT-TYPE
        SYNTAX  INTEGER{enable(1),disable(2)}
        MAX-ACCESS  read-write
        STATUS  current
        DESCRIPTION
            "Using enable and disable to describe interface outside amat state"
        ::= { zxrosAMATInterfaceEnableEntry 3 }

 zxrosAMATInterfaceStatisticTable  OBJECT-TYPE
        SYNTAX  SEQUENCE OF ZxrosAMATInterfaceStatisticEntry
        MAX-ACCESS  not-accessible
        STATUS  current
        DESCRIPTION
            "AMAT interface statistic table"
        ::= { zxrosAMATIF 2 } 
        
 zxrosAMATInterfaceStatisticEntry  OBJECT-TYPE
        SYNTAX  ZxrosAMATInterfaceStatisticEntry
        MAX-ACCESS  not-accessible
        STATUS  current
        DESCRIPTION
            "AMAT interface statistic entry"
        INDEX  { zxrosAMATInterfaceStatisticIfIndex }
        ::= { zxrosAMATInterfaceStatisticTable 1 }
        
 ZxrosAMATInterfaceStatisticEntry ::=
     SEQUENCE {
         zxrosAMATInterfaceStatisticIfIndex
             Integer32,
         zxrosAMATInFilterpackets
             Counter64,
         zxrosAMATOutFilterpackets
             Counter64
 }
 
 zxrosAMATInterfaceStatisticIfIndex  OBJECT-TYPE
        SYNTAX   Integer32
        MAX-ACCESS  read-only
        STATUS  current
        DESCRIPTION
            "Interface index"
        ::= { zxrosAMATInterfaceStatisticEntry 1 }
        
 zxrosAMATInFilterpackets  OBJECT-TYPE
        SYNTAX   Counter64
        MAX-ACCESS  read-only
        STATUS  current
        DESCRIPTION
            "An 64 bit unsigned integer description of the zxrosAMATInFilterpackets"
        ::= { zxrosAMATInterfaceStatisticEntry 2 }
        
 zxrosAMATOutFilterpackets  OBJECT-TYPE
        SYNTAX   Counter64
        MAX-ACCESS  read-only
        STATUS  current
        DESCRIPTION
            "An 64 bit unsigned integer description of the zxrosAMATInFilterpackets"
        ::= { zxrosAMATInterfaceStatisticEntry 3 }

     
    END
