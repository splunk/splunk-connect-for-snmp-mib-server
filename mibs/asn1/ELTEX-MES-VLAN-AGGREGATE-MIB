ELTEX-MES-VLAN-AGGREGATE-MIB DEFINITIONS ::= BEGIN

-- Version:    1.0
-- Date:       23 May 2014

IMPORTS
    eltMes                                      FROM ELTEX-MES
    DisplayString,RowStatus                     FROM SNMPv2-TC
    MODULE-IDENTITY, OBJECT-TYPE                FROM SNMPv2-SMI;

eltMesIpUnnumbered MODULE-IDENTITY
            LAST-UPDATED "201405230000Z"
            ORGANIZATION "Eltex Enterprise Co, Ltd."
            CONTACT-INFO
                  "www.eltex.nsk.ru"
            DESCRIPTION
                  "This private MIB module defines End of Eltex private MIBs."
            REVISION "201405230000Z"
            DESCRIPTION
                  "Initial version of this MIB."
          ::= { eltMes 7 }

eltIpUnnumberedInterfaceTable OBJECT-TYPE
    SYNTAX      SEQUENCE OF EltIpUnnumberedInterfaceEntry
    MAX-ACCESS  not-accessible
    STATUS      current
    DESCRIPTION
        "A table contains ip unnumbered interfaces."
    ::= { eltMesIpUnnumbered 1 }

eltIpUnnumberedInterfaceEntry OBJECT-TYPE
    SYNTAX      EltIpUnnumberedInterfaceEntry
    MAX-ACCESS  not-accessible
    STATUS      current
    DESCRIPTION
        "The row definition for this table."
    INDEX   {eltIpUnnumberedIfIndex}
    ::= { eltIpUnnumberedInterfaceTable 1 }

EltIpUnnumberedInterfaceEntry ::=SEQUENCE {
    eltIpUnnumberedIfIndex           INTEGER,
    eltIpUnnumberedAggrIfIndex       INTEGER,
    eltIpUnnumberedVlan1to1024       OCTET STRING,
    eltIpUnnumberedVlan1025to2048    OCTET STRING,
    eltIpUnnumberedVlan2049to3072    OCTET STRING,
    eltIpUnnumberedVlan3073to4094    OCTET STRING,
    eltIpUnnumberedStatus            RowStatus

}

eltIpUnnumberedIfIndex OBJECT-TYPE
   SYNTAX      INTEGER
   MAX-ACCESS  read-write
   STATUS      current
   DESCRIPTION
     "An index is entrie's sequence.
     The table contains only one static entry."

   ::= { eltIpUnnumberedInterfaceEntry 1}

eltIpUnnumberedAggrIfIndex OBJECT-TYPE
   SYNTAX      INTEGER
   MAX-ACCESS  read-only
   STATUS      current
   DESCRIPTION
     "An index is entrie's sequence.
     The table contains only one static entry."

   ::= { eltIpUnnumberedInterfaceEntry 2}

eltIpUnnumberedVlan1to1024 OBJECT-TYPE
   SYNTAX      OCTET STRING(SIZE(0..128))
   MAX-ACCESS  read-write
   STATUS      current
   DESCRIPTION
     "A list of staticaly created vlans from 1 to 1024."

   ::= { eltIpUnnumberedInterfaceEntry 3}

eltIpUnnumberedVlan1025to2048 OBJECT-TYPE
   SYNTAX      OCTET STRING(SIZE(0..128))
   MAX-ACCESS  read-write
   STATUS      current
   DESCRIPTION
     "A list of staticaly created vlans from 1025 to 2048."
   DEFVAL {'00'H}
   ::= { eltIpUnnumberedInterfaceEntry 4}

eltIpUnnumberedVlan2049to3072 OBJECT-TYPE
   SYNTAX      OCTET STRING(SIZE(0..128))
   MAX-ACCESS  read-write
   STATUS      current
   DESCRIPTION
     "A list of staticaly created vlans from 2049 to 3072."
   DEFVAL {'00'H}
   ::= { eltIpUnnumberedInterfaceEntry 5}

eltIpUnnumberedVlan3073to4094 OBJECT-TYPE
   SYNTAX      OCTET STRING(SIZE(0..128))
   MAX-ACCESS  read-write
   STATUS      current
   DESCRIPTION
     "A list of staticaly created vlans from 3073 to 4094."
   DEFVAL {'00'H}
   ::= { eltIpUnnumberedInterfaceEntry 6}

eltIpUnnumberedStatus OBJECT-TYPE
        SYNTAX       RowStatus
        MAX-ACCESS   read-create
        STATUS       current
        DESCRIPTION
           "This variable displays the status of  the  en-
           try."
       ::= { eltIpUnnumberedInterfaceEntry 7 }

END
