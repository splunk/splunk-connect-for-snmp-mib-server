PSAX-TRAP-MIB DEFINITIONS ::= BEGIN
IMPORTS
    enterprises, Counter
        FROM RFC1155-SMI
    OBJECT-TYPE
        FROM RFC-1212
    DisplayString
        FROM RFC1213-MIB
    NOTIFICATION-TYPE, MODULE-IDENTITY, ObjectName, Integer32, Counter32, snmpModules
        FROM SNMPv2-SMI
    reason, timeOccurred, code, csID, csType, registrationStatus, gwID, comment, percent, moduleID, port, gwIP, gwType
        FROM AGGREGATED-EXT-MIB
    TruthValue, DisplayString, TestAndIncr, TimeStamp, RowStatus
        FROM SNMPv2-TC;

	lucent		        OBJECT IDENTIFIER  ::=  {  enterprises  1751  }
	products	        OBJECT IDENTIFIER  ::=  {  lucent  1  }
	softSwitch	        OBJECT IDENTIFIER  ::=  {  products 1198  }
	psaxDeviceServer    OBJECT IDENTIFIER  ::=  {  softSwitch 6 }

psaxTraps   MODULE-IDENTITY    
        LAST-UPDATED "240701"
        ORGANIZATION "Lucent Technologies"    
        CONTACT-INFO 
                ""    
        DESCRIPTION
                "The MIB module for entities implementing the xxxx
                protocol."  

::=  {  psaxDeviceServer 0  }

	-- The traps group. Listed below are the traps currently
	-- supported by this device server  



	psaxCSConnectionStatus NOTIFICATION-TYPE
		OBJECTS{ timeOccurred, code, csID, csType, registrationStatus, reason, comment }
        STATUS current
		DESCRIPTION
             		"Indicates the registration status of the device 
			server(registered, unregistered or registration 
			failed).
       			VARIABLE DEFINITIONS:
			1) timeStamp - time when the alarm occured, in 
			<sec>.<usec> format
			2) code - bitwise OR of severity, facility, errorCode,
			instanceID, severity<<28 | facility<<24 | 
			errorCode<<16 | instanceid
			3) csID - call server identifier which will be 
			returned by the call server when any device server 
			registers to it.
			4) csType - call server type, 'primary' or 'secondary'.
			(Right now this information does not come from the 
			call server. It is set to 'primary'.), value = 0 for
			primary, value = 1 for secondary
			5) registrationStatus - registered | unregistred |
			registrationFailed depending on whether the device 
			server is registered, unregistered or could not 
			register to the call server respectively.
			6) reason - {unreachable | unknown | 
			invalidParam}, indicates the cause for the 
			registration failure. 
			7) comment - Any comment sent along with this trap.
 			Severity: INFO for registration/unregistration.
                       	CRITICAL for failed registration."
      		 ::= { psaxTraps  0 }

	psaxGatewayUtilization NOTIFICATION-TYPE
      		OBJECTS{ timeOccurred, code, gwID, moduleID, percent, comment} 
            STATUS current
       		DESCRIPTION
             		"It is triggered when a preset utilization value 
			is set for a gateway and it has met that utilization.
			VARIABLE DEFINITIONS:
			1) timeStamp - time when the alarm occured, in 
			<sec>.<usec> format
			2) code - bitwise OR of severity, facility, errorCode,
			instanceID, severity<<28 | facility<<24 | 
			errorCode<<16 | instanceid
			2) gwID - unique identifier assigned to the gateway.
			3) moduleID - The module of the gateway that reports 
			utilization.
			4) percent - The percent of utilization being reported.
			5) comment - Any comment sent along with this trap
			Severity: INFO/MINOR depending on the preset value."
       		::= { psaxTraps  1 }

	psaxDSError NOTIFICATION-TYPE
       		OBJECTS { timeOccurred, code, reason, comment }
            STATUS current
       		DESCRIPTION
              		"When any error occurs in the device server. 
       			VARIABLE DEFINITIONS:
			1) timeStamp - time when the alarm occured, in 
			<sec>.<usec> format
			2) code - bitwise OR of severity, facility, errorCode,
			instanceID, severity<<28 | facility<<24 | 
			errorCode<<16 | instanceid
			2) reason - the reason for the error that occurs 
			in the device server. Takes one of these values:
			internalError | systemResourceUnavailable |
			invalidGatewayID | unknown 
			3) comment - Any comment sent along with this trap.
			Severity: INFO (internalError), 
			MAJOR (systemResourceUnavailable),
                        INFO (invalidGatewayID - gateway ID is invalid or 
			no such gateway exists)                    
                       	INFO (unknownError - any other errors)."
	       ::= { psaxTraps  2 }

	psaxUnreachableGateway NOTIFICATION-TYPE
		OBJECTS { timeOccurred, code, gwID, gwType, gwIP, port, comment }
            STATUS current
       		DESCRIPTION 
             		"When any gateway is unreachable . Either the 
			TCP/IP address is wrong or the gateway is down.
			VARIABLE DEFINITIONS:
			1) timeStamp - time when the alarm occured, in 
			<sec>.<usec> format
			2) code - bitwise OR of severity, facility, errorCode,
			instanceID, severity<<28 | facility<<24 | 
			errorCode<<16 | instanceid
			3) gwID - unique identifier of the gateway
     			4) gwType - protocol handled by the gateway,
			{ h323 | sip | psax }
			5) gwIP - IP Address of the gateway, the device server 
			tries to connect to, in order to place a call.
     			6) port - call signalling port of the gateway, 
			the device server tries to connect to.
     			7) comment - Any comment sent along with this trap
			Severity: MINOR depending on the preset value."

	       ::= { psaxTraps  3 }

	psaxCommandFailed NOTIFICATION-TYPE 
       		OBJECTS { timeOccurred, code, reason, comment }
            STATUS current
       		DESCRIPTION 
             		"Triggered when any request is failed by the 
			device server. 		
			VARIABLE DEFINITIONS:
			1) timeStamp - time when the alarm occured, in 
			<sec>.<usec> format
			2) code - bitwise OR of severity, facility, errorCode,
			instanceID, severity<<28 | facility<<24 | 
			errorCode<<16 | instanceid
			3) reason -  reason for the failure of the command. 
			{internalError | systemResourceUnavailable 
			|notSupported | unknown }
     			4) comment - Any comment along with this trap.
			Severity: MINOR (or may be command sensitive)."

       		::= { psaxTraps  4 }

END
