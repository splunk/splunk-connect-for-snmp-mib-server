RADLAN-RCLI-MIB DEFINITIONS ::= BEGIN

-- Title:                RADLAN ROS
--                       Private RCLI MIB
-- Version:              7.46
-- Date:                 15-Jan-2007

IMPORTS
    rnd                                          FROM RADLAN-MIB
    OBJECT-TYPE, MODULE-IDENTITY                 FROM SNMPv2-SMI;

rlRCli MODULE-IDENTITY
                LAST-UPDATED "200701020000Z"
                ORGANIZATION "Radlan - a MARVELL company.
                              Marvell Semiconductor, Inc."
                CONTACT-INFO
                      "www.marvell.com"
                DESCRIPTION
                      "This private MIB module defines RCli private MIBs."
                REVISION "200701020000Z"
                DESCRIPTION
                      "Initial revision."
        ::= { rnd 70 }

rlRCliMibVersion OBJECT-TYPE
    SYNTAX  INTEGER
    MAX-ACCESS  read-only
    STATUS  current
    DESCRIPTION
        "MIB's version, the current version is 1."
    ::= { rlRCli 1 }

rlRCliUserPassword OBJECT-TYPE
   SYNTAX OCTET STRING (SIZE(0..32))
   MAX-ACCESS read-write
   STATUS current
   DESCRIPTION
       "RCLI User mode Password"
   ::= { rlRCli 2 }

rlRCliEnablePassword OBJECT-TYPE
   SYNTAX OCTET STRING (SIZE(0..32))
   MAX-ACCESS read-write
   STATUS current
   DESCRIPTION
       "RCLI Enable mode Password"
   ::= { rlRCli 3 }

rlRCliConfigPassword OBJECT-TYPE
   SYNTAX OCTET STRING (SIZE(0..32))
   MAX-ACCESS read-write
   STATUS current
   DESCRIPTION
       "RCLI Config mode Password"
   ::= { rlRCli 4 }

rlRCliTimer OBJECT-TYPE
   SYNTAX INTEGER (5..3600)
   MAX-ACCESS read-write
   STATUS current
   DESCRIPTION
       "RCLI Timeout"
   ::= { rlRCli 5 }

rlRcliFileAction OBJECT-TYPE
    SYNTAX INTEGER {
        notUsedAfterReset(1),
        usedAfterReset   (2)
       }
   MAX-ACCESS read-write
   STATUS current
   DESCRIPTION
       "RCLI Configuration File action determines whether
        The device configuration after reset will be set by
        the configuration file content or not."
   ::= { rlRCli 6 }

END
