-- ========================================================
-- Source Safe data:
-- $Revision: 3 $
-- Check In: $Date: 11/07/10 8:23a $
-- $Author: Sbiton $
-- $Archive: /MIBs/Version 1.0/Source/Avaya/CIG-CLIENTS-MIB.my $
-- ========================================================
CIG-CLIENTS-MIB DEFINITIONS ::= BEGIN
   IMPORTS
     OBJECT-GROUP, NOTIFICATION-GROUP, MODULE-COMPLIANCE
         FROM SNMPv2-CONF
     Integer32, Unsigned32, enterprises, Gauge32, Counter32, OBJECT-TYPE, 
      MODULE-IDENTITY, NOTIFICATION-TYPE
         FROM SNMPv2-SMI
      RowStatus, TEXTUAL-CONVENTION, TruthValue, DateAndTime, TimeInterval, DisplayString
         FROM SNMPv2-TC
      InetAddress, InetAddressType
    	 FROM INET-ADDRESS-MIB         
      IpAddress
         FROM RFC1155-SMI;
      


     cigClients MODULE-IDENTITY
       LAST-UPDATED "200910251352Z"   
     ORGANIZATION
                       "Avaya"
     CONTACT-INFO
     "
       Avaya Customer Services
       Postal: Avaya, Inc.
       211 Mt Airy Rd.
       Basking Ridge, NJ 07920
       USA
       Tel:	+1 908 953 6000
       WWW: 	http://www.avaya.com
     "
     DESCRIPTION
     "              
     This module defines the cig Clients. The first client in the DHCP client used for getting 
     dynamic IP address and configuration parameters from DHCP server.The DHCP client will be 
     a function of interfaces.
     The second client is DNS resolver client. 
               
     Copyright notice:
     
     This AVAYA SNMP Management Information Base Specification (Specification) embodies
     AVAYA confidential and Proprietary intellectual property.  AVAYA retains all Title
     and ownership in the Specification, including any revisionsIt is AVAYA's intent to
     encourage the widespread use of this Specification in connection with the management
     of AVAYA products. AVAYA grants vendors, end-users, and other interested parties a
     non-exclusive license to use this Specification in connection with the management 
     of AVAYA products.This Specification is supplied 'as is', and AVAYA makes no warranty,
     either express or implied, as to the use, operation, condition, or performance of the
     Specification.     
     "
           ::= { lsg 17  } 
                      
                      
-- Version 200910251352Z
-- 1. Updating IPv6 notes.
                                            
-- Version 200909011828Z
-- 1. Add IPv6 mib definitions.
                       
-- Version 200531050827Z
-- 1. Add cigDhcpClientsDefaultRouterTrackId for tracking the default router.
--                        
-- Version 200509021627Z
-- cigDhcpClientsClientId and cigDhcpClientsHostName will be limited to 80 characters
--
-- Version 200407110820Z
-- Updating DNS Client MIB
-- 1. Adding new MIB item cigDnsResolverOperations with the enumeration clearDynamicServers(2) that
-- will clear all the dynamic servers (learnt from PPP interfaces and DHCP clients) 
-- from DNS server list.
-- 
-- Version 200421101022Z
-- Updating DHCP client MIB
-- 1. Updating the cigDhcpClientsStatus enumeration. Adding idle(9) and reboot(8) states        
-- and changing the enumeration of release(6) and decline(7).
-- 2. Updating the description of cigDhcpClientsHostName.
-- 3. Change the name of cigDhcpClientsRequestList to cigDhcpClientsRequestBitmap and update the 
-- description.   
-- 4. Change the cigDhcpClientsDefaultGateway to cigDhcpClientsDefaultGatewayList and 
-- cigDhcpClientsDnsServer to cigDhcpClientsDnsServerList.  
--
-- Version 200417101622Z
-- Adding DNS resolver Lior remarks:
-- 1. Updating the size of cigDnsResolverDnsServersListDescription to be 1..64 instead of 0..32.
-- 2. Updating the description of cigDnsResolverDnsServersListEntry, 
-- cigDnsResolverDnsServersListRowStatus and cigDnsResolverDomainRowStatus.
-- 
-- Version 200410031408Z
-- Adding DNS resolver Lior remarks:
-- 1. Adding cigDnsResolverDnsServerListIndex as index to cigDnsResolverDnsServerEntry.
-- 2. Adding note to cigDnsResolverDnsServerRowStatus.
-- 3. cigDnsResolverDnsServerType is R/O instead of R/W. The type is determined according the index 
--    of the server (1-6 static - user configuration and 100-... dynamic servers - automatic/device
--    configuration).
-- 4. Changing cigDnsResolverDomain to be DisplayString [1..255] instead of [1..256].

-- Version 200409190813Z
-- Adding DNS resolver remarks according to DNS resolver MIB review.

-- Version 200409140609Z
-- Adding DNS resolver section.

-- Version 200408292112Z
-- Adding remark to cigDhcpClientsHostName.

-- Version 200408231614Z
--   MIB Review remarks
-- Moving IP address MIB items to Dynamic IP interfaces in CROUTE-MIB (cigDhcpClientsIpInterfaceName,
-- cigDhcpClientsIpInterfaceOperStatus, cigDhcpClientsIcmpRedirects)

-- Version 200408190841Z
--   Initial Version


avaya OBJECT IDENTIFIER ::= { enterprises 6889 }
       
mibs OBJECT IDENTIFIER ::= { avaya 2 }  

lsg  OBJECT IDENTIFIER ::= { mibs 1 }       

cigDhcpClients OBJECT IDENTIFIER ::= { cigClients 1 }

cigDnsResolver OBJECT IDENTIFIER ::= { cigClients 2 }

cigDhcpClientsNotification OBJECT IDENTIFIER ::= { cigDhcpClients 0 }

cigDhcpClientsConflictDetectionTrap NOTIFICATION-TYPE
            OBJECTS { cigDhcpClientsIfAlias, cigDhcpClientsIPAddress, cigDhcpClientsHostName,
            cigDhcpClientsClientId, 
            cigDhcpClientsServerIpAddr}
            STATUS current
            DESCRIPTION
                "DHCP IP address conflict detection. This trap is based on:                          
                The Client Decline Packets after the client sent gratuitous Arp and get response 
                which implies that another station use this IP address."
            ::= { cigDhcpClientsNotification 1 }   

cigDhcpClientsTable OBJECT-TYPE
			SYNTAX SEQUENCE OF CigDhcpClientsEntry
			MAX-ACCESS not-accessible
			STATUS current
			DESCRIPTION
				"cigDhcpClientsTable parameters. Used for DHCP clients 
				which gathered dynamic IP addresses and configuration from DHCP servers."
			::= { cigDhcpClients 1 }
		
cigDhcpClientsEntry OBJECT-TYPE
			SYNTAX CigDhcpClientsEntry
			MAX-ACCESS not-accessible
			STATUS current
			DESCRIPTION
				"cigDhcpClients Entry Parameters."
			INDEX { cigDhcpClientsIfIndex }
			::= { cigDhcpClientsTable 1 }
		
		CigDhcpClientsEntry ::=
			SEQUENCE { 
				cigDhcpClientsIfIndex
					INTEGER,
				cigDhcpClientsRowStatus
					RowStatus,      
				cigDhcpClientsIfAlias
					DisplayString,    	
				cigDhcpClientsIPAddress
				    IpAddress,    
				cigDhcpClientsSubnetMask   
					IpAddress,    
				cigDhcpClientsClientId
					OCTET STRING,
				cigDhcpClientsHostName
					DisplayString,    
				cigDhcpClientsRequestLeaseTime
					Unsigned32,
				cigDhcpClientsReceiveLeaseTime
					Unsigned32,
                cigDhcpClientsRemainLeaseTime
					Unsigned32,  
				cigDhcpClientsRenewLeaseTime
					Unsigned32, 
				cigDhcpClientsRebindLeaseTime				
					Unsigned32, 
				cigDhcpClientsDefaultGatewayList
					DisplayString,
				cigDhcpClientsDnsServerList				
					DisplayString,
				cigDhcpClientsDomainName
					DisplayString,
				cigDhcpClientsServerIpAddr
					IpAddress,
				cigDhcpClientsOperations
					INTEGER,
				cigDhcpClientsStatus
					INTEGER,
				cigDhcpClientsRequestBitmap
				    OCTET STRING,
				cigDhcpClientsDefaultRouterTrackId
					Unsigned32
				 }

		cigDhcpClientsIfIndex OBJECT-TYPE
			SYNTAX INTEGER
			MAX-ACCESS read-only
			STATUS current
			DESCRIPTION
				"A unique value for each interface. This value is same as ifIndex from ifTable.
				The DHCP client can be enabled on Vlan and on WAN Fast Ethernet interfaces. "
			::= { cigDhcpClientsEntry 1 }
		
		cigDhcpClientsRowStatus OBJECT-TYPE
			SYNTAX RowStatus
			MAX-ACCESS read-write
			STATUS current
			DESCRIPTION
				" This is a row status mib item For adding and deleting DHCP clients
				interfaces.                                              
				For configuring only DHCP client parameters use create and wait for specific interface.
				When activating the DHCP client, activate the row. Activating the row will create a new row
				in the ipDynamic Table in CROUTE-MIB that presents dynamic ipInterface.
				Deactivating the DHCP client will cause to erasing the row in the ipDynamic Mib table 
				and deactivating the DHCP client row in order to keep the specific DHCP parameters which 
				already were configured.
				"
			::= { cigDhcpClientsEntry 2 }
	
		cigDhcpClientsIfAlias OBJECT-TYPE
			SYNTAX DisplayString (SIZE (0..32))
			MAX-ACCESS read-only
			STATUS current
			DESCRIPTION
				"This object is an 'alias' name for
				the lower-layer interface on top of
				which this IP interface is defined.
				It is the same as the ifAlias from the standard interface table."
			::= { cigDhcpClientsEntry 3 }

		cigDhcpClientsIPAddress OBJECT-TYPE
			SYNTAX IpAddress
			MAX-ACCESS read-only
			STATUS current
			DESCRIPTION
				"The IP address received from remote peer during the DHCP session.
				This is the same MIB item as ipInterface table in CROUTE-MIB."
			DEFVAL { '00000000'h }
			::= { cigDhcpClientsEntry 4 }

		cigDhcpClientsSubnetMask OBJECT-TYPE
			SYNTAX IpAddress
			MAX-ACCESS read-only
			STATUS current
			DESCRIPTION
				"The subnet mask associated with the
				IP address of this entry. The value of
				the mask is an IP address with all the
				network bits set to 1 and all the
				hosts bits set to 0.
				In case of DHCP client this is DHCP option 1 == Subnet Mask.
				This is the same MIB item as ipInterface table in CROUTE-MIB."
			::= { cigDhcpClientsEntry 5 }

		cigDhcpClientsClientId OBJECT-TYPE
	    	SYNTAX OCTET STRING (SIZE (0..80))
			MAX-ACCESS read-write
			STATUS current
			DESCRIPTION
			"Client identifier used for manual leased. The structure of the client identifier is 
		 	as follows: combination of TYPE and Data. Where Type = 01 if for Ethernet MACs and Data for 
		 	this case if Ethernet MAC address.      
		 	The user can use also other client identifiers as strings. 
		 	Default: '' - 01:Interface MAC address."
        	::= { cigDhcpClientsEntry 6 }         
			

        cigDhcpClientsHostName OBJECT-TYPE           
        	SYNTAX DisplayString (SIZE (0..80))     
        	MAX-ACCESS read-write
        	STATUS current            
        	DESCRIPTION
         	"Host name is sent by the DHCP client as Dhcp option 12. It is specifically used by 
         	part of DHCP servers (MS2000) to identify the client in the binding file (more user
         	intuitive). This option is used as well by part of the DHCP server with the support
         	of DHCP client (sending option 81) to update the DNS server with the new IP for specific
         	host. 
         	The format of the string can be: 'usernameA'. 
         	The hostname shall comply to RFC 1035 naming convention with the following exceptions:
         	a. allow digits at the start of the name.
         	b. Do not check length constraints of 63 bytes.
         	The default of the host name used by the DHCP client is the device host name."                  
        	DEFVAL {"" }
        	::= { cigDhcpClientsEntry 7}           

    	cigDhcpClientsRequestLeaseTime OBJECT-TYPE
        	SYNTAX 	Unsigned32
        	MAX-ACCESS read-write
        	STATUS current
        	DESCRIPTION
        	"The Requested leased time in seconds. Infinite is defined as 0xffffffff. 
        	0 - used to present that no lease time requested from the DHCP server. I.e. option 51 
        	will not be sent by the client. Default 0 seconds."     
        	DEFVAL { 0 }        
        	::= { cigDhcpClientsEntry 8 }        	
        				
       	cigDhcpClientsReceiveLeaseTime OBJECT-TYPE
        	SYNTAX 	Unsigned32
        	MAX-ACCESS read-only
        	STATUS current
        	DESCRIPTION
        	"The received leased time from the DHCP server in seconds. 
        	Infinite is defined as 0xffffffff. Default 0 seconds."     
        	DEFVAL { 0 }        
        	::= { cigDhcpClientsEntry 9 }

    	cigDhcpClientsRemainLeaseTime OBJECT-TYPE
        	SYNTAX 	Unsigned32
        	MAX-ACCESS read-only
        	STATUS current
        	DESCRIPTION
        	"The remains leased time in seconds . Infinite is defined as 0xffffffff.
         	Default 0 seconds."     
        	DEFVAL { 0 }        
        	::= { cigDhcpClientsEntry 10 }         
        	
    	cigDhcpClientsRenewLeaseTime OBJECT-TYPE
        	SYNTAX 	Unsigned32
        	MAX-ACCESS read-only
        	STATUS current
        	DESCRIPTION
        	"The time defined for renewing phase in seconds . Infinite is defined as 0xffffffff.
        	It is defined as 0.5 of the receive lease.
         	Default 0 seconds."     
        	DEFVAL { 0 }        
        	::= { cigDhcpClientsEntry 11 }        
        	
    	cigDhcpClientsRebindLeaseTime OBJECT-TYPE
        	SYNTAX 	Unsigned32
        	MAX-ACCESS read-only
        	STATUS current
        	DESCRIPTION
        	"The time defined for rebinding phase in seconds . Infinite is defined as 0xffffffff.
        	It is defined as 0.875 of the receive lease.
         	Default 0 seconds."     
        	DEFVAL { 0 }        
        	::= { cigDhcpClientsEntry 12 }                	        	
        	
	  	cigDhcpClientsDefaultGatewayList OBJECT-TYPE           
        	SYNTAX DisplayString (SIZE (0..128))     
        	MAX-ACCESS read-only
        	STATUS current            
        	DESCRIPTION
         	"Default Gateway is Dhcp option 3.  Default = '' = Null String.
         	The format of the string can be up to 8 IP addresses in the list, for example:
         	'121.23.1.12 135.64.13.190 192.123.242.230'"
        	DEFVAL {"" }
        	::= { cigDhcpClientsEntry 13}
        
    	cigDhcpClientsDnsServerList OBJECT-TYPE           
 	       SYNTAX DisplayString (SIZE (0..128))     
    	    MAX-ACCESS read-only
        	STATUS current            
        	DESCRIPTION
         	"DNS Server is Dhcp option 6.  Default = '' = Null String.
         	The format of the string can be up to 8 IP addresses in the list, for exapmle:
         	'121.23.1.12 135.64.13.190 192.123.242.230'"
         	DEFVAL {"" }
        	::= { cigDhcpClientsEntry 14}
    
    	cigDhcpClientsDomainName OBJECT-TYPE           
        	SYNTAX DisplayString (SIZE (0..128))     
        	MAX-ACCESS read-only
        	STATUS current            
        	DESCRIPTION
         	"DNS Server is Dhcp option 15.  Default = Null String
         	The format of the string can be: 'avaya'
         	There is no ability to configure this option in the general option table.
         	"                  
        	DEFVAL {"" }
        	::= { cigDhcpClientsEntry 15}
    
   		cigDhcpClientsServerIpAddr OBJECT-TYPE
			SYNTAX IpAddress
			MAX-ACCESS read-only
			STATUS current
			DESCRIPTION
				"The DHCP server IP address that the client gets from it
				the IP address allocation and keep requesting for lease extension from it.
				In case no IP address is gathered from DHCP server then value is 0.0.0.0.
				Default 0.0.0.0."
			::= { cigDhcpClientsEntry 16 }    

    	cigDhcpClientsOperations OBJECT-TYPE            
        SYNTAX  INTEGER  {
        	idle(1),
        	release(2), 
        	renew(3)        	
        	}
        MAX-ACCESS read-write
        STATUS current            
        DESCRIPTION
         "Used for instruct the DHCP client to perfrom release or renew operations."                    
        ::= { cigDhcpClientsEntry 17} 			
			
    	cigDhcpClientsStatus OBJECT-TYPE            
        	SYNTAX  INTEGER  {
        		select(1), 
        		request(2),
        		bound(3),
        		rebind(4), 
        		renew(5),
        		release(6),
        		decline(7),
        		reboot(8),
        		idle(9),
        		notSupported(255)
        		}
        	MAX-ACCESS read-only
        	STATUS current            
        	DESCRIPTION
         	"The status of the DHCP client.
         	Select - Sending DISCOVER packets
         	Request - Requesting IP address after selecting from all the offer packets.
         	Bound - Receiving ACK packet and there is no conflict detection by sending ARP packets.
         	Rebind - After 0.875 out of the lease time the renewal phase enter to rebind.
         	Renew - After 0.5 out of the lease time the device try to renew the lease until 0.875 of the lease time.
         	Release - The client release the lease.
         	Decline - The client detect IP conflict by sending ARP packet.
         	Idle - The client did not get IP address and keep trying after an Idle time (~40 seconds) 
         	to reach new IP address.
         	"                    
        	::= { cigDhcpClientsEntry 18} 			
        	

		cigDhcpClientsRequestBitmap OBJECT-TYPE
	    	SYNTAX OCTET STRING (SIZE (1..32))
			MAX-ACCESS read-write
			STATUS current
			DESCRIPTION
			"
			Each bit of this value set to '1' indicates a specific requested DHCP option (Bitmap
			of 255 options represented by 32Bytes).
			When the bit is set to '1' then specific DHCP option is requested by the client. 
			Subnet mask bit 1 - is always requested.

			Bits are numbered from the most-significant leftmost bit in the
			octet (bit 0) to the least-significant rightmost bit (bit 7).

			Numbering continues across octets, so that octet 1 bit 0 is
			called bit 8.  

		 	Default: '0x5201' which equals to:
		 	bit 1 - Subnet mask (Always requested!)
		 	Bit 3 - Default routers
		 	Bit 6 - DNS servers
		 	Bit 15 - Domain Name"
        	::= { cigDhcpClientsEntry 19 }              
        	
        	
		cigDhcpClientsDefaultRouterTrackId OBJECT-TYPE
            SYNTAX Unsigned32
            MAX-ACCESS read-write
            STATUS current 
            DESCRIPTION
       		"Bind the status of the DHCP default router to an object-tracker by specifying
 			the ID of the object-tracker (avstrTrackerId in 
			AVAYA-SAA-TRACK-MIB).
			A value of 0 means that the default router is not bound to any 
			object-tracker.
			A value of 0xffffffff is notSupported feature for the relevant default router.
			"
            DEFVAL { 0 }
            ::= { cigDhcpClientsEntry 20 }              


cigDnsResolverGenConfig	OBJECT IDENTIFIER ::= { cigDnsResolver 1 } 

cigDnsResolverMode  OBJECT-TYPE
      	SYNTAX TruthValue
      	MAX-ACCESS read-write
        STATUS current
        DESCRIPTION
        "Enable the DNS resolver in the device. Default = True (Enable)."
        DEFVAL { true }
        ::= { cigDnsResolverGenConfig 1 }

cigDnsResolverRetry  OBJECT-TYPE
        SYNTAX 	Unsigned32
        MAX-ACCESS read-write
        STATUS current
        DESCRIPTION
        "The number of retries for each query for specific DNS server
        when there is timeout.
        The range is 0-100."     
        DEFVAL { 2 }             
        ::= { cigDnsResolverGenConfig 2 }

cigDnsResolverTimeout  OBJECT-TYPE
        SYNTAX 	Unsigned32
        MAX-ACCESS read-write
        STATUS current
        DESCRIPTION
        "The timeout in seconds for each query for specific DNS server.
        The range is 1-3600 seconds."     
        DEFVAL { 3 }             
        ::= { cigDnsResolverGenConfig 3 }          

cigDnsResolverOperations OBJECT-TYPE            
        SYNTAX  INTEGER  {
        	idle(1),
        	clearDynamicServers(2),
        	clearDNSCache(3)
        	}
        MAX-ACCESS read-write
        STATUS current            
        DESCRIPTION
         "Used for specific operations for DNS server.
         clearDynamicServers(2) will clear all the dynamic servers (learnt from PPP interfaces 
         and DHCP clients) from DNS server list.
         clearDNSCache(3) - Clear the DNS Resolver cache.
         "                    
        DEFVAL { idle }      
        ::= { cigDnsResolverGenConfig 4} 	


cigDnsResolverDnsServersListTable OBJECT-TYPE
			SYNTAX SEQUENCE OF CigDnsResolverDnsServersListEntry
			MAX-ACCESS not-accessible
			STATUS current
			DESCRIPTION
				"Lists of DNS servers. The default list(1) includes all the static DNS server and the
				dynamic DNS servers from the DHCP clients/PPP interfaces as PPPoE and Dial out modem.
				"
			::= { cigDnsResolver 2 }
		
cigDnsResolverDnsServersListEntry OBJECT-TYPE
			SYNTAX CigDnsResolverDnsServersListEntry
			MAX-ACCESS not-accessible
			STATUS current
			DESCRIPTION
				"The DNS servers list. Lists of DNS servers."
			INDEX { cigDnsResolverDnsServersListIndex}
			::= { cigDnsResolverDnsServersListTable 1 }
		
CigDnsResolverDnsServersListEntry ::=
			SEQUENCE { 
				cigDnsResolverDnsServersListIndex
					INTEGER,              
				cigDnsResolverDnsServersListDescription
				    DisplayString,     
				cigDnsResolverDnsServersListRowStatus
					RowStatus
				 }

cigDnsResolverDnsServersListIndex OBJECT-TYPE
			SYNTAX INTEGER
			MAX-ACCESS read-only
			STATUS current
			DESCRIPTION
				"The index of the list of DNS servers. Default list index is 1.
				The user will not be able to create lists other then default list 
				at the first release."
			::= { cigDnsResolverDnsServersListEntry 1 }
			
cigDnsResolverDnsServersListDescription OBJECT-TYPE
			SYNTAX DisplayString (SIZE (1..64))
			MAX-ACCESS read-write
			STATUS current
			DESCRIPTION
				"This is the list description. Default for DNS list #1: 'DNS list #1'"
			::= { cigDnsResolverDnsServersListEntry 2 }

cigDnsResolverDnsServersListRowStatus OBJECT-TYPE
			SYNTAX RowStatus
			MAX-ACCESS read-write
			STATUS current
			DESCRIPTION
				"This is a row status mib item For adding and deleting DNS server lists. 
				The user will not be able to create lists other then list 1 at the first release."
			::= { cigDnsResolverDnsServersListEntry 3 }

cigDnsResolverDnsServerTable OBJECT-TYPE
			SYNTAX SEQUENCE OF CigDnsResolverDnsServerEntry
			MAX-ACCESS not-accessible
			STATUS current
			DESCRIPTION
				"DNS servers. The user can configure up to 6 static servers located in places 1-6. 
				The other indexes are of dynamic servers which can not be created 
				(learnt automatically by the device) but can be erased.				
				The indexes 1-99 are for static servers (only the first 6 are configurable).
				The indexes 100-199 are for dynamic servers.
				"
			::= { cigDnsResolver 3 }
		
cigDnsResolverDnsServerEntry OBJECT-TYPE
			SYNTAX CigDnsResolverDnsServerEntry
			MAX-ACCESS not-accessible
			STATUS current
			DESCRIPTION
				"The DNS server entry. The user can configure up to 6 static servers located in places 1-6. 
				The other indexes are of dynamic servers which can not be created 
				(learnt automatically by the device) but can be erased.				
				The indexes 1-99 are for static servers (only the first 6 are configurable).
				The indexes 100-199 are for dynamic servers."
			INDEX { cigDnsResolverDnsServerListIndex,  cigDnsResolverDnsServerIndex}
			::= { cigDnsResolverDnsServerTable 1 }
		
CigDnsResolverDnsServerEntry ::=
			SEQUENCE {               
				cigDnsResolverDnsServerListIndex
					INTEGER,
				cigDnsResolverDnsServerIndex
					INTEGER,              
				cigDnsResolverDnsServerIpAddress
					IpAddress,
				cigDnsResolverDnsServerIfIndex
					INTEGER, 
				cigDnsResolverDnsServerType
					INTEGER, 
				cigDnsResolverDnsServerRowStatus
					RowStatus,
				cigDnsResolverDnsServerInetAddressType 
        			InetAddressType,
    			cigDnsResolverDnsServerInetAddress 
    				InetAddress
				 }

cigDnsResolverDnsServerListIndex OBJECT-TYPE
			SYNTAX INTEGER
			MAX-ACCESS read-only
			STATUS current
			DESCRIPTION
				"The index of the list of DNS servers. Default list index is 1.
				The user will not be able to create lists other then default list 
				at the first release."
			::= { cigDnsResolverDnsServerEntry 1 }

cigDnsResolverDnsServerIndex OBJECT-TYPE
			SYNTAX INTEGER
			MAX-ACCESS read-only
			STATUS current
			DESCRIPTION
				"The index of DNS server in the list of DNS servers. The index presents
				the preference of the server. The lower the index the higher priority to use it."
			::= { cigDnsResolverDnsServerEntry 2 }

cigDnsResolverDnsServerIpAddress OBJECT-TYPE
			SYNTAX IpAddress
			MAX-ACCESS read-write
			STATUS current
			DESCRIPTION
				"The DNS server IP address."
			::= { cigDnsResolverDnsServerEntry 3 }

cigDnsResolverDnsServerIfIndex OBJECT-TYPE
			SYNTAX INTEGER
			MAX-ACCESS read-only
			STATUS current
			DESCRIPTION
				"A unique value for each interface. This value is same as ifIndex from ifTable.
				This field is used when the DNS server is learnt from interface running DHCP client
				or PPP negotiated (PPPoE/Dial Out modem).
				This field has no valid value when the type of the DNS server is static."
			::= { cigDnsResolverDnsServerEntry 4 }

cigDnsResolverDnsServerType OBJECT-TYPE            
        SYNTAX  INTEGER  {
        	static(1),
        	dynamic-dhcp(2),
        	dynamic-ppp(3)
        	}
        MAX-ACCESS read-only
        STATUS current            
        DESCRIPTION
         "This is the server type. The user can create new row only when the server type is
         static.
         dynamic-dhcp represents DNS server learnt from DHCP client.
         dynamic-ppp represents DNS server learnt from ppp interface (PPPoE/Dial out modem)."                    
        ::= { cigDnsResolverDnsServerEntry 5} 	

cigDnsResolverDnsServerRowStatus OBJECT-TYPE
			SYNTAX RowStatus
			MAX-ACCESS read-write
			STATUS current
			DESCRIPTION
				" This is a row status mib item For adding and deleting DNS servers. 
				The user can add only static servers in locations 1-6.
				For static servers the operation suppported is CreateAndWait and dynamic servers are
				automatically created by the device."
			::= { cigDnsResolverDnsServerEntry 6 }      
			

cigDnsResolverDnsServerInetAddressType OBJECT-TYPE
    		SYNTAX     InetAddressType
    		MAX-ACCESS read-write
    		STATUS     current
    		DESCRIPTION
           		"The address type of cigDnsResolverDnsServerInetAddress. "
    		::= { cigDnsResolverDnsServerEntry 7 }
    		
	
cigDnsResolverDnsServerInetAddress OBJECT-TYPE
    		SYNTAX     InetAddress
    		MAX-ACCESS read-write
    		STATUS     current
    		DESCRIPTION
           		"The Inet Address of the dns server.   
           		1. The address type of this object is specified in 
                cigDnsResolverDnsServerInetAddressType.
                2. Management applications can use cigDnsResolverDnsServerIpAddress or 
                cigDnsResolverDnsServerInetAddressType/cigDnsResolverDnsServerInetAddress
                to set IPv4 server address and only 
                cigDnsResolverDnsServerInetAddressType/cigDnsResolverDnsServerInetAddress
                to set IPv6 server address.         
				3. The cigDnsResolverDnsServerInetAddressType must always been set before the 
				cigDnsResolverDnsServerInetAddress is set (the avGenOpServerInetAddress must conform 
				to the cigDnsResolverDnsServerInetAddressType).                  
				4. Setting cigDnsResolverDnsServerIpAddress address mib item will change 
				cigDnsResolverDnsServerInetAddressType to IPv4(1) and 
				cigDnsResolverDnsServerInetAddress to IPv4 address configured.
				5. Setting cigDnsResolverDnsServerInetAddress as IPv4 address will also 
				set cigDnsResolverDnsServerIpAddress. 
				6. Setting cigDnsResolverDnsServerInetAddress as IPv6 address will also 
				set cigDnsResolverDnsServerIpAddress to	0.0.0.0.
				7. Default of cigDnsResolverDnsServerInetAddressType is unknown(0) and 
				cigDnsResolverDnsServerInetAddress is zero length.  
				8. Setting cigDnsResolverDnsServerInetAddressType to IPv4 will return 
				cigDnsResolverDnsServerIpAddress and 
				cigDnsResolverDnsServerInetAddressType to default value of  0.0.0.0. 
				Setting genOpServerInetAddressType to value other than IPv4 return 
				cigDnsResolverDnsServerIpAddress to default value of  0.0.0.0 and 
				cigDnsResolverDnsServerInetAddressType to default value of null 
				string.
                Row status can not be active if cigDnsResolverDnsServerIpAddress or 
                cigDnsResolverDnsServerInetAddressType/cigDnsResolverDnsServerInetAddress
                are not configured.
                "
    		::= { cigDnsResolverDnsServerEntry 8 }

cigDnsResolverDomainTable OBJECT-TYPE
			SYNTAX SEQUENCE OF CigDnsResolverDomainEntry
			MAX-ACCESS not-accessible
			STATUS current
			DESCRIPTION
				"The domains used by the DNS resolver to add to non full qualified names.
				I.e. when the host name is not a full host name then these domains are added 
				in order to resolve the non full qulified name. 
				an example for domain is : avaya.com.
				an example for non qualified name  is lantis.
				Therefore when trying to resolve lantis the suffix avaya.com will be added to
				create the name lantis.avaya.com"
			::= { cigDnsResolver 4 }
		
cigDnsResolverDomainEntry OBJECT-TYPE
			SYNTAX CigDnsResolverDomainEntry
			MAX-ACCESS not-accessible
			STATUS current
			DESCRIPTION
				"The Domain entry.
				The domains used by the DNS resolver to add to non full qualified names.
				I.e. when the host name is not a full host name then these domains are added 
				in order to resolve the non full qulified name. 
				an example for domain is : avaya.com.
				an example for non qualified name  is lantis.
				Therefore when trying to resolve lantis the suffix avaya.com will be added to
				create the name lantis.avaya.com"
			INDEX { cigDnsResolverDomainIndex }
			::= { cigDnsResolverDomainTable 1 }
		
CigDnsResolverDomainEntry ::=
			SEQUENCE { 
				cigDnsResolverDomainIndex
					INTEGER,
				cigDnsResolverDomain
					DisplayString,
				cigDnsResolverDomainRowStatus
					RowStatus
				 }

cigDnsResolverDomainIndex OBJECT-TYPE
			SYNTAX INTEGER
			MAX-ACCESS read-only
			STATUS current
			DESCRIPTION
				"The index of the domain. The index presents the precedence of the domain.
				I.e. the lower the index the higher priority this domain is used."
			::= { cigDnsResolverDomainEntry 1 }
			

cigDnsResolverDomain OBJECT-TYPE
			SYNTAX DisplayString (SIZE (1..255))
			MAX-ACCESS read-write
			STATUS current
			DESCRIPTION
				"The Domain shall follow RFC 1035 Host name convention.
				
				The following syntax will result in fewer problems with 
				many applications that use domain names (e.g., mail, TELNET).

				Note that while upper and lower case letters are allowed in domain
				names, no significance is attached to the case.  That is, two names with
				the same spelling but different case are to be treated as if identical.

				The labels must follow the rules for ARPANET host names.  They must
				start with a letter, end with a letter or digit, and have as interior
				characters only letters, digits, and hyphen.  There are also some
				restrictions on the length.  Labels must be 63 characters or less.

				For example, the following strings identify hosts in the Internet:
				A.ISI.EDU XX.LCS.MIT.EDU SRI-NIC.ARPA
				"
			::= { cigDnsResolverDomainEntry 2 }

cigDnsResolverDomainRowStatus OBJECT-TYPE
			SYNTAX RowStatus
			MAX-ACCESS read-write
			STATUS current
			DESCRIPTION
				"This is a row status mib item For adding and deleting domains.
				The row is created by CreateAndWait.
				"
			::= { cigDnsResolverDomainEntry 3 }

END
