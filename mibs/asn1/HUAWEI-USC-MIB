-- ===================================================================
-- Copyright (C) 2014 by HUAWEI TECHNOLOGIES. All rights reserved.
-- Description: 
-- Reference:
-- Version: V1.01
-- ===================================================================

       HUAWEI-USC-MIB DEFINITIONS ::= BEGIN
 
        IMPORTS                                            
            OBJECT-GROUP, MODULE-COMPLIANCE, NOTIFICATION-GROUP            
                FROM SNMPv2-CONF            
            DisplayString, RowStatus                        
                FROM SNMPv2-TC
            TimeTicks, Integer32, Unsigned32, IpAddress, Counter32, OBJECT-TYPE, 
            MODULE-IDENTITY, NOTIFICATION-TYPE            
                FROM SNMPv2-SMI
            hwBRASMib            
                FROM HUAWEI-MIB;
    
    
        hwUSC MODULE-IDENTITY 
            LAST-UPDATED "201407111600Z"        
            ORGANIZATION 
                  "Huawei Technologies Co.,Ltd."
            CONTACT-INFO 
                  "Huawei Industrial Base
  Bantian, Longgang
   Shenzhen 518129
   People's Republic of China
   Website: http://www.huawei.com
   Email: support@huawei.com"
            DESCRIPTION 
                "Please provide the descritpion."

           REVISION    "201407111600Z"   
            DESCRIPTION "V1.01, initial version."

            REVISION    "201008111600Z"   
            DESCRIPTION "V1.00, initial version."
    
            ::= { hwBRASMib 19 }


        
       hwUSCObjects  OBJECT IDENTIFIER ::= { hwUSC  1 }
                                        
        hwUSCConfigTable OBJECT-TYPE
            SYNTAX SEQUENCE OF HwUSCConfigEntry
            MAX-ACCESS not-accessible
            STATUS current
            DESCRIPTION
                "The table describes USC configuration."
            ::= { hwUSCObjects 1 }
        
        hwUSCConfigEntry OBJECT-TYPE
            SYNTAX HwUSCConfigEntry
            MAX-ACCESS not-accessible
            STATUS current
            DESCRIPTION
                "Description."
            INDEX { hwUSCPortIndex }
            ::= { hwUSCConfigTable 1 }
        
        HwUSCConfigEntry ::=
            SEQUENCE { 
                hwUSCPortIndex
                    Integer32,
                hwUSCInterfaceName
                    DisplayString,
                hwAuthenControlPoint
                    INTEGER,
                hwUSCLinkDownOffline
                	Integer32,
                hwUSCControlDownOffline
                    Integer32,
                hwUSCUserSyncInterval
                   Integer32,
                hwUSCUserSyncRetry
                	Integer32
                      }

        hwUSCPortIndex OBJECT-TYPE
            SYNTAX Integer32(0..4294967295)
            MAX-ACCESS read-only
            STATUS current
            DESCRIPTION
                "USC Portindex."
            ::= { hwUSCConfigEntry 1 } 
            
        hwUSCInterfaceName OBJECT-TYPE
            SYNTAX DisplayString (SIZE(1..64))
            MAX-ACCESS read-write
            STATUS current
            DESCRIPTION
                "The name of USC interface."
            ::= { hwUSCConfigEntry 2 }


        hwAuthenControlPoint OBJECT-TYPE
            SYNTAX INTEGER
            {   
              enabled(0),
              disabled(1)
            }
            MAX-ACCESS read-write
            STATUS current
            DESCRIPTION
                "Control-point status on this interface"  
             ::= { hwUSCConfigEntry 3 }   
        
         hwUSCLinkDownOffline OBJECT-TYPE
            SYNTAX Integer32(0..65535)
            MAX-ACCESS read-write
            STATUS current
            DESCRIPTION
                "The port LinkDownOffline<0 60>, unlimited:65535"
            ::= { hwUSCConfigEntry 4 }

        
        hwUSCControlDownOffline OBJECT-TYPE
            SYNTAX Integer32 (0..65535)
            MAX-ACCESS read-write
            STATUS current
            DESCRIPTION
                "The port ControlDownOffline<0 60>, unlimited:65535"
            ::= { hwUSCConfigEntry 5 } 
             
        hwUSCUserSyncInterval OBJECT-TYPE
            SYNTAX Integer32(60..3600)
            MAX-ACCESS read-write
            STATUS current
            DESCRIPTION
                "user-sync interval.seconds:60"
            ::= { hwUSCConfigEntry 6 }

        hwUSCUserSyncRetry OBJECT-TYPE
            SYNTAX Integer32(5..300)
            MAX-ACCESS read-write
            STATUS current
            DESCRIPTION
                "user-sync retry.times:5"
            ::= { hwUSCConfigEntry 7 }       
                  
        END
