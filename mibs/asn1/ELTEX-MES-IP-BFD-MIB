ELTEX-MES-IP-BFD-MIB DEFINITIONS ::= BEGIN

-- Title:      Eltex's MES Switches Private MIB
-- Version:    1.00
-- Date:       30-Aug-2013

IMPORTS
    eltMes                       FROM ELTEX-MES
    IpAddress,
    OBJECT-TYPE,
    Unsigned32,
    MODULE-IDENTITY              FROM SNMPv2-SMI
    TruthValue,
    RowStatus                    FROM SNMPv2-TC;


eltMesIpBfd MODULE-IDENTITY
                LAST-UPDATED "201403280000Z"
                ORGANIZATION "Eltex Enterprise Co, Ltd."
                CONTACT-INFO
                      "www.eltex.nsk.ru"
                DESCRIPTION
                      "This private MIB module defines End of Eltex private MIBs."
                REVISION "201403280000Z"
                DESCRIPTION
                      "Initial revision."
    ::= { eltMes 6 }

--
-- eltMesIpBfd
--

    eltIpBfdOspfEnable OBJECT-TYPE
        SYNTAX     INTEGER {
            enabled(1),
            disabled(2)
        }
        MAX-ACCESS read-write
        STATUS     current
        DESCRIPTION
            ""
        DEFVAL { disabled }
        ::= { eltMesIpBfd 1 }

        eltIpBfdIfTable OBJECT-TYPE
        SYNTAX     SEQUENCE OF EltIpBfdIfEntry
        MAX-ACCESS not-accessible
        STATUS     current
        DESCRIPTION
            ""
        ::= { eltMesIpBfd 2 }

    eltIpBfdIfEntry OBJECT-TYPE
        SYNTAX     EltIpBfdIfEntry
        MAX-ACCESS not-accessible
        STATUS     current
        DESCRIPTION
            "The BFD Session Entry describes BFD session."
        INDEX { eltIpBfdAddr }
        ::= { eltIpBfdIfTable 1 }

    EltIpBfdIfEntry ::= SEQUENCE {
          eltIpBfdAddr                      IpAddress,
          eltIpBfdDesiredMinTxInterval      Unsigned32,
          eltIpBfdReqMinRxInterval          Unsigned32,
          eltIpBfdDetectMult                Unsigned32,
          eltIpBfdOspfDisable               TruthValue,
          eltIpBfdRipDisable                TruthValue,
          eltIpBfdRowStatus                 RowStatus
    }

    eltIpBfdAddr OBJECT-TYPE
        SYNTAX     IpAddress
        MAX-ACCESS read-only
        STATUS     current
        DESCRIPTION
            ""
        ::= { eltIpBfdIfEntry 1 }

    eltIpBfdDesiredMinTxInterval OBJECT-TYPE
        SYNTAX     Unsigned32
        MAX-ACCESS read-write
        STATUS     current
        DESCRIPTION
            ""
        ::= { eltIpBfdIfEntry 2 }

    eltIpBfdReqMinRxInterval OBJECT-TYPE
        SYNTAX     Unsigned32
        MAX-ACCESS read-write
        STATUS     current
        DESCRIPTION
            ""
        ::= { eltIpBfdIfEntry 3 }

    eltIpBfdDetectMult OBJECT-TYPE
        SYNTAX     Unsigned32
        MAX-ACCESS read-write
        STATUS     current
        DESCRIPTION
            ""
        ::= { eltIpBfdIfEntry 4 }

    eltIpBfdRowStatus OBJECT-TYPE
        SYNTAX     RowStatus
        MAX-ACCESS read-create
        STATUS     current
        DESCRIPTION
            ""
        ::= { eltIpBfdIfEntry 7 }

    eltIpBfdOspfDisable OBJECT-TYPE
        SYNTAX     TruthValue
        MAX-ACCESS read-write
        STATUS     current
        DESCRIPTION
            ""
        ::= { eltIpBfdIfEntry 5 }

    eltIpBfdRipDisable OBJECT-TYPE
        SYNTAX     TruthValue
        MAX-ACCESS read-write
        STATUS     current
        DESCRIPTION
            ""
        ::= { eltIpBfdIfEntry 6 }

END
