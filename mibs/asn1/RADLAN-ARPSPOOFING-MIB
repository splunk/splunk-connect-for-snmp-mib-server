RADLAN-ARPSPOOFING-MIB DEFINITIONS ::= BEGIN

-- Title:                RADLAN ROS
--                       Private ARP SPOOFING MIB
-- Version:              7.46
-- Date:                 15-Jan-2007

IMPORTS
    rnd                                                     FROM RADLAN-MIB
    OBJECT-TYPE, MODULE-IDENTITY, IpAddress                 FROM SNMPv2-SMI
    RowStatus, PhysAddress                                  FROM SNMPv2-TC
    InterfaceIndex, InterfaceIndexOrZero                    FROM IF-MIB;

rlArpSpoofing MODULE-IDENTITY
                LAST-UPDATED "200701020000Z"
                ORGANIZATION "Radlan - a MARVELL company.
                              Marvell Semiconductor, Inc."
                CONTACT-INFO
                      "www.marvell.com"
                DESCRIPTION
                      "This private MIB module defines ARP spoofing private MIBs."
                REVISION "200701020000Z"
                DESCRIPTION
                      "Initial revision."
        ::= { rnd 60 }

rlArpSpoofingMibVersion OBJECT-TYPE
    SYNTAX  INTEGER
    MAX-ACCESS  read-only
    STATUS  current
    DESCRIPTION
        "MIB's version, the current version is 1."
    ::= { rlArpSpoofing 1 }

rlArpSpoofingTable  OBJECT-TYPE
    SYNTAX  SEQUENCE OF RlArpSpoofingEntry
    MAX-ACCESS  not-accessible
    STATUS  current
    DESCRIPTION
        "A list of the ifIndexes, IP addresses and corresponding MAC addresses."
    ::= { rlArpSpoofing 2 }

rlArpSpoofingEntry OBJECT-TYPE
    SYNTAX  RlArpSpoofingEntry
    MAX-ACCESS  not-accessible
    STATUS  current
    DESCRIPTION
        "An entry of this table specifis ifIndex,IP Address and
         MAC address."
    INDEX  { rlArpSpoofingIfIndex, rlArpSpoofingLocalIpAddr }
    ::= { rlArpSpoofingTable 1 }

RlArpSpoofingEntry ::= SEQUENCE {
    rlArpSpoofingIfIndex        InterfaceIndex,
    rlArpSpoofingLocalIpAddr    IpAddress,
    rlArpSpoofingMacAddr        PhysAddress,
    rlArpSpoofingRemoteIpAddr   IpAddress,
    rlArpSpoofingOutPhysIfIndex InterfaceIndexOrZero,
    rlArpSpoofingStatus         RowStatus
}

rlArpSpoofingIfIndex OBJECT-TYPE
    SYNTAX      InterfaceIndex
    MAX-ACCESS      read-create
    STATUS      current
    DESCRIPTION
        "The physical interface for which this entry contains information."
    ::= { rlArpSpoofingEntry 1 }

rlArpSpoofingLocalIpAddr OBJECT-TYPE
    SYNTAX  IpAddress
    MAX-ACCESS  read-create
    STATUS  current
    DESCRIPTION
        "Ip addres for which the device will send ARP reply (ARP spoofing)."
    ::= { rlArpSpoofingEntry 2 }

rlArpSpoofingMacAddr OBJECT-TYPE
    SYNTAX  PhysAddress
    MAX-ACCESS  read-create
    STATUS  current
    DESCRIPTION
        "MAC addres with which the device will send ARP reply.
        If the field is ommited or its value 0.0.0.0 the device will
        send with the interface's MAC address."
    ::= { rlArpSpoofingEntry 3 }

rlArpSpoofingRemoteIpAddr OBJECT-TYPE
    SYNTAX  IpAddress
    MAX-ACCESS  read-create
    STATUS  current
    DESCRIPTION
        "Ip addres for which the device will send periodically ARP requests
         if its value differs from 0.0.0.0."
    ::= { rlArpSpoofingEntry 4 }

rlArpSpoofingOutPhysIfIndex OBJECT-TYPE
    SYNTAX      InterfaceIndexOrZero
    MAX-ACCESS      read-create
    STATUS      current
    DESCRIPTION
        "The physical interface to which the device will send periodically
         ARP requests if its value differs from 0. If its value is 0 then ARP
         requests will send to all the VLAN's ports."
    DEFVAL { 0 }
    ::= { rlArpSpoofingEntry 5 }

rlArpSpoofingStatus OBJECT-TYPE
    SYNTAX  RowStatus
    MAX-ACCESS  read-create
    STATUS  current
    DESCRIPTION
        "It is used to insert, update or delete an entry"
    ::= { rlArpSpoofingEntry 6 }

END
