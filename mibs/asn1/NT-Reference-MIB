NT-Reference-MIB        DEFINITIONS ::= BEGIN

EXPORTS
	nt, meridian, experimental, modules, common,
	cybele, mobility, callProcessing, iccm;

IMPORTS
	MODULE-IDENTITY, enterprises
		FROM SNMPv2-SMI

	TEXTUAL-CONVENTION
		FROM SNMPv2-TC

	MODULE-COMPLIANCE, OBJECT-GROUP
		FROM SNMPv2-CONF;


nt              OBJECT IDENTIFIER ::= { enterprises 562 }

meridian        OBJECT IDENTIFIER ::= { nt 3 }

experimental    OBJECT IDENTIFIER ::= { meridian 0 }

modules         OBJECT IDENTIFIER ::= { meridian 1 }

common          OBJECT IDENTIFIER ::= { meridian 2 }

smp             OBJECT IDENTIFIER ::= { meridian 3 }

cybele          OBJECT IDENTIFIER ::= { meridian 4 }

mobility        OBJECT IDENTIFIER ::= { meridian 5 }

callProcessing  OBJECT IDENTIFIER ::= { meridian 6 }

iccm            OBJECT IDENTIFIER ::= { meridian 7 }

ngen            OBJECT IDENTIFIER ::= { meridian 8 }

amber           OBJECT IDENTIFIER ::= { meridian 9 }

entityNaming    OBJECT IDENTIFIER ::= { common 0 }

networkID       OBJECT IDENTIFIER ::= { entityNaming 0 }

cybeleNaming    OBJECT IDENTIFIER ::= { entityNaming 1 }

ngenNaming      OBJECT IDENTIFIER ::= { entityNaming 2 }

mailNaming      OBJECT IDENTIFIER ::= { entityNaming 3 }

mobilityNmaing  OBJECT IDENTIFIER ::= { entityNaming 4 }

--maintenanceMIB  MODULE-IDENTITY
--			LAST-UPDATED "9409230000Z"
--			ORGANIZATION "NT MERIDIAN SMP Group"
--			CONTACT-INFO " Prakash Bettadapur
--						Northern Telecom Inc
--						2305 Mission Colleage Blvd
--						Santa Clara, CA 95054-8173
--						U.S.A.
--						Tel     : +1 408-565-7068
--						ESN     : [655] 7068
--						email : "
--			DESCRIPTION     "This MIB specifies the basic
--						maintenance reqmnts."
--			::= { modules 1 }
--
--cybeleMIB       MODULE-IDENTITY
--			LAST-UPDATED "9410030000Z"
--			ORGANIZATION "NT MERIDIAN Cybele Group"
--			CONTACT-INFO " Prakash Bettadapur
--						Northern Telecom Inc
--						2305 Mission Colleage Blvd
--						Santa Clara, CA 95054-8173
--						U.S.A.
--						Tel     : +1 408-565-7068
--						ESN     : [655] 7068
--						email : "
--			DESCRIPTION     "This MIB specifies the objects and
--						notifications emited by a Cybele
--						system."
--			::= { modules 2 }


END
