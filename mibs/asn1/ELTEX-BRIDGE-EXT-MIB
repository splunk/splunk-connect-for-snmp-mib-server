ELTEX-BRIDGE-EXT-MIB DEFINITIONS ::= BEGIN

-- Title:      ELTEX Bridge Extension Private
-- Version:    1.0
-- Date:       20 Nov 2015

IMPORTS
    eltexLtd                                                FROM ELTEX-SMI-ACTUAL
    VlanIndex                                               FROM Q-BRIDGE-MIB
    MODULE-IDENTITY, OBJECT-TYPE                            FROM SNMPv2-SMI
    TruthValue                                              FROM SNMPv2-TC;

eltexBridgeExtMIB MODULE-IDENTITY
    LAST-UPDATED "201511150000Z"    -- 20/11/2015 00:00GMT
    ORGANIZATION "Eltex Enterprise, Ltd."
    CONTACT-INFO
        "www.eltex.nsk.ru"

    DESCRIPTION
        "This MIB module contains Bridge Extension MIB
        definitions for Eltex Networks."

    REVISION     "201511150000Z"    -- 20/11/2015 00:00GMT
    DESCRIPTION
        "The initial version of this MIB module"

    ::= { eltexLtd 35 } 

eltexBridgeExtMIBObjects  OBJECT IDENTIFIER
    ::= { eltexBridgeExtMIB 1 }


END
