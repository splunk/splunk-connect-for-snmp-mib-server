WebGraph-AnalogIn-57643-US-MIB DEFINITIONS ::= BEGIN
----------------------------------------------------------------
-- Revison: 1.29
----------------------------------------------------------------
-- 22.06.2010 	Webio
--		Syntax correction 
----------------------------------------------------------------
-- Revison: 1.28
----------------------------------------------------------------
-- 02.12.2008 	Webio
--		New Graphics java script base parameter 
----------------------------------------------------------------
-- Revison: 1.27
----------------------------------------------------------------
-- 09.11.2006 	Webio
--		DHCP enable 
----------------------------------------------------------------
-- Revison: 1.26
----------------------------------------------------------------
-- 28.06.2006 	New: Community String Trap
--		
----------------------------------------------------------------
-- Revison: 1.25
----------------------------------------------------------------
-- 25.11.2005 	#57643, WebGraph AnalogIn 2x 0..10V
--
----------------------------------------------------------------
-- Revison: 1.24
----------------------------------------------------------------
-- 26.07.2005 	#57643, WebGraph AnalogIn
--		CRON timer function
----------------------------------------------------------------
-- Revison: 1.23
----------------------------------------------------------------
-- 14.07.2005 	#57643, WebGraph AnalogIn
--		FTP functions
----------------------------------------------------------------
-- Revison: 1.22
----------------------------------------------------------------
-- 17.05.2005 	#57643, WebGraph AnalogIn
--		Trap NMS annotations
----------------------------------------------------------------
-- Revison: 1.21
----------------------------------------------------------------
-- 19.04.2005 	#57605, WebGraph Themometer
--		Mail Authentication
----------------------------------------------------------------
-- Revison: 1.20
----------------------------------------------------------------
-- 05.11.2004 	#57606, WebGraph Thermo-Hygrometer
--		New: Syslog
--		     
----------------------------------------------------------------
-- Revison: 1.19
----------------------------------------------------------------
-- 08.09.2004 	#57606 WebGraph Thermo-Hygrometer
--		New: 
--			wtWebGraphThermHygroAlarmRHMin
--			wtWebGraphThermHygroAlarmRHMax
--			wtWebGraphThermHygroAlarmRHHysteresis
--			wtWebGraphThermHygroPortSensorSelect
--			wtWebGraphThermHygroAlarmDeltaTemp		
--			wtWebGraphThermHygroAlarmAHMin		
--			wtWebGraphThermHygroAlarmAHMax		
----------------------------------------------------------------
-- Revison: 1.18
----------------------------------------------------------------
-- 21.07.2004 	#57601/3/4, Webio Anx
--		New: 
--		     Diagnosis
----------------------------------------------------------------
-- Revison: 1.17
----------------------------------------------------------------
-- 28.06.2004 	#57630/1/2, Webio Digital
--		Neu: Puls Mode
----------------------------------------------------------------
-- Revison: 1.16
----------------------------------------------------------------
-- 16.04.2004 	New: #57632, Webio Digital EA24x24
--
--		#57630/1, Webio Digital EA12x12
--		New:
--			wtWebioEA12x12InputCounterClear
----------------------------------------------------------------
-- Revison: 1.15
----------------------------------------------------------------
-- 27.02.2004 	#57630/1, Webio Digital EA12x12
--		New:
--		Length changed to 32 Bit:
--			wtWebioEA12x12InputValue
--			wtWebioEA12x12OutputValue
--			wtWebioEA12x12LoadControlView
--			wtWebioEA12x12LCShutDownView
--			wtWebioEA12x12SetOutput
--			wtWebioEA12x12AlarmInputTrigger
--			wtWebioEA12x12AlarmOutputTrigger
--			wtWebioEA12x12PortOutputSafetyState
----------------------------------------------------------------
-- Revison: 1.14
----------------------------------------------------------------
-- 16.02.2004 	#57630/1, Webio Digital EA12x12
--		New:
--		Text: Location, Contact
--		SNMP: ColdStart, WarmStart, ComunityString Read/RW
--		Alarm: ColdStart / WarmStart trigger
--
-- 	 	#57601, 1xWebThermometer
--		#57603, 2xWebThermometer		
--		#57604, 8xWebThermometer
--		New:
--		Alarm Hysteresis 
--		Alarm Clear Traps and Mails
----------------------------------------------------------------
-- Revison: 1.13
----------------------------------------------------------------
-- 05.02.2004 	#57601, 1xWebThermometer
--		#57603, 2xWebThermometer		
--		#57604, 8xWebThermometer
--		New:
--		Text: Location, Contact
--		SNMP: ColdStart, WarmStart, ComunityString Read/RW
--		Alarm: ColdStart / WarmStart trigger
----------------------------------------------------------------
-- Revison: 1.12
----------------------------------------------------------------
-- 05.11.2003 	#57601, 1xWebThermometer
--		#57603, 2xWebThermometer		
--		#57604, 8xWebThermometer
--		New features:
--		Mail  : Option CSV attachment
--		Port  : Offset calibration
--		Alarm : TCP Client mode		
----------------------------------------------------------------
-- Revison: 1.11
----------------------------------------------------------------
-- 28.10.2003 	#57630/1, Webio Digital EA12x12
--		New features:
--		Alarm : TCP Client mode		
--		Inputs: Puls filter
----------------------------------------------------------------
-- Revison: 1.10
----------------------------------------------------------------
-- 22.07.2003 	#57630, Webio Digital EA12x12
--		New navigation tree, new binary modes		
--
----------------------------------------------------------------
-- Revison: 1.09
----------------------------------------------------------------
-- 24.03.2003 	Trap Enterprise (Type 1, 2) corrected 
----------------------------------------------------------------
-- Revison: 1.08
----------------------------------------------------------------
-- 04.03.2003 	reconciled the language versions DE/US
----------------------------------------------------------------
-- Revison: 1.07
----------------------------------------------------------------
-- 25.02.2003 	Correction: wtWebioEA12x12LoadControl
----------------------------------------------------------------
-- Revison: 1.06
----------------------------------------------------------------
-- 24.02.2003 	New:
--		#57630, Webio EA12x12, LoadControl Group
--		Correction: Trap variable names
----------------------------------------------------------------
-- Revison: 1.05
----------------------------------------------------------------
-- 21.01.2003 	New:
--		#57630, Webio EA12x12
----------------------------------------------------------------
-- Revison: 1.04
----------------------------------------------------------------
-- 02.01.2003 	New:
--		#57601, 1xWebThermometer
--		#57603, 2xWebThermometer, 8 alarms
----------------------------------------------------------------
-- Revison: 1.03
----------------------------------------------------------------
-- 21.11.2002 	New:
--		#57604, 2xWebThermometer, BOOTP, StartupSite
--		#57603, 8xWebThermometer, BOOTP, StartupSite
----------------------------------------------------------------
-- Revison: 1.02
----------------------------------------------------------------
-- 26.07.2002 	New:
--		#57604, 2xWebThermometer
--		#57603, 8xWebThermometer
-- 		


    IMPORTS

    OBJECT-TYPE                                        FROM RFC-1212
    TRAP-TYPE                                          FROM RFC-1215
    DisplayString, PhysAddress                         FROM RFC1213-MIB
    enterprises, TimeTicks, IpAddress, NetworkAddress  FROM RFC1155-SMI;

 
--    IpAddress ::=
--        [APPLICATION 0]
--            IMPLICIT OCTET STRING (SIZE (4))
--    Counter ::=
--        [APPLICATION 1]
--            IMPLICIT INTEGER (0..4294967295)
--    Gauge ::=
--        [APPLICATION 2]
--            IMPLICIT INTEGER (0..4294967295)
--    TimeTicks ::=
--        [APPLICATION 3]
--            IMPLICIT INTEGER (0..4294967295)


--    DisplayString ::= OCTET STRING
--    PhysAddress   ::= OCTET STRING

--    internet         OBJECT IDENTIFIER ::= { iso org(3) dod(6) 1 }
--    privat           OBJECT IDENTIFIER ::= { internet 4 }
--    enterprises      OBJECT IDENTIFIER ::= { privat 1 }



--  Wiesemann & Theis Com-Server MIB

    wut                				OBJECT IDENTIFIER ::= { enterprises 5040 }
    wtComServer        				OBJECT IDENTIFIER ::= { wut 1 }
    wtWebio            				OBJECT IDENTIFIER ::= { wtComServer 2 }

--  wtWebGraph Tree

    wtWebGraphAnalogIn57643  			OBJECT IDENTIFIER ::= { wtWebio 12 }
    	
--  wtWebGraphAnalogIn57643 Tree

    wtWebGraphAnalogIn57643Inventory    	OBJECT IDENTIFIER ::= { wtWebGraphAnalogIn57643 1 }
    wtWebGraphAnalogIn57643SessCntrl 		OBJECT IDENTIFIER ::= { wtWebGraphAnalogIn57643 2 }
    wtWebGraphAnalogIn57643Config    		OBJECT IDENTIFIER ::= { wtWebGraphAnalogIn57643 3 }
    wtWebGraphAnalogIn57643Diag    		OBJECT IDENTIFIER ::= { wtWebGraphAnalogIn57643 4 }
    
--  wtWebGraphAnalogIn57643Config Tree

    wtWebGraphAnalogIn57643Device    		OBJECT IDENTIFIER ::= { wtWebGraphAnalogIn57643Config 1 }
    wtWebGraphAnalogIn57643Ports     		OBJECT IDENTIFIER ::= { wtWebGraphAnalogIn57643Config 2 }	
    wtWebGraphAnalogIn57643Manufact  		OBJECT IDENTIFIER ::= { wtWebGraphAnalogIn57643Config 3 }	

--  wtWebGraphAnalogIn57643Device Tree

    wtWebGraphAnalogIn57643Text			OBJECT IDENTIFIER ::= { wtWebGraphAnalogIn57643Device 1 }	
    wtWebGraphAnalogIn57643TimeDate 		OBJECT IDENTIFIER ::= { wtWebGraphAnalogIn57643Device 2 }
    wtWebGraphAnalogIn57643Basic		OBJECT IDENTIFIER ::= { wtWebGraphAnalogIn57643Device 3 }	
    wtWebGraphAnalogIn57643Datalogger		OBJECT IDENTIFIER ::= { wtWebGraphAnalogIn57643Device 4 }	
    wtWebGraphAnalogIn57643Alarm		OBJECT IDENTIFIER ::= { wtWebGraphAnalogIn57643Device 5 }
    wtWebGraphAnalogIn57643Graphics 		OBJECT IDENTIFIER ::= { wtWebGraphAnalogIn57643Device 6 }	
    
--  wtWebGraphAnalogIn57643TimeDate Tree

    wtWebGraphAnalogIn57643TimeZone		OBJECT IDENTIFIER ::= { wtWebGraphAnalogIn57643TimeDate 1 }
    wtWebGraphAnalogIn57643TimeServer		OBJECT IDENTIFIER ::= { wtWebGraphAnalogIn57643TimeDate 2 }	
    wtWebGraphAnalogIn57643DeviceClock		OBJECT IDENTIFIER ::= { wtWebGraphAnalogIn57643TimeDate 3 }

--  wtWebGraphAnalogIn57643Basic Tree
    
    wtWebGraphAnalogIn57643Network		OBJECT IDENTIFIER ::= { wtWebGraphAnalogIn57643Basic 1 }
    wtWebGraphAnalogIn57643HTTP			OBJECT IDENTIFIER ::= { wtWebGraphAnalogIn57643Basic 2 }
    wtWebGraphAnalogIn57643Mail			OBJECT IDENTIFIER ::= { wtWebGraphAnalogIn57643Basic 3 }	
    wtWebGraphAnalogIn57643SNMP			OBJECT IDENTIFIER ::= { wtWebGraphAnalogIn57643Basic 4 }
    wtWebGraphAnalogIn57643UDP			OBJECT IDENTIFIER ::= { wtWebGraphAnalogIn57643Basic 5 }
    wtWebGraphAnalogIn57643Syslog		OBJECT IDENTIFIER ::= { wtWebGraphAnalogIn57643Basic 6 }
    wtWebGraphAnalogIn57643FTP			OBJECT IDENTIFIER ::= { wtWebGraphAnalogIn57643Basic 7 }

--  wtWebGraphAnalogIn57643Graphics Tree
    
    wtWebGraphAnalogIn57643GraphicsBase 	OBJECT IDENTIFIER ::= { wtWebGraphAnalogIn57643Graphics 1 }
    wtWebGraphAnalogIn57643GraphicsSelect 	OBJECT IDENTIFIER ::= { wtWebGraphAnalogIn57643Graphics 2 }
    wtWebGraphAnalogIn57643GraphicsScale 	OBJECT IDENTIFIER ::= { wtWebGraphAnalogIn57643Graphics 3 }
       
-- wtWebGraphAnalogIn57643Inventory Group
------------------------

wtWebGraphAnalogIn57643Sensors OBJECT-TYPE
    SYNTAX INTEGER (1..2)
    ACCESS read-only
    STATUS mandatory
    DESCRIPTION
        "Number of sensors"
    ::= { wtWebGraphAnalogIn57643Inventory 1 }

-- Interface Table

wtWebGraphAnalogIn57643SensorTable OBJECT-TYPE
    SYNTAX SEQUENCE OF WtWebGraphAnalogIn57643SensorEntry
    ACCESS not-accessible
    STATUS mandatory
    DESCRIPTION
        "List of sensors."
    ::= { wtWebGraphAnalogIn57643Inventory 2 }

wtWebGraphAnalogIn57643SensorEntry OBJECT-TYPE
    SYNTAX WtWebGraphAnalogIn57643SensorEntry
    ACCESS not-accessible
    STATUS mandatory
    DESCRIPTION
        "List of sensor numbers."
    INDEX  { wtWebGraphAnalogIn57643SensorNo }
    ::= { wtWebGraphAnalogIn57643SensorTable 1 }

WtWebGraphAnalogIn57643SensorEntry ::= SEQUENCE {
    wtWebGraphAnalogIn57643SensorNo INTEGER
}

wtWebGraphAnalogIn57643SensorNo OBJECT-TYPE
    SYNTAX INTEGER (1..2)
    ACCESS read-only
    STATUS mandatory
    DESCRIPTION
        "Sensor number."
    ::= { wtWebGraphAnalogIn57643SensorEntry 1 }


-- wtWebGraphAnalogIn57643Values Table

wtWebGraphAnalogIn57643ValuesTable OBJECT-TYPE
    SYNTAX SEQUENCE OF WtWebGraphAnalogIn57643ValuesEntry
    ACCESS not-accessible
    STATUS mandatory
    DESCRIPTION
        "List of measurement values corresponding to the channel numbers."
    ::= { wtWebGraphAnalogIn57643Inventory 3 }

wtWebGraphAnalogIn57643ValuesEntry OBJECT-TYPE
    SYNTAX WtWebGraphAnalogIn57643ValuesEntry
    ACCESS not-accessible
    STATUS mandatory
    DESCRIPTION
        "Measurement values of the sensors."
    INDEX  { wtWebGraphAnalogIn57643SensorNo }
    ::= { wtWebGraphAnalogIn57643ValuesTable 1 }

WtWebGraphAnalogIn57643ValuesEntry ::= SEQUENCE{
    wtWebGraphAnalogIn57643Values OCTET STRING
}

wtWebGraphAnalogIn57643Values OBJECT-TYPE
    SYNTAX OCTET STRING (SIZE (5))
    ACCESS read-only
    STATUS mandatory
    DESCRIPTION
        "Measurement value of the sensor, ASCII, 7 characters in length."
    ::= { wtWebGraphAnalogIn57643ValuesEntry 1 }

-- wtWebGraphAnalogIn57643BinaryValues Table

wtWebGraphAnalogIn57643BinaryValuesTable OBJECT-TYPE
    SYNTAX SEQUENCE OF WtWebGraphAnalogIn57643BinaryValuesEntry
    ACCESS not-accessible
    STATUS mandatory
    DESCRIPTION
        "List of binary measurement values corresponding to the channel numbers."
    ::= { wtWebGraphAnalogIn57643Inventory 4 }

wtWebGraphAnalogIn57643BinaryValuesEntry OBJECT-TYPE
    SYNTAX WtWebGraphAnalogIn57643BinaryValuesEntry
    ACCESS not-accessible
    STATUS mandatory
    DESCRIPTION
        "Binary measurement values of the sensors."
    INDEX  { wtWebGraphAnalogIn57643SensorNo }
    ::= { wtWebGraphAnalogIn57643BinaryValuesTable 1 }

WtWebGraphAnalogIn57643BinaryValuesEntry ::= SEQUENCE{
    wtWebGraphAnalogIn57643BinaryValues INTEGER
}    

wtWebGraphAnalogIn57643BinaryValues OBJECT-TYPE
    SYNTAX INTEGER
    ACCESS read-only
    STATUS mandatory
    DESCRIPTION
        "Binary measurement value of the sensor in 1/10 degrees Celsius or 1/10 per cent,
        signed number, 0x4FFF6 indicates an 
        invalid measured value."
    ::= { wtWebGraphAnalogIn57643BinaryValuesEntry 1 }

-- wtWebGraphAnalogIn57643SessCntrl Group
--------------------------------

wtWebGraphAnalogIn57643SessCntrlPassword OBJECT-TYPE
    SYNTAX OCTET STRING 
    ACCESS read-write
    STATUS mandatory
    DESCRIPTION
        "Entering this password opens a session which is ended by writing a 1 to 
        wtWebGraphAnalogIn57643SessCntrlLogout. When read this variable provides a string of
        length zero."
    ::= { wtWebGraphAnalogIn57643SessCntrl 1 }

wtWebGraphAnalogIn57643SessCntrlConfigMode OBJECT-TYPE
    SYNTAX INTEGER {
    wtWebGraphAnalogIn57643SessCntrl-NoSession(0),
    wtWebGraphAnalogIn57643SessCntrl-Session(1)
    }
    ACCESS read-only
    STATUS mandatory
    DESCRIPTION
        "When the device is in SNMP configuration mode, the value 1 is
        returned, otherwise 0. If the read value is 0 even though the
        password was written, the device is already in config mode and the
        variables can only be read."
    ::= { wtWebGraphAnalogIn57643SessCntrl 2 }

wtWebGraphAnalogIn57643SessCntrlLogout OBJECT-TYPE
    SYNTAX INTEGER 
    ACCESS read-write
    STATUS mandatory
    DESCRIPTION
        "If the device is in configuration mode and the session was opened by
        this SNMP Manager, writing a 1 to this variable will end the session 
        and all parameters are stored.
        Writing a 2 discards all entries again.
        When read this variable provides the value 0."
    ::= { wtWebGraphAnalogIn57643SessCntrl 3 }

wtWebGraphAnalogIn57643SessCntrlAdminPassword OBJECT-TYPE
    SYNTAX OCTET STRING 
    ACCESS read-write
    STATUS mandatory
    DESCRIPTION
        "This password protects access to the variables with administrator rights.
        It can only be changed by the administrator. If no password was assigned,
        the valid password is public."
    ::= { wtWebGraphAnalogIn57643SessCntrl 4 }

wtWebGraphAnalogIn57643SessCntrlConfigPassword OBJECT-TYPE
    SYNTAX OCTET STRING 
    ACCESS read-write
    STATUS mandatory
    DESCRIPTION
        "This password protects access to the variables with configurator rights. It can
        be changed by the administrator and by the configurator. If no password was assigned, 
        the valid password is public. When read this variable provides a null-pointer."
    ::= { wtWebGraphAnalogIn57643SessCntrl 5 }
    

-- wtWebGraphAnalogIn57643Text Group
------------------------

wtWebGraphAnalogIn57643DeviceName OBJECT-TYPE
    SYNTAX OCTET STRING 
    ACCESS read-write
    STATUS mandatory
    DESCRIPTION
        "Name of the Webio, which is user definable."
    ::= { wtWebGraphAnalogIn57643Text 1 }

wtWebGraphAnalogIn57643DeviceText OBJECT-TYPE
    SYNTAX OCTET STRING 
    ACCESS read-write
    STATUS mandatory
    DESCRIPTION
        "Description of the Webio, which is user definable."
    ::= { wtWebGraphAnalogIn57643Text 2 }

wtWebGraphAnalogIn57643DeviceLocation OBJECT-TYPE
    SYNTAX OCTET STRING 
    ACCESS read-write
    STATUS mandatory
    DESCRIPTION
        "Description of the location of the Webio, which is user definable."
    ::= { wtWebGraphAnalogIn57643Text 3 }

wtWebGraphAnalogIn57643DeviceContact OBJECT-TYPE
    SYNTAX OCTET STRING 
    ACCESS read-write
    STATUS mandatory
    DESCRIPTION
        "Contact address of the system operator of the Webio, which is user definable."
    ::= { wtWebGraphAnalogIn57643Text 4 }

-- wtWebGraphAnalogIn57643TimeZone Group
----------------------------

wtWebGraphAnalogIn57643TzOffsetHrs OBJECT-TYPE
    SYNTAX INTEGER 
    ACCESS read-write
    STATUS mandatory
    DESCRIPTION
        "Offset hours for the time zone (winter time) with respect to UTC."
    ::= { wtWebGraphAnalogIn57643TimeZone 1 }

wtWebGraphAnalogIn57643TzOffsetMin OBJECT-TYPE
    SYNTAX INTEGER 
    ACCESS read-write
    STATUS mandatory
    DESCRIPTION
        "Offset minutes for the time zone (winter time) with respect to UTC."
    ::= { wtWebGraphAnalogIn57643TimeZone 2 }

wtWebGraphAnalogIn57643TzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Timezone"
    ::= { wtWebGraphAnalogIn57643TimeZone 3 }    
    
wtWebGraphAnalogIn57643StTzOffsetHrs OBJECT-TYPE
    SYNTAX INTEGER 
    ACCESS read-write
    STATUS mandatory
    DESCRIPTION
        "Offset hours of the time zone (summer time) with respect to UTC."
    ::= { wtWebGraphAnalogIn57643TimeZone 4 }

wtWebGraphAnalogIn57643StTzOffsetMin OBJECT-TYPE
    SYNTAX INTEGER 
    ACCESS read-write
    STATUS mandatory
    DESCRIPTION
        "Offset minutes of the time zone (summer time) with respect to UTC."
    ::= { wtWebGraphAnalogIn57643TimeZone 5 }
    
wtWebGraphAnalogIn57643StTzEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Summertime"
    ::= { wtWebGraphAnalogIn57643TimeZone 6 }       
    
wtWebGraphAnalogIn57643StTzStartMonth OBJECT-TYPE
    SYNTAX INTEGER {
    	wtWebGraphAnalogIn57643StartMonth-January(1),
    	wtWebGraphAnalogIn57643StartMonth-February(2),
    	wtWebGraphAnalogIn57643StartMonth-March(3),
    	wtWebGraphAnalogIn57643StartMonth-April(4),
    	wtWebGraphAnalogIn57643StartMonth-May(5),
    	wtWebGraphAnalogIn57643StartMonth-June(6),
    	wtWebGraphAnalogIn57643StartMonth-July(7),
    	wtWebGraphAnalogIn57643StartMonth-August(8),
    	wtWebGraphAnalogIn57643StartMonth-September(9),
    	wtWebGraphAnalogIn57643StartMonth-October(10),
    	wtWebGraphAnalogIn57643StartMonth-November(11),
    	wtWebGraphAnalogIn57643StartMonth-December(12)
    	}
    	
    ACCESS read-write
    STATUS mandatory
    DESCRIPTION
        "Month in which the change is made from winter time to summer time."
    ::= { wtWebGraphAnalogIn57643TimeZone 7 }

wtWebGraphAnalogIn57643StTzStartMode OBJECT-TYPE
    SYNTAX INTEGER {
    	wtWebGraphAnalogIn57643StartMode-first(1),
    	wtWebGraphAnalogIn57643StartMode-second(2),
    	wtWebGraphAnalogIn57643StartMode-third(3),
    	wtWebGraphAnalogIn57643StartMode-fourth(4),
    	wtWebGraphAnalogIn57643StartMode-last(5)
    	}
    	
    ACCESS read-write
    STATUS mandatory
    DESCRIPTION
        "Mode of the day of the week for which the change is made from winter time to summer time."
    ::= { wtWebGraphAnalogIn57643TimeZone 8 }

wtWebGraphAnalogIn57643StTzStartWday OBJECT-TYPE
    SYNTAX INTEGER {
    	wtWebGraphAnalogIn57643StartWday-Sunday(1),
    	wtWebGraphAnalogIn57643StartWday-Monday(2),
    	wtWebGraphAnalogIn57643StartWday-Tuesday(3),
    	wtWebGraphAnalogIn57643StartWday-Thursday(4),
    	wtWebGraphAnalogIn57643StartWday-Wednesday(5),
    	wtWebGraphAnalogIn57643StartWday-Friday(6),
    	wtWebGraphAnalogIn57643StartWday-Saturday(7)
    	}
    	
    ACCESS read-write
    STATUS mandatory
    DESCRIPTION
        "Day of the week on which the change is made from winter time to summer time"
    ::= { wtWebGraphAnalogIn57643TimeZone 9 }
    
wtWebGraphAnalogIn57643StTzStartHrs OBJECT-TYPE
    SYNTAX INTEGER 
    ACCESS read-write
    STATUS mandatory
    DESCRIPTION
        "Hour in which the time zone is changed from winter to summer time with
        respect to UTC."
    ::= { wtWebGraphAnalogIn57643TimeZone 10 }

wtWebGraphAnalogIn57643StTzStartMin OBJECT-TYPE
    SYNTAX INTEGER 
    ACCESS read-write
    STATUS mandatory
    DESCRIPTION
        "Minute in which the time zone is changed from winter to summer time with
        respect to UTC."
    ::= { wtWebGraphAnalogIn57643TimeZone 11 }
 
wtWebGraphAnalogIn57643StTzStopMonth OBJECT-TYPE
    SYNTAX INTEGER {
    	wtWebGraphAnalogIn57643StopMonth-January(1),
    	wtWebGraphAnalogIn57643StopMonth-February(2),
    	wtWebGraphAnalogIn57643StopMonth-March(3),
    	wtWebGraphAnalogIn57643StopMonth-April(4),
    	wtWebGraphAnalogIn57643StopMonth-May(5),
    	wtWebGraphAnalogIn57643StopMonth-June(6),
    	wtWebGraphAnalogIn57643StopMonth-July(7),
    	wtWebGraphAnalogIn57643StopMonth-August(8),
    	wtWebGraphAnalogIn57643StopMonth-September(9),
    	wtWebGraphAnalogIn57643StopMonth-October(10),
    	wtWebGraphAnalogIn57643StopMonth-November(11),
    	wtWebGraphAnalogIn57643StopMonth-December(12)
    	}
    ACCESS read-write
    STATUS mandatory
    DESCRIPTION
        "Month in which the change is made from summer time to winter time."
   ::= { wtWebGraphAnalogIn57643TimeZone 12 }

wtWebGraphAnalogIn57643StTzStopMode OBJECT-TYPE
    SYNTAX INTEGER {
    	wtWebGraphAnalogIn57643StopMode-first(1),
    	wtWebGraphAnalogIn57643StopMode-second(2),
    	wtWebGraphAnalogIn57643StopMode-third(3),
    	wtWebGraphAnalogIn57643StopMode-fourth(4),
    	wtWebGraphAnalogIn57643StopMode-last(5)
    	}
    ACCESS read-write
    STATUS mandatory
    DESCRIPTION
        "Mode of the week day on which the change is made from summer time to winter time."
    ::= { wtWebGraphAnalogIn57643TimeZone 13 }

wtWebGraphAnalogIn57643StTzStopWday OBJECT-TYPE
    SYNTAX INTEGER {
    	wtWebGraphAnalogIn57643StopWday-Sunday(1),
    	wtWebGraphAnalogIn57643StopWday-Monday(2),
    	wtWebGraphAnalogIn57643StopWday-Tuesday(3),
    	wtWebGraphAnalogIn57643StopWday-Thursday(4),
    	wtWebGraphAnalogIn57643StopWday-Wednesday(5),
    	wtWebGraphAnalogIn57643StopWday-Friday(6),
    	wtWebGraphAnalogIn57643StopWday-Saturday(7)
    	}
    ACCESS read-write
    STATUS mandatory
    DESCRIPTION
        "Day of the week on which the change is made from summer time to winter time."
    ::= { wtWebGraphAnalogIn57643TimeZone 14 }
    
wtWebGraphAnalogIn57643StTzStopHrs OBJECT-TYPE
    SYNTAX INTEGER 
    ACCESS read-write
    STATUS mandatory
    DESCRIPTION
        "Hour at which the time zone is changed from summer to winter time with
        respect to UTC."
    ::= { wtWebGraphAnalogIn57643TimeZone 15 }

wtWebGraphAnalogIn57643StTzStopMin OBJECT-TYPE
    SYNTAX INTEGER 
    ACCESS read-write
    STATUS mandatory
    DESCRIPTION
        "Minute at which the time zone is changed from summer to winter time with
        respect to UTC."
    ::= { wtWebGraphAnalogIn57643TimeZone 16 }

-- wtWebGraphAnalogIn57643TimeServer Group
----------------------------

wtWebGraphAnalogIn57643TimeServer1 OBJECT-TYPE
    SYNTAX OCTET STRING 
    ACCESS read-write
    STATUS mandatory
    DESCRIPTION
        "IP address or name of the 1st time server in ASCII"
    ::= { wtWebGraphAnalogIn57643TimeServer 1 }

wtWebGraphAnalogIn57643TimeServer2 OBJECT-TYPE
    SYNTAX OCTET STRING 
    ACCESS read-write
    STATUS mandatory
    DESCRIPTION
        "IP address or name of the 2nd time server in ASCII"
    ::= { wtWebGraphAnalogIn57643TimeServer 2 }
    
wtWebGraphAnalogIn57643TsEnable OBJECT-TYPE
    SYNTAX OCTET STRING (SIZE(4))
    ACCESS read-write
    STATUS mandatory
    DESCRIPTION
        "Binary coded conditions:
        Octet 1: unused
        Octet 2: unused
        Octet 3: unused
        Octet 4:
        	Bit 1-7: unused
	        Bit 0  : Apply Time Server"
    ::= { wtWebGraphAnalogIn57643TimeServer 3 }
    
wtWebGraphAnalogIn57643TsSyncTime OBJECT-TYPE
    SYNTAX INTEGER 
    ACCESS read-write
    STATUS mandatory
    DESCRIPTION
        "Daily synchronisation time with the time server (hour: 0-23)."
    ::= { wtWebGraphAnalogIn57643TimeServer 4 } 
    
-- wtWebGraphAnalogIn57643DeviceClock Group
----------------------------

wtWebGraphAnalogIn57643ClockHrs OBJECT-TYPE
    SYNTAX INTEGER (0..23)
    ACCESS read-write
    STATUS mandatory
    DESCRIPTION
        "Clock hours taking into account the time zone settings."
    ::= { wtWebGraphAnalogIn57643DeviceClock 1 }

wtWebGraphAnalogIn57643ClockMin OBJECT-TYPE
    SYNTAX INTEGER (0..59)
    ACCESS read-write
    STATUS mandatory
    DESCRIPTION
        "Clock minutes taking into account the time zone settings."
    ::= { wtWebGraphAnalogIn57643DeviceClock 2 }

wtWebGraphAnalogIn57643ClockDay OBJECT-TYPE
    SYNTAX INTEGER (1..31)
    ACCESS read-write
    STATUS mandatory
    DESCRIPTION
        "Date: Day of the month, taking into account the time zone settings."
    ::= { wtWebGraphAnalogIn57643DeviceClock 3 }

wtWebGraphAnalogIn57643ClockMonth OBJECT-TYPE
   SYNTAX INTEGER {
    	wtWebGraphAnalogIn57643ClockMonth-January(1),
    	wtWebGraphAnalogIn57643ClockMonth-February(2),
    	wtWebGraphAnalogIn57643ClockMonth-March(3),
    	wtWebGraphAnalogIn57643ClockMonth-April(4),
    	wtWebGraphAnalogIn57643ClockMonth-May(5),
    	wtWebGraphAnalogIn57643ClockMonth-June(6),
    	wtWebGraphAnalogIn57643ClockMonth-July(7),
    	wtWebGraphAnalogIn57643ClockMonth-August(8),
    	wtWebGraphAnalogIn57643ClockMonth-September(9),
    	wtWebGraphAnalogIn57643ClockMonth-October(10),
    	wtWebGraphAnalogIn57643ClockMonth-November(11),
    	wtWebGraphAnalogIn57643ClockMonth-December(12)
    	}
    ACCESS read-write
    STATUS mandatory
    DESCRIPTION
        "Date: Month, taking into account the time zone settings."
    ::= { wtWebGraphAnalogIn57643DeviceClock 4 }

wtWebGraphAnalogIn57643ClockYear OBJECT-TYPE
    SYNTAX INTEGER (0..65535)
    ACCESS read-write
    STATUS mandatory
    DESCRIPTION
        "Date: Year, taking into account the time zone settings."
    ::= { wtWebGraphAnalogIn57643DeviceClock 5 }
    

-- wtWebGraphAnalogIn57643Network Group
------------------------

wtWebGraphAnalogIn57643IpAddress OBJECT-TYPE
    SYNTAX IpAddress
    ACCESS read-write
    STATUS mandatory
    DESCRIPTION
        "IP address of the Webio"
    ::= { wtWebGraphAnalogIn57643Network 1 }

wtWebGraphAnalogIn57643SubnetMask OBJECT-TYPE
    SYNTAX IpAddress
    ACCESS read-write
    STATUS mandatory
    DESCRIPTION
        "Subnet mask of the Webio"
    ::= { wtWebGraphAnalogIn57643Network 2 }

wtWebGraphAnalogIn57643Gateway OBJECT-TYPE
    SYNTAX IpAddress
    ACCESS read-write
    STATUS mandatory
    DESCRIPTION
        "Gateway of the Webio"
    ::= { wtWebGraphAnalogIn57643Network 3 }

wtWebGraphAnalogIn57643DnsServer1 OBJECT-TYPE
    SYNTAX OCTET STRING 
    ACCESS read-write
    STATUS mandatory
    DESCRIPTION
        "IP address of the 1st DNS server in ASCII"
    ::= { wtWebGraphAnalogIn57643Network 4 }

wtWebGraphAnalogIn57643DnsServer2 OBJECT-TYPE
    SYNTAX OCTET STRING 
    ACCESS read-write
    STATUS mandatory
    DESCRIPTION
        "IP address of the 2nd DNS server in ASCII"
    ::= { wtWebGraphAnalogIn57643Network 5 }

wtWebGraphAnalogIn57643AddConfig OBJECT-TYPE
    SYNTAX OCTET STRING 
    ACCESS read-write
    STATUS mandatory
    DESCRIPTION
        "Additional configuration (1=ON):
        Octet 1: unused
        Octet 2: unused
        Octet 3: unused
        Octet 4:
	        Bit 1: DHCP disable
	        Bit 0: BOOTP disable
	        "
    ::= { wtWebGraphAnalogIn57643Network 6 }

--  wtWebGraphAnalogIn57643HTTP Group
--------------------------------

wtWebGraphAnalogIn57643Startup OBJECT-TYPE
    SYNTAX OCTET STRING 
    ACCESS read-write
    STATUS mandatory
    DESCRIPTION
        "Binary coded start page:
        Octet 1: unused
        Octet 2: unused
        Octet 3: unused
        Octet 4:
	        Bit 1: Index.htm
	        Bit 2: Home.htm
	        Bit 3: User.htm
	Only one page may be selected at a time."
    ::= { wtWebGraphAnalogIn57643HTTP 1 }

wtWebGraphAnalogIn57643GetHeaderEnable OBJECT-TYPE
    SYNTAX OCTET STRING 
    ACCESS read-write
    STATUS mandatory
    DESCRIPTION
        "If these bits are set, every answer of a short form GET question will be lead
        by the IP-address and name of the device and/or a HTTP header:
        Octet 1: unused
        Octet 2: unused
        Octet 3: unused
        Octet 4:
        	Bit 1-6: unused
        	Bit 1  : GET HTTP enable
                Bit 0  : GET Header enable"
    ::= { wtWebGraphAnalogIn57643HTTP 2 }  
    
wtWebGraphAnalogIn57643HttpPort OBJECT-TYPE
    SYNTAX INTEGER (1..65535)
    ACCESS read-write
    STATUS mandatory
    DESCRIPTION
        "Definition of the standard HTML port (Default: 80)."
    ::= { wtWebGraphAnalogIn57643HTTP 3 }    


-- wtWebGraphAnalogIn57643Mail Group
--------------------------------

wtWebGraphAnalogIn57643MailAdName OBJECT-TYPE
    SYNTAX OCTET STRING 
    ACCESS read-write
    STATUS mandatory
    DESCRIPTION
        "Device name for mail administration."
    ::= { wtWebGraphAnalogIn57643Mail 1 }
    
wtWebGraphAnalogIn57643MailReply OBJECT-TYPE
    SYNTAX OCTET STRING 
    ACCESS read-write
    STATUS mandatory
    DESCRIPTION
        "Reply address for the mail server."
    ::= { wtWebGraphAnalogIn57643Mail 2 }
    
wtWebGraphAnalogIn57643MailServer OBJECT-TYPE
    SYNTAX OCTET STRING 
    ACCESS read-write
    STATUS mandatory
    DESCRIPTION
        "Name or IP address of the mail server."
    ::= { wtWebGraphAnalogIn57643Mail 3 }
    
wtWebioAn1MailEnable OBJECT-TYPE
    SYNTAX OCTET STRING 
    ACCESS read-write
    STATUS mandatory
    DESCRIPTION
        "Set this bit to enable the sending of mails:
        Octet 1: unused
        Octet 2: unused
        Octet 3: unused
        Octet 4:
        	Bit 1-7: unused
                Bit 0  : Mail enable"
    ::= { wtWebGraphAnalogIn57643Mail 4 }
    
wtWebGraphAnalogIn57643MailAuthentication OBJECT-TYPE
    SYNTAX OCTET STRING (SIZE (4))
    ACCESS read-write
    STATUS mandatory
    DESCRIPTION
        "Selection of the authentication modi:
        The OCTETS are interpreted bit-by-bit, with each bit corresponding to an output. 
        Bit 0 corresponds to the LSB.
        OCTET 1: unused
        OCTET 2: unused
        OCTET 3: unused
        OCTET 4: Bit 3-7: unused
        	 Bit 2  : POP3 before SMTP
        	 Bit 1  : ESMTP, authentication
        	 Bit 0  : SMTP, no authentication"
    ::= { wtWebGraphAnalogIn57643Mail 5 }
    
wtWebGraphAnalogIn57643MailAuthUser OBJECT-TYPE
    SYNTAX OCTET STRING 
    ACCESS read-write
    STATUS mandatory
    DESCRIPTION
        "Name of the user to be authenticated."
    ::= { wtWebGraphAnalogIn57643Mail 6 }    
    
wtWebGraphAnalogIn57643MailAuthPassword OBJECT-TYPE
    SYNTAX OCTET STRING 
    ACCESS read-write
    STATUS mandatory
    DESCRIPTION
        "Authentication password."
    ::= { wtWebGraphAnalogIn57643Mail 7 }    
    
wtWebGraphAnalogIn57643MailPop3Server OBJECT-TYPE
    SYNTAX OCTET STRING 
    ACCESS read-write
    STATUS mandatory
    DESCRIPTION
        "Name or Ip-address of the POP3 Servers."
    ::= { wtWebGraphAnalogIn57643Mail 8 }            

-- wtWebGraphAnalogIn57643SNMP Group
--------------------------------

wtWebGraphAnalogIn57643SnmpCommunityStringRead OBJECT-TYPE
    SYNTAX OCTET STRING
    ACCESS read-write
    STATUS mandatory
    DESCRIPTION
        "Community string read only"
    ::= { wtWebGraphAnalogIn57643SNMP 1 }

wtWebGraphAnalogIn57643SnmpCommunityStringReadWrite OBJECT-TYPE
    SYNTAX OCTET STRING
    ACCESS read-write
    STATUS mandatory
    DESCRIPTION
        "Community string read / write"
    ::= { wtWebGraphAnalogIn57643SNMP 2 }

wtWebGraphAnalogIn57643SystemTrapManagerIP OBJECT-TYPE
    SYNTAX OCTET STRING 
    ACCESS read-write
    STATUS mandatory
    DESCRIPTION
        "Name or IP address of the TCP server which accepts the system trap."
    ::= { wtWebGraphAnalogIn57643SNMP 3 }
    
wtWebGraphAnalogIn57643SystemTrapEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2-7: unused"
    ::= { wtWebGraphAnalogIn57643SNMP 4 }
    
wtWebGraphAnalogIn57643SnmpEnable OBJECT-TYPE
    SYNTAX OCTET STRING 
    ACCESS read-write
    STATUS mandatory
    DESCRIPTION
        "Set bit 0 to enable SNMP.
        If disabled, the device did not respond to any SNMP requests.
        Bit 1 decided wether the community string of read operations 
        is compared with the system password or not:
        Octet 1: unused
        Octet 2: unused
        Octet 3: unused
        Octet 4:
        	Bit 1-7: unused
        	Bit 0  : SNMP enable"
    ::= { wtWebGraphAnalogIn57643SNMP 5 }
    
wtWebGraphAnalogIn57643SnmpCommunityStringTrap OBJECT-TYPE
    SYNTAX OCTET STRING
    ACCESS read-write
    STATUS mandatory
    DESCRIPTION
        "Community string send within traps."
    ::= { wtWebGraphAnalogIn57643SNMP 6 }    
        
    
    
-- wtWebGraphAnalogIn57643UDP Group
--------------------------------
    
wtWebGraphAnalogIn57643UdpPort OBJECT-TYPE
    SYNTAX INTEGER (1..65535)
    ACCESS read-write
    STATUS mandatory
    DESCRIPTION
        "Udp port to which the Udp queries ( short form GET requests) can be sent. This
        port number must be unique within the device."
    ::= { wtWebGraphAnalogIn57643UDP 1 }
    
wtWebGraphAnalogIn57643UdpEnable OBJECT-TYPE
    SYNTAX OCTET STRING 
    ACCESS read-write
    STATUS mandatory
    DESCRIPTION
        "Set this bit to enable UDP support:
        Octet 1: unused
        Octet 2: unused
        Octet 3: unused
        Octet 4:
        	Bit 1-7: unused
                Bit 0  : UDP enable"
    ::= { wtWebGraphAnalogIn57643UDP 2 }
    
--  wtWebGraphAnalogIn57643Syslog Group
--------------------------------
    
wtWebGraphAnalogIn57643SyslogServerIP OBJECT-TYPE
    SYNTAX OCTET STRING 
    ACCESS read-write
    STATUS mandatory
    DESCRIPTION
        "Name or IP address of the Syslog server, which accepts the Syslog messgaes."
    ::= { wtWebGraphAnalogIn57643Syslog 1 }
    
wtWebGraphAnalogIn57643SyslogServerPort OBJECT-TYPE
    SYNTAX INTEGER
    ACCESS read-write
    STATUS mandatory
    DESCRIPTION
        "Portnumber of the Syslog servers, default 514."
    ::= { wtWebGraphAnalogIn57643Syslog 2 }

wtWebGraphAnalogIn57643SyslogSystemMessagesEnable OBJECT-TYPE
    SYNTAX OCTET STRING (SIZE(4))
    ACCESS read-write
    STATUS mandatory
    DESCRIPTION
        "Binary coded trigger conditions:
        Octet 1: unused
        Octet 2: unused
        Octet 3: unused
        Octet 4:
	        Bit 0:   ColdStart
	        Bit 1:   WarmStart
	        Bit 2:   Diag Messages
	        Bit 3-7: unused"
    ::= { wtWebGraphAnalogIn57643Syslog 3 }    

wtWebGraphAnalogIn57643SyslogEnable OBJECT-TYPE
    SYNTAX OCTET STRING 
    ACCESS read-write
    STATUS mandatory
    DESCRIPTION
        "Set bit 0to enable Syslog:
        Octet 1: unused
        Octet 2: unused
        Octet 3: unused
        Octet 4:
        	Bit 1-7: unused
                Bit 0  : Syslog enable"
    ::= { wtWebGraphAnalogIn57643Syslog 4 }
    
--  wtWebGraphAnalogIn57643FTP Group
--------------------------------

wtWebGraphAnalogIn57643FTPServerIP OBJECT-TYPE
    SYNTAX OCTET STRING 
    ACCESS read-write
    STATUS mandatory
    DESCRIPTION
        "Name or IP address of the FTP server, which accepts the FTP messages."
    ::= { wtWebGraphAnalogIn57643FTP 1 }
    
wtWebGraphAnalogIn57643FTPServerControlPort OBJECT-TYPE
    SYNTAX INTEGER
    ACCESS read-write
    STATUS mandatory
    DESCRIPTION
        "Portnumber of the control port of the FTP server, default 21."
    ::= { wtWebGraphAnalogIn57643FTP 2 }
    
wtWebGraphAnalogIn57643FTPUserName OBJECT-TYPE
    SYNTAX OCTET STRING 
    ACCESS read-write
    STATUS mandatory
    DESCRIPTION
        "FTP Loggin: user name."
    ::= { wtWebGraphAnalogIn57643FTP 3 }
    
wtWebGraphAnalogIn57643FTPPassword OBJECT-TYPE
    SYNTAX OCTET STRING 
    ACCESS read-write
    STATUS mandatory
    DESCRIPTION
        "FTP Loggin: user password."
    ::= { wtWebGraphAnalogIn57643FTP 4 }

wtWebGraphAnalogIn57643FTPAccount OBJECT-TYPE
    SYNTAX OCTET STRING 
    ACCESS read-write
    STATUS mandatory
    DESCRIPTION
        "FTP Loggin: name of account."
    ::= { wtWebGraphAnalogIn57643FTP 5 }

wtWebGraphAnalogIn57643FTPOption OBJECT-TYPE
    SYNTAX OCTET STRING 
    ACCESS read-write
    STATUS mandatory
    DESCRIPTION
        "Bit 0 switches the FTP Server in Passiv-Mode,
        the Client controls the data connection on its own:
        Octet 1: unused
        Octet 2: unused
        Octet 3: unused
        Octet 4:
        	Bit 1-7: unused
                Bit 0  : PASV enable"
    ::= { wtWebGraphAnalogIn57643FTP 6 }
    
wtWebGraphAnalogIn57643FTPEnable OBJECT-TYPE
    SYNTAX OCTET STRING 
    ACCESS read-write
    STATUS mandatory
    DESCRIPTION
        "Set Bit 0 to enable FTP:
        Octet 1: unused
        Octet 2: unused
        Octet 3: unused
        Octet 4:
        	Bit 1-7: unused
                Bit 0  : FTP enable"
    ::= { wtWebGraphAnalogIn57643FTP 7 }    
    
-- wtWebGraphAnalogIn57643Datalogger Group
--------------------------------

wtWebGraphAnalogIn57643LoggerTimebase OBJECT-TYPE
    SYNTAX INTEGER {
    wtWebGraphAnalogIn57643Datalogger-1Min(1),
    wtWebGraphAnalogIn57643Datalogger-5Min(2),
    wtWebGraphAnalogIn57643Datalogger-15Min(3),
    wtWebGraphAnalogIn57643Datalogger-60Min(4)
    }
    ACCESS read-write
    STATUS mandatory
    DESCRIPTION
        "Time base of the data logger"
    ::= { wtWebGraphAnalogIn57643Datalogger 1 }

wtWebGraphAnalogIn57643LoggerSensorSel OBJECT-TYPE
    SYNTAX OCTET STRING (SIZE(4))
    ACCESS read-write
    STATUS mandatory
    DESCRIPTION
        "Binary coded trigger conditions:
        Octet 1: unused
        Octet 2: unused
        Octet 3: unused
        Octet 4:
        	Bit 0: Sensor 1
        	Bit 1: Sensor 2
        	Bit 2-7: unused"
    ::= { wtWebGraphAnalogIn57643Datalogger 2 }

wtWebGraphAnalogIn57643DisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2-7: unused"
    ::= { wtWebGraphAnalogIn57643Datalogger 3 }    
    
-- Graph Sensor Color Table

wtWebGraphAnalogIn57643SensorColorTable OBJECT-TYPE
    SYNTAX SEQUENCE OF WtWebGraphAnalogIn57643SensorColorEntry
    ACCESS not-accessible
    STATUS mandatory
    DESCRIPTION
        "List of sensor colors for the praphical presentation."
    ::= { wtWebGraphAnalogIn57643Datalogger 4 }

wtWebGraphAnalogIn57643SensorColorEntry OBJECT-TYPE
    SYNTAX WtWebGraphAnalogIn57643SensorColorEntry
    ACCESS not-accessible
    STATUS mandatory
    DESCRIPTION
        "Index numbers of the sensors."
    INDEX  { wtWebGraphAnalogIn57643SensorNo }
    ::= { wtWebGraphAnalogIn57643SensorColorTable 1 }

WtWebGraphAnalogIn57643SensorColorEntry ::= SEQUENCE {
    wtWebGraphAnalogIn57643SensorColor OCTET STRING
}

wtWebGraphAnalogIn57643SensorColor OBJECT-TYPE
    SYNTAX OCTET STRING (SIZE(3))
    ACCESS read-write
    STATUS mandatory
    DESCRIPTION
        "Color of the sensors at the praphical presention."
    ::= { wtWebGraphAnalogIn57643SensorColorEntry 1 }
    
wtWebGraphAnalogIn57643AutoScaleEnable OBJECT-TYPE
    SYNTAX OCTET STRING 
    ACCESS read-write
    STATUS mandatory
    DESCRIPTION
        "If bit 0 is set, vertical auto scale is enabled:
        Octet 1: unused
        Octet 2: unused
        Octet 3: unused
        Octet 4:
        	Bit 1-7: unused
                Bit 0  : Auto Scale enable"
    ::= { wtWebGraphAnalogIn57643Datalogger 5 }
    
wtWebGraphAnalogIn57643VerticalUpperLimit OBJECT-TYPE
    SYNTAX OCTET STRING 
    ACCESS read-write
    STATUS mandatory
    DESCRIPTION
        "This value defines the maximum temperature shown in the graphical presentation,
        if no auto scaling is selected.
        Temperature in degrees with maximum 2 decimal places."
    ::= { wtWebGraphAnalogIn57643Datalogger 6 }

wtWebGraphAnalogIn57643VerticalLowerLimit OBJECT-TYPE
    SYNTAX OCTET STRING 
    ACCESS read-write
    STATUS mandatory
    DESCRIPTION
        "This value defines the minimum temperature shown in the graphical presentation,
        if no auto scaling is selected.
        Temperature in degrees with maximum 2 decimal places."
    ::= { wtWebGraphAnalogIn57643Datalogger 7 }
    
wtWebGraphAnalogIn57643HorizontalZoom OBJECT-TYPE
    SYNTAX INTEGER {
    wtWebGraphAnalogIn57643Zoom-25min(1),
    wtWebGraphAnalogIn57643Zoom-75min(2),
    wtWebGraphAnalogIn57643Zoom-5hrs(3),
    wtWebGraphAnalogIn57643Zoom-30hrs(4),
    wtWebGraphAnalogIn57643Zoom-5days(5),
    wtWebGraphAnalogIn57643Zoom-25days(6)
    }
    ACCESS read-write
    STATUS mandatory
    DESCRIPTION
        "Defines the default zoom stage, if no auto scaling is selected."
    ::= { wtWebGraphAnalogIn57643Datalogger 8 }    

-- wtWebGraphAnalogIn57643Alarm Group
----------------------------

wtWebGraphAnalogIn57643AlarmCount OBJECT-TYPE
    SYNTAX INTEGER (1..8)
    ACCESS read-only
    STATUS mandatory
    DESCRIPTION
        "Number of independent alarms."
    ::= { wtWebGraphAnalogIn57643Alarm 1 }
    
-- Alarm Interface Table

wtWebGraphAnalogIn57643AlarmIfTable OBJECT-TYPE
    SYNTAX SEQUENCE OF WtWebGraphAnalogIn57643AlarmIfEntry
    ACCESS not-accessible
    STATUS mandatory
    DESCRIPTION
        "List of alarm indices."
    ::= { wtWebGraphAnalogIn57643Alarm 2 }

wtWebGraphAnalogIn57643AlarmIfEntry OBJECT-TYPE
    SYNTAX WtWebGraphAnalogIn57643AlarmIfEntry
    ACCESS not-accessible
    STATUS mandatory
    DESCRIPTION
        "Numbers of the alarms."
    INDEX  { wtWebGraphAnalogIn57643AlarmNo }
    ::= { wtWebGraphAnalogIn57643AlarmIfTable 1 }

WtWebGraphAnalogIn57643AlarmIfEntry ::= SEQUENCE {
    wtWebGraphAnalogIn57643AlarmNo INTEGER
}

wtWebGraphAnalogIn57643AlarmNo OBJECT-TYPE
    SYNTAX INTEGER (1..8)
    ACCESS read-only
    STATUS mandatory
    DESCRIPTION
        "Alarm number."
    ::= { wtWebGraphAnalogIn57643AlarmIfEntry 1 }

-- Alarm Table

wtWebGraphAnalogIn57643AlarmTable OBJECT-TYPE
    SYNTAX SEQUENCE OF WtWebGraphAnalogIn57643AlarmEntry
    ACCESS not-accessible
    STATUS mandatory
    DESCRIPTION
        "List of settings depending on the alarm number."
    ::= { wtWebGraphAnalogIn57643Alarm 3 }

wtWebGraphAnalogIn57643AlarmEntry OBJECT-TYPE
    SYNTAX WtWebGraphAnalogIn57643AlarmEntry
    ACCESS not-accessible
    STATUS mandatory
    DESCRIPTION
        "Alarm parameters of the individual alarms."
    INDEX  { wtWebGraphAnalogIn57643AlarmNo }
    ::= { wtWebGraphAnalogIn57643AlarmTable 1 }

WtWebGraphAnalogIn57643AlarmEntry ::= SEQUENCE {
    wtWebGraphAnalogIn57643AlarmTrigger			OCTET STRING,
    wtWebGraphAnalogIn57643AlarmMin			OCTET STRING,
    wtWebGraphAnalogIn57643AlarmMax			OCTET STRING,
    wtWebGraphAnalogIn57643AlarmHysteresis		OCTET STRING,
    wtWebGraphAnalogIn57643AlarmDelay			OCTET STRING,
    wtWebGraphAnalogIn57643AlarmInterval		OCTET STRING,
    wtWebGraphAnalogIn57643AlarmEnable			OCTET STRING,
    wtWebGraphAnalogIn57643AlarmEMailAddr		OCTET STRING,
    wtWebGraphAnalogIn57643AlarmMailSubject		OCTET STRING,
    wtWebGraphAnalogIn57643AlarmMailText		OCTET STRING,
    wtWebGraphAnalogIn57643AlarmManagerIP		OCTET STRING,
    wtWebGraphAnalogIn57643AlarmTrapText		OCTET STRING,
    wtWebGraphAnalogIn57643AlarmMailOptions		OCTET STRING,
    wtWebGraphAnalogIn57643AlarmTcpIpAddr		OCTET STRING,
    wtWebGraphAnalogIn57643AlarmTcpPort			INTEGER,
    wtWebGraphAnalogIn57643AlarmTcpText			OCTET STRING,
    wtWebGraphAnalogIn57643AlarmClearMailSubject	OCTET STRING,
    wtWebGraphAnalogIn57643AlarmClearMailText		OCTET STRING,
    wtWebGraphAnalogIn57643AlarmClearTrapText		OCTET STRING,
    wtWebGraphAnalogIn57643AlarmClearTcpText		OCTET STRING,
    wtWebGraphAnalogIn57643Alarm2Min			OCTET STRING,
    wtWebGraphAnalogIn57643Alarm2Max			OCTET STRING,
    wtWebGraphAnalogIn57643Alarm2Hysteresis		OCTET STRING,
    wtWebGraphAnalogIn57643AlarmSyslogIpAddr		OCTET STRING,
    wtWebGraphAnalogIn57643AlarmSyslogPort		INTEGER,
    wtWebGraphAnalogIn57643AlarmSyslogText		OCTET STRING,
    wtWebGraphAnalogIn57643AlarmSyslogClearText		OCTET STRING,
    wtWebGraphAnalogIn57643AlarmFtpDataPort		OCTET STRING,
    wtWebGraphAnalogIn57643AlarmFtpFileName		OCTET STRING,
    wtWebGraphAnalogIn57643AlarmFtpText			OCTET STRING,
    wtWebGraphAnalogIn57643AlarmFtpClearText		OCTET STRING,
    wtWebGraphAnalogIn57643AlarmFtpOption		OCTET STRING,
    wtWebGraphAnalogIn57643AlarmTimerCron		OCTET STRING

}

wtWebGraphAnalogIn57643AlarmTrigger OBJECT-TYPE
    SYNTAX OCTET STRING (SIZE(4))
    ACCESS read-write
    STATUS mandatory
    DESCRIPTION
        "Binary coded trigger conditions:
        Octet 1: unused
        Octet 2: unused
        Octet 3:
        	Bit 0: Timer
        	Bit 1: ColdStart
        	Bit 2: WarmStart
        	
        Octet 4:
        	Bit 0: Sensor 1
        	Bit 1: Sensor 2
        	Bit 2-7: unused"
    ::= { wtWebGraphAnalogIn57643AlarmEntry 1 }

wtWebGraphAnalogIn57643AlarmMin OBJECT-TYPE
    SYNTAX OCTET STRING 
    ACCESS read-write
    STATUS mandatory
    DESCRIPTION
        "Minimum temperature in degrees with maximum 2 decimal places."
    ::= { wtWebGraphAnalogIn57643AlarmEntry 2 }

wtWebGraphAnalogIn57643AlarmMax OBJECT-TYPE
    SYNTAX OCTET STRING 
    ACCESS read-write
    STATUS mandatory
    DESCRIPTION
        "Maximum temperature in degrees with maximum 2 decimal places."
    ::= { wtWebGraphAnalogIn57643AlarmEntry 3 }
    
wtWebGraphAnalogIn57643AlarmHysteresis OBJECT-TYPE
    SYNTAX OCTET STRING 
    ACCESS read-write
    STATUS mandatory
    DESCRIPTION
        "Temperature changes of this size clears the alarm state (MAX-hyst, MIN+hyst.)
        , in degrees with maximum 2 decimal places."
    ::= { wtWebGraphAnalogIn57643AlarmEntry 4 }

wtWebGraphAnalogIn57643AlarmDelay OBJECT-TYPE
    SYNTAX OCTET STRING 
    ACCESS read-write
    STATUS mandatory
    DESCRIPTION
        "Alarm will be delayed by setting this time while stable alarm 
        condition occur (time in minutes)."
    ::= { wtWebGraphAnalogIn57643AlarmEntry 5 }
        

wtWebGraphAnalogIn57643AlarmInterval OBJECT-TYPE
    SYNTAX OCTET STRING 
    ACCESS read-write
    STATUS mandatory
    DESCRIPTION
        "Send interval for alarm messages."
    ::= { wtWebGraphAnalogIn57643AlarmEntry 6 }

wtWebGraphAnalogIn57643AlarmEnable OBJECT-TYPE
    SYNTAX OCTET STRING (SIZE(4))
    ACCESS read-write
    STATUS mandatory
    DESCRIPTION
        "Binary coded alarm enable:
        Octet 1: unused
        Octet 2: unused
        Octet 3: unused
        Octet 4:
		Bit 0:	Mail Enable
        	Bit 1:	SNMP Trap enable
        	Bit 2:  TCP Client enable"
    ::= { wtWebGraphAnalogIn57643AlarmEntry 7 }

wtWebGraphAnalogIn57643AlarmEMailAddr OBJECT-TYPE
    SYNTAX OCTET STRING 
    ACCESS read-write
    STATUS mandatory
    DESCRIPTION
        "E-Mail address for sending the alarm mail to."
    ::= { wtWebGraphAnalogIn57643AlarmEntry 8 }

wtWebGraphAnalogIn57643AlarmMailSubject OBJECT-TYPE
    SYNTAX OCTET STRING 
    ACCESS read-write
    STATUS mandatory
    DESCRIPTION
        "Subject line for alarm mail."
    ::= { wtWebGraphAnalogIn57643AlarmEntry 9 }

wtWebGraphAnalogIn57643AlarmMailText OBJECT-TYPE
    SYNTAX OCTET STRING 
    ACCESS read-write
    STATUS mandatory
    DESCRIPTION
        "Alarm mail text: <Tn> provides the current temperature; n = 1..8.
        <Z> provides the current time."
    ::= { wtWebGraphAnalogIn57643AlarmEntry 10 }

wtWebGraphAnalogIn57643AlarmManagerIP OBJECT-TYPE
    SYNTAX OCTET STRING 
    ACCESS read-write
    STATUS mandatory
    DESCRIPTION
        "Name or IP address of the SNMP Manager which accepts the trap."
    ::= { wtWebGraphAnalogIn57643AlarmEntry 11 }

wtWebGraphAnalogIn57643AlarmTrapText OBJECT-TYPE
    SYNTAX OCTET STRING 
    ACCESS read-write
    STATUS mandatory
    DESCRIPTION
        "This text is sent in the trap body."
    ::= { wtWebGraphAnalogIn57643AlarmEntry 12 }
    
wtWebGraphAnalogIn57643AlarmMailOptions OBJECT-TYPE
    SYNTAX OCTET STRING (SIZE(4))
    ACCESS read-write
    STATUS mandatory
    DESCRIPTION
        "Binary coded options:
        Octet 1: unused
        Octet 2: unused
        Octet 3: unused
        Octet 4:
		Bit 0  :	Attach Thermo.csv Enable
		Bit 1  :	CSV-Data_since_last_report
        	Bit 2-7:	unused"
    ::= { wtWebGraphAnalogIn57643AlarmEntry 13 }    
    
wtWebGraphAnalogIn57643AlarmTcpIpAddr OBJECT-TYPE
    SYNTAX OCTET STRING 
    ACCESS read-write
    STATUS mandatory
    DESCRIPTION
        "Name or IP address of the TCP server which accepts the trap."
    ::= { wtWebGraphAnalogIn57643AlarmEntry 14 }    

wtWebGraphAnalogIn57643AlarmTcpPort OBJECT-TYPE
    SYNTAX INTEGER (1..65535) 
    ACCESS read-write
    STATUS mandatory
    DESCRIPTION
        "Port number of the TCP server which accepts the trap."
    ::= { wtWebGraphAnalogIn57643AlarmEntry 15 }    

wtWebGraphAnalogIn57643AlarmTcpText OBJECT-TYPE
    SYNTAX OCTET STRING 
    ACCESS read-write
    STATUS mandatory
    DESCRIPTION
        "This text is sent in the TCP trap body."
    ::= { wtWebGraphAnalogIn57643AlarmEntry 16 }

wtWebGraphAnalogIn57643AlarmClearMailSubject OBJECT-TYPE
    SYNTAX OCTET STRING 
    ACCESS read-write
    STATUS mandatory
    DESCRIPTION
        "Subject line for alarm clear mail."
    ::= { wtWebGraphAnalogIn57643AlarmEntry 17 }

wtWebGraphAnalogIn57643AlarmClearMailText OBJECT-TYPE
    SYNTAX OCTET STRING 
    ACCESS read-write
    STATUS mandatory
    DESCRIPTION
        "Alarm clear mail text: <Tn> provides the current temperature; n = 1..8.
        <Z> provides the current time."
    ::= { wtWebGraphAnalogIn57643AlarmEntry 18 }

wtWebGraphAnalogIn57643AlarmClearTrapText OBJECT-TYPE
    SYNTAX OCTET STRING 
    ACCESS read-write
    STATUS mandatory
    DESCRIPTION
        "This text is sent in the trap body."
    ::= { wtWebGraphAnalogIn57643AlarmEntry 19 }

wtWebGraphAnalogIn57643AlarmClearTcpText OBJECT-TYPE
    SYNTAX OCTET STRING 
    ACCESS read-write
    STATUS mandatory
    DESCRIPTION
        "This text is sent in the TCP trap body."
    ::= { wtWebGraphAnalogIn57643AlarmEntry 20 }
    
wtWebGraphAnalogIn57643Alarm2Min OBJECT-TYPE
    SYNTAX OCTET STRING 
    ACCESS read-write
    STATUS mandatory
    DESCRIPTION
        "Minimum rel. Humidity in percent with maximum 2 decimal places."
    ::= { wtWebGraphAnalogIn57643AlarmEntry 21 }

wtWebGraphAnalogIn57643Alarm2Max OBJECT-TYPE
    SYNTAX OCTET STRING 
    ACCESS read-write
    STATUS mandatory
    DESCRIPTION
        "Maximum rel.Humidity in percent with maximum 2 decimal places."
    ::= { wtWebGraphAnalogIn57643AlarmEntry 22 }

wtWebGraphAnalogIn57643Alarm2Hysteresis OBJECT-TYPE
    SYNTAX OCTET STRING 
    ACCESS read-write
    STATUS mandatory
    DESCRIPTION
        "Hysterese rel. Humidity in percent with maximum 2 decimal places."
    ::= { wtWebGraphAnalogIn57643AlarmEntry 23 }

wtWebGraphAnalogIn57643AlarmSyslogIpAddr OBJECT-TYPE
    SYNTAX OCTET STRING 
    ACCESS read-write
    STATUS mandatory
    DESCRIPTION
        "IP address of the syslog server to which the Webio device should send syslog messages."
    ::= { wtWebGraphAnalogIn57643AlarmEntry 24 }    

wtWebGraphAnalogIn57643AlarmSyslogPort OBJECT-TYPE
    SYNTAX INTEGER (1..65535) 
    ACCESS read-write
    STATUS mandatory
    DESCRIPTION
        "Port number of the syslog server to which the Webio device should send syslog messages."
    ::= { wtWebGraphAnalogIn57643AlarmEntry 25 }    

wtWebGraphAnalogIn57643AlarmSyslogText OBJECT-TYPE
    SYNTAX OCTET STRING 
    ACCESS read-write
    STATUS mandatory
    DESCRIPTION
        "Every message starts with the priority key, a time stamp and the host ip address, according RFC3164.
        This text appears in the following syslog message body."
    ::= { wtWebGraphAnalogIn57643AlarmEntry 26 }
    
wtWebGraphAnalogIn57643AlarmSyslogClearText OBJECT-TYPE
    SYNTAX OCTET STRING 
    ACCESS read-write
    STATUS mandatory
    DESCRIPTION
        "Every message starts with the priority key, a time stamp and the host ip address, according RFC3164.
        This text appears in the following syslog message body of a alarm clear message."
    ::= { wtWebGraphAnalogIn57643AlarmEntry 27 }
    
wtWebGraphAnalogIn57643AlarmFtpDataPort OBJECT-TYPE
    SYNTAX OCTET STRING 
    ACCESS read-write
    STATUS mandatory
    DESCRIPTION
        "Local data port: 1..65535 or AUTO: the next free port will be assigned."
    ::= { wtWebGraphAnalogIn57643AlarmEntry 28 }
    
wtWebGraphAnalogIn57643AlarmFtpFileName OBJECT-TYPE
    SYNTAX OCTET STRING 
    ACCESS read-write
    STATUS mandatory
    DESCRIPTION
        "Name of the file including path informations."
    ::= { wtWebGraphAnalogIn57643AlarmEntry 29 }
    
wtWebGraphAnalogIn57643AlarmFtpText OBJECT-TYPE
    SYNTAX OCTET STRING 
    ACCESS read-write
    STATUS mandatory
    DESCRIPTION
        "Message text to store on the FTP server."
    ::= { wtWebGraphAnalogIn57643AlarmEntry 30 }

wtWebGraphAnalogIn57643AlarmFtpClearText OBJECT-TYPE
    SYNTAX OCTET STRING 
    ACCESS read-write
    STATUS mandatory
    DESCRIPTION
        "Alarm clear message to store on the FTP server."
    ::= { wtWebGraphAnalogIn57643AlarmEntry 31 }
    
wtWebGraphAnalogIn57643AlarmFtpOption OBJECT-TYPE
    SYNTAX OCTET STRING (SIZE(4))
    ACCESS read-write
    STATUS mandatory
    DESCRIPTION
        "Binary coded options, select only one option at the same time:
        STORE  = replace file
        APPEND = append message at the end of the file
        
        Octet 1: unused
        Octet 2: unused
        Octet 3: unused
        Octet 4:
		Bit 0  :	STORE
		Bit 1  :	APPEND
        	Bit 2-7:	unused"
    ::= { wtWebGraphAnalogIn57643AlarmEntry 32 }      
    
wtWebGraphAnalogIn57643AlarmTimerCron OBJECT-TYPE
    SYNTAX OCTET STRING
    ACCESS read-write
    STATUS mandatory
    DESCRIPTION
        "This entry contains 5 space or tab seperated text fields for time trigger definition.
        Each field must match with the actual time to trigger a message, weekday and day of month
        are interpreted separatley.
        1: Minutes	Range 0-59
        2. Hours	Range 0-23, 0 is midnight
        3: Day of month	Range 1-31
        4: Month	Range 1-12
        5: Weekday	Range 0-6, 0 is sunday
        
        Syntax for every field:
         - an asterix (*) enables every possible setting of a field
         - single numbers seperated by commas
         - a partition within the allowed range (1-5)
         - step size within an partition of the allowed range (0-59/2: every second minute)."
    ::= { wtWebGraphAnalogIn57643AlarmEntry 33 }      

-- wtWebGraphAnalogIn57643GraphicsBase Group
----------------------------

wtWebGraphAnalogIn57643GraphicsBaseEnable OBJECT-TYPE
    SYNTAX OCTET STRING 
    ACCESS read-write
    STATUS mandatory
    DESCRIPTION
        "Defines the viewing options of the graphic:
        Octet 1: unused
        Octet 2: unused
        Octet 3: unused
        Octet 4:
                Bit 0  : Auto scroll enable
                Bit 1  : Show table
                Bit 2  : Show graph
                Bit 3  : Show control buttons
                Bit 4  : Show config menu
                Bit 5-7: unused"
    ::= { wtWebGraphAnalogIn57643GraphicsBase 1 }

wtWebGraphAnalogIn57643GraphicsBaseWidth OBJECT-TYPE
    SYNTAX INTEGER 
    ACCESS read-write
    STATUS mandatory
    DESCRIPTION
        "Defines the width of the graphic in pixels."
    ::= { wtWebGraphAnalogIn57643GraphicsBase 2 }
    
wtWebGraphAnalogIn57643GraphicsBaseHeight OBJECT-TYPE
        SYNTAX INTEGER 
        ACCESS read-write
        STATUS mandatory
        DESCRIPTION
            "Defines the height of the graphic in pixels."
        ::= { wtWebGraphAnalogIn57643GraphicsBase 3 }

wtWebGraphAnalogIn57643GraphicsBaseFrameColor OBJECT-TYPE
    SYNTAX OCTET STRING (SIZE(3))
    ACCESS read-write
    STATUS mandatory
    DESCRIPTION
        "Frame color definition in RGB."
    ::= { wtWebGraphAnalogIn57643GraphicsBase 4 }

wtWebGraphAnalogIn57643GraphicsBaseBackgroundColor OBJECT-TYPE
    SYNTAX OCTET STRING (SIZE(3))
    ACCESS read-write
    STATUS mandatory
    DESCRIPTION
        "Background color definition in RGB."
    ::= { wtWebGraphAnalogIn57643GraphicsBase 5 }
    
wtWebGraphAnalogIn57643GraphicsBasePollingrate OBJECT-TYPE
        SYNTAX INTEGER 
        ACCESS read-write
        STATUS mandatory
        DESCRIPTION
            "Defines the pollingrate in seconds, 
            which defines the refreshing intervall of the graphic."
        ::= { wtWebGraphAnalogIn57643GraphicsBase 6 }
   
-- wtWebGraphAnalogIn57643GraphicsSelect Group
----------------------------

wtWebGraphAnalogIn57643GraphicsSelectDisplaySensorSel OBJECT-TYPE
    SYNTAX OCTET STRING (SIZE(4))
    ACCESS read-write
    STATUS mandatory
    DESCRIPTION
        "Binary coded sensor selection:
        only selected sensors will be shown in the graphical presentation:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
    ::= { wtWebGraphAnalogIn57643GraphicsSelect 1 }   
    
wtWebGraphAnalogIn57643GraphicsSelectDisplayShowExtrem OBJECT-TYPE
    SYNTAX OCTET STRING (SIZE(4))
    ACCESS read-write
    STATUS mandatory
    DESCRIPTION
        "Binary coded sensor selection:
        only selected sensors will be shown with minima and maxima:
        Octet 1: unused
        Octet 2: unused
        Octet 3: unused
        Octet 4:
        	Bit 0: Sensor 1
        	Bit 1: Sensor 2
        	Bit 2: Sensor 3
        	Bit 3: Sensor 4
        	Bit 4: Sensor 5
        	Bit 5: Sensor 6
        	Bit 6: Sensor 7
        	Bit 7: Sensor 8"
     ::= { wtWebGraphAnalogIn57643GraphicsSelect 2 }   

-- Graph Sensor Color Table

wtWebGraphAnalogIn57643SensorColor2Table OBJECT-TYPE
    SYNTAX SEQUENCE OF WtWebGraphAnalogIn57643SensorColor2Entry
    ACCESS not-accessible
    STATUS mandatory
    DESCRIPTION
        "List of sensor colors for the praphical presentation."
    ::= { wtWebGraphAnalogIn57643GraphicsSelect 3 }

wtWebGraphAnalogIn57643SensorColor2Entry OBJECT-TYPE
    SYNTAX WtWebGraphAnalogIn57643SensorColor2Entry
    ACCESS not-accessible
    STATUS mandatory
    DESCRIPTION
        "Numbers of the sensors."
    INDEX  { wtWebGraphAnalogIn57643SensorNo }
    ::= { wtWebGraphAnalogIn57643SensorColor2Table 1 }

WtWebGraphAnalogIn57643SensorColor2Entry ::= SEQUENCE {
    wtWebGraphAnalogIn57643GraphicsSensorColor OCTET STRING,
    wtWebGraphAnalogIn57643GraphicsSelectScale OCTET STRING
}

wtWebGraphAnalogIn57643GraphicsSensorColor OBJECT-TYPE
    SYNTAX OCTET STRING (SIZE(3))
    ACCESS read-write
    STATUS mandatory
    DESCRIPTION
        "Color of the sensors at the praphical presention."
    ::= { wtWebGraphAnalogIn57643SensorColor2Entry 1 }
    
wtWebGraphAnalogIn57643GraphicsSelectScale OBJECT-TYPE
    SYNTAX OCTET STRING 
    ACCESS read-write
    STATUS mandatory
    DESCRIPTION
        "Assignes one of 4 scales to a sensor:
        Octet 1: unused
        Octet 2: unused
        Octet 3: unused
        Octet 4:
                Bit 0  : Use Scale 1
                Bit 1  : Use Scale 2
                Bit 2  : Use Scale 3
                Bit 3  : Use Scale 4
                Bit 4-7: unused"
    ::= { wtWebGraphAnalogIn57643SensorColor2Entry 2 }
   
-- wtWebGraphAnalogIn57643GraphicsScale Group
----------------------------

wtWebGraphAnalogIn57643GraphicsScaleAutoScaleEnable OBJECT-TYPE
    SYNTAX OCTET STRING 
    ACCESS read-write
    STATUS mandatory
    DESCRIPTION
        "Select the Auto Scale Mode:
        Octet 1: unused
        Octet 2: unused
        Octet 3: unused
        Octet 4:
                Bit 0  : Scale 1 Auto scale enable
                Bit 1  : Scale 2 Auto scale enable
                Bit 2  : Scale 3 Auto scale enable
                Bit 3  : Scale 4 Auto scale enable
                Bit 4-7: unused"
    ::= { wtWebGraphAnalogIn57643GraphicsScale 1 }


wtWebGraphAnalogIn57643GraphicsScaleAutoFitEnable OBJECT-TYPE
    SYNTAX OCTET STRING 
    ACCESS read-write
    STATUS mandatory
    DESCRIPTION
        "Select the Auto Fit Mode::
        Octet 1: unused
        Octet 2: unused
        Octet 3: unused
        Octet 4:
                Bit 0  : Scale 1 Auto fit enable
                Bit 1  : Scale 2 Auto fit enable
                Bit 2  : Scale 3 Auto fit enable
                Bit 3  : Scale 4 Auto fit enable
                Bit 4-7: unused"
    ::= { wtWebGraphAnalogIn57643GraphicsScale 2 }

wtWebGraphAnalogIn57643GraphicsScale1Min OBJECT-TYPE
    SYNTAX INTEGER
    ACCESS read-only
    STATUS mandatory
    DESCRIPTION
        "Scale 1: Minimum."
    ::= { wtWebGraphAnalogIn57643GraphicsScale 3 }
   
wtWebGraphAnalogIn57643GraphicsScale2Min OBJECT-TYPE
    SYNTAX INTEGER
    ACCESS read-only
    STATUS mandatory
    DESCRIPTION
        "Scale 2: Minimum."
    ::= { wtWebGraphAnalogIn57643GraphicsScale 4 }

wtWebGraphAnalogIn57643GraphicsScale3Min OBJECT-TYPE
    SYNTAX INTEGER
    ACCESS read-only
    STATUS mandatory
    DESCRIPTION
        "Scale 3: Minimum."
    ::= { wtWebGraphAnalogIn57643GraphicsScale 5 }

wtWebGraphAnalogIn57643GraphicsScale4Min OBJECT-TYPE
    SYNTAX INTEGER
    ACCESS read-only
    STATUS mandatory
    DESCRIPTION
        "Scale 4: Minimum."
    ::= { wtWebGraphAnalogIn57643GraphicsScale 6 }

wtWebGraphAnalogIn57643GraphicsScale1Max OBJECT-TYPE
    SYNTAX INTEGER
    ACCESS read-only
    STATUS mandatory
    DESCRIPTION
        "Scale 1: Maximum."
    ::= { wtWebGraphAnalogIn57643GraphicsScale 7 }

wtWebGraphAnalogIn57643GraphicsScale2Max OBJECT-TYPE
    SYNTAX INTEGER
    ACCESS read-only
    STATUS mandatory
    DESCRIPTION
        "Scale 2: Maximum."
    ::= { wtWebGraphAnalogIn57643GraphicsScale 8 }

wtWebGraphAnalogIn57643GraphicsScale3Max OBJECT-TYPE
    SYNTAX INTEGER
    ACCESS read-only
    STATUS mandatory
    DESCRIPTION
        "Scale 3: Maximum."
    ::= { wtWebGraphAnalogIn57643GraphicsScale 9 }

wtWebGraphAnalogIn57643GraphicsScale4Max OBJECT-TYPE
    SYNTAX INTEGER
    ACCESS read-only
    STATUS mandatory
    DESCRIPTION
        "Scale 4: Maximum."
    ::= { wtWebGraphAnalogIn57643GraphicsScale 10 }

wtWebGraphAnalogIn57643GraphicsScale1Unit OBJECT-TYPE
    SYNTAX OCTET STRING
    ACCESS read-only
    STATUS mandatory
    DESCRIPTION
        "Scale 1: Unit."
    ::= { wtWebGraphAnalogIn57643GraphicsScale 11 }

wtWebGraphAnalogIn57643GraphicsScale2Unit OBJECT-TYPE
    SYNTAX OCTET STRING
    ACCESS read-only
    STATUS mandatory
    DESCRIPTION
        "Scale 2: Unit."
    ::= { wtWebGraphAnalogIn57643GraphicsScale 12 }

wtWebGraphAnalogIn57643GraphicsScale3Unit OBJECT-TYPE
    SYNTAX OCTET STRING
    ACCESS read-only
    STATUS mandatory
    DESCRIPTION
        "Scale 3: Unit."
    ::= { wtWebGraphAnalogIn57643GraphicsScale 13 }

wtWebGraphAnalogIn57643GraphicsScale4Unit OBJECT-TYPE
    SYNTAX OCTET STRING
    ACCESS read-only
    STATUS mandatory
    DESCRIPTION
        "Scale 4: Unit."
    ::= { wtWebGraphAnalogIn57643GraphicsScale 14 }    
    
-- wtWebGraphAnalogIn57643Ports Group
----------------------------

-- Table

wtWebGraphAnalogIn57643PortTable OBJECT-TYPE
    SYNTAX SEQUENCE OF WtWebGraphAnalogIn57643PortEntry
    ACCESS not-accessible
    STATUS mandatory
    DESCRIPTION
        "List of settings depending on the sensor number."
    ::= { wtWebGraphAnalogIn57643Ports 1 }

wtWebGraphAnalogIn57643PortEntry OBJECT-TYPE
    SYNTAX WtWebGraphAnalogIn57643PortEntry
    ACCESS not-accessible
    STATUS mandatory
    DESCRIPTION
        "Sensor parameters for the individual sensors."
    INDEX  { wtWebGraphAnalogIn57643SensorNo }
    ::= { wtWebGraphAnalogIn57643PortTable 1 }

WtWebGraphAnalogIn57643PortEntry ::= SEQUENCE {
    wtWebGraphAnalogIn57643PortName		OCTET STRING,
    wtWebGraphAnalogIn57643PortText		OCTET STRING,
    wtWebGraphAnalogIn57643PortOffset1		OCTET STRING,
    wtWebGraphAnalogIn57643SetPoint1		OCTET STRING,
    wtWebGraphAnalogIn57643PortOffset2		OCTET STRING,
    wtWebGraphAnalogIn57643SetPoint2		OCTET STRING,
    wtWebGraphAnalogIn57643PortComment		OCTET STRING,
    wtWebGraphAnalogIn57643PortSensorSelect	OCTET STRING,
    wtWebGraphAnalogIn57643PortUnit		OCTET STRING,
    wtWebGraphAnalogIn57643PortScale0		OCTET STRING,
    wtWebGraphAnalogIn57643PortScale100		OCTET STRING
}

wtWebGraphAnalogIn57643PortName OBJECT-TYPE
    SYNTAX OCTET STRING 
    ACCESS read-write
    STATUS mandatory
    DESCRIPTION
        "Name of the sensor."
    ::= { wtWebGraphAnalogIn57643PortEntry 1 }

wtWebGraphAnalogIn57643PortText OBJECT-TYPE
    SYNTAX OCTET STRING 
    ACCESS read-write
    STATUS mandatory
    DESCRIPTION
        "Description of the sensor."
    ::= { wtWebGraphAnalogIn57643PortEntry 2 }

wtWebGraphAnalogIn57643PortOffset1 OBJECT-TYPE
    SYNTAX OCTET STRING 
    ACCESS read-write
    STATUS mandatory
    DESCRIPTION
        "Offset calibration: Offset in degrees with maximum 2 decimal places at set point 1."
    ::= { wtWebGraphAnalogIn57643PortEntry 3 }

wtWebGraphAnalogIn57643SetPoint1 OBJECT-TYPE
    SYNTAX OCTET STRING 
    ACCESS read-write
    STATUS mandatory
    DESCRIPTION
        "Offset calibration: set point 1 in degrees with maximum 2 decimal places."
    ::= { wtWebGraphAnalogIn57643PortEntry 4 }

wtWebGraphAnalogIn57643PortOffset2 OBJECT-TYPE
    SYNTAX OCTET STRING 
    ACCESS read-write
    STATUS mandatory
    DESCRIPTION
        "Offset calibration: Offset in degrees with maximum 2 decimal places at set point 2."
    ::= { wtWebGraphAnalogIn57643PortEntry 5 }

wtWebGraphAnalogIn57643SetPoint2 OBJECT-TYPE
    SYNTAX OCTET STRING 
    ACCESS read-write
    STATUS mandatory
    DESCRIPTION
        "Offset calibration: set point 2 in degrees with maximum 2 decimal places."
    ::= { wtWebGraphAnalogIn57643PortEntry 6 }

wtWebGraphAnalogIn57643PortComment OBJECT-TYPE
    SYNTAX OCTET STRING 
    ACCESS read-write
    STATUS mandatory
    DESCRIPTION
        "Offset calibration: informations of date, name of operator, reference devices."
    ::= { wtWebGraphAnalogIn57643PortEntry 7 }   

wtWebGraphAnalogIn57643PortSensorSelect OBJECT-TYPE
    SYNTAX OCTET STRING (SIZE(4))
    ACCESS read-write
    STATUS mandatory
    DESCRIPTION
        "Binary coded options for sensor 1:
        Octet 1: unused
        Octet 2: unused
        Octet 3: unused
        Octet 4:
		Bit 0  :	0-10V (default)
		Bit 1  :	Disconnect
        	Bit 2-7:	unused
        
        Binary coded options for sensor 2:
	Octet 1: unused
	Octet 2: unused
	Octet 3: unused
	Octet 4:
		Bit 0  :	0-10V (default)
		Bit 1  :	Disconnect
        	Bit 2-7:	unused"
    ::= { wtWebGraphAnalogIn57643PortEntry 8 }    
    
wtWebGraphAnalogIn57643PortUnit OBJECT-TYPE
    SYNTAX OCTET STRING 
    ACCESS read-write
    STATUS mandatory
    DESCRIPTION
        "User scale: displayed unit."
    ::= { wtWebGraphAnalogIn57643PortEntry 9 }   
    
wtWebGraphAnalogIn57643PortScale0 OBJECT-TYPE
    SYNTAX OCTET STRING 
    ACCESS read-write
    STATUS mandatory
    DESCRIPTION
        "User scale: displayed value in 1/1000 at 0% full scale range.
        Range: -999999.999 to 999999.999"
    ::= { wtWebGraphAnalogIn57643PortEntry 10 }   

wtWebGraphAnalogIn57643PortScale100 OBJECT-TYPE
    SYNTAX OCTET STRING 
    ACCESS read-write
    STATUS mandatory
    DESCRIPTION
        "User scale: displayed value in 1/1000 at 100% full scale range.
        Range: -999999.999 to 999999.999"
    ::= { wtWebGraphAnalogIn57643PortEntry 11 }   

-- wtWebGraphAnalogIn57643Manufact Group
----------------------------

wtWebGraphAnalogIn57643MfName OBJECT-TYPE
    SYNTAX OCTET STRING 
    ACCESS read-write
    STATUS mandatory
    DESCRIPTION
        "Manufacturer company name"
    ::= { wtWebGraphAnalogIn57643Manufact 1 }

wtWebGraphAnalogIn57643MfAddr OBJECT-TYPE
    SYNTAX OCTET STRING 
    ACCESS read-write
    STATUS mandatory
    DESCRIPTION
        "Manufacturer address."
    ::= { wtWebGraphAnalogIn57643Manufact 2 }

wtWebGraphAnalogIn57643MfHotline OBJECT-TYPE
    SYNTAX OCTET STRING 
    ACCESS read-write
    STATUS mandatory
    DESCRIPTION
        "Manufacturer hotline."
    ::= { wtWebGraphAnalogIn57643Manufact 3 }

wtWebGraphAnalogIn57643MfInternet OBJECT-TYPE
    SYNTAX OCTET STRING 
    ACCESS read-write
    STATUS mandatory
    DESCRIPTION
        "Manufacturer Internet address."
    ::= { wtWebGraphAnalogIn57643Manufact 4 }

wtWebGraphAnalogIn57643MfDeviceTyp OBJECT-TYPE
    SYNTAX OCTET STRING 
    ACCESS read-write
    STATUS mandatory
    DESCRIPTION
        "Manufacturer device name (model number)."
    ::= { wtWebGraphAnalogIn57643Manufact 5 }

wtWebGraphAnalogIn57643MfOrderNo OBJECT-TYPE
    SYNTAX OCTET STRING 
    ACCESS read-write
    STATUS mandatory
    DESCRIPTION
        "Manufacturer part number."
    ::= { wtWebGraphAnalogIn57643Manufact 6 }

-- wtWebGraphAnalogIn57643Diag Group
----------------------------

wtWebGraphAnalogIn57643DiagErrorCount OBJECT-TYPE
    SYNTAX INTEGER
    ACCESS read-only
    STATUS mandatory
    DESCRIPTION
        "Number of entries in the error memory."
    ::= { wtWebGraphAnalogIn57643Diag 1 }

wtWebGraphAnalogIn57643DiagBinaryError OBJECT-TYPE
    SYNTAX OCTET STRING 
    ACCESS read-only
    STATUS mandatory
    DESCRIPTION
        "Error causes coded bit-by-bit."
    ::= { wtWebGraphAnalogIn57643Diag 2 }

wtWebGraphAnalogIn57643DiagErrorIndex OBJECT-TYPE
    SYNTAX INTEGER
    ACCESS read-write
    STATUS mandatory
    DESCRIPTION
        "The value of this variable is used as an index to read 
        an error massege from wtWebGraphAnalogIn57643DiagErrorMessage.
        Errors are numbered from 1 to wtWebGraphAnalogIn57643DiagErrorCount.
        Writing a valid value into this variable, making the appropriate 
        message readable from wtWebGraphAnalogIn57643DiagErrorMessage."
    ::= { wtWebGraphAnalogIn57643Diag 3 }

wtWebGraphAnalogIn57643DiagErrorMessage OBJECT-TYPE
    SYNTAX OCTET STRING 
    ACCESS read-only
    STATUS mandatory
    DESCRIPTION
        "Using wtWebGraphAnalogIn57643DiagErrorIndex as an index, the appropriate message is available."
    ::= { wtWebGraphAnalogIn57643Diag 4 }
    
wtWebGraphAnalogIn57643DiagErrorClear OBJECT-TYPE
    SYNTAX INTEGER
    ACCESS write-only
    STATUS mandatory
    DESCRIPTION
        "Writing 1 into this variable clears all diagnosis messages."
    ::= { wtWebGraphAnalogIn57643Diag 5 }

-- TRAP DEFINITIONS

-- Diese SNMP-Traps werden gesendet, wenn die Alarmtriggerbedingungen zutreffen 

wtWebGraphAnalogIn57643Alert1 TRAP-TYPE
    ENTERPRISE  wtWebGraphAnalogIn57643
    VARIABLES   { wtWebGraphAnalogIn57643AlarmTrapText }
    DESCRIPTION
        "This SNMP trap is generated when Alarm 1 was triggered,
        SNMP trap enable is set and
        SNMP is enabled."
    -- NMS trap annotation
    --#TYPE "Thermo-Hygrometer Alarm 1"
    --#SUMMARY "Alarm 1: %s"
    --#ARGUMENTS {0}
    --#SEVERITY INFORMATIONAL
    --#TIMEINDEX 99
    --#STATE OPERATIONAL    
    ::= 31

wtWebGraphAnalogIn57643Alert2 TRAP-TYPE
    ENTERPRISE  wtWebGraphAnalogIn57643
    VARIABLES   { wtWebGraphAnalogIn57643AlarmTrapText }
    DESCRIPTION
        "This SNMP trap is generated when Alarm 2 was triggered,
        SNMP trap enable is set and
        SNMP is enabled."
    -- NMS trap annotation
    --#TYPE "Thermo-Hygrometer Alarm 2"
    --#SUMMARY "Alarm 2: %s"
    --#ARGUMENTS {0}
    --#SEVERITY INFORMATIONAL
    --#TIMEINDEX 99
    --#STATE OPERATIONAL    
    ::= 32

wtWebGraphAnalogIn57643Alert3 TRAP-TYPE
    ENTERPRISE  wtWebGraphAnalogIn57643
    VARIABLES   { wtWebGraphAnalogIn57643AlarmTrapText }
    DESCRIPTION
        "This SNMP trap is generated when Alarm 3 was triggered,
        SNMP trap enable is set and
        SNMP is enabled."
    -- NMS trap annotation
    --#TYPE "Thermo-Hygrometer Alarm 3"
    --#SUMMARY "Alarm 3: %s"
    --#ARGUMENTS {0}
    --#SEVERITY INFORMATIONAL
    --#TIMEINDEX 99
    --#STATE OPERATIONAL    
    ::= 33

wtWebGraphAnalogIn57643Alert4 TRAP-TYPE
    ENTERPRISE  wtWebGraphAnalogIn57643
    VARIABLES   { wtWebGraphAnalogIn57643AlarmTrapText }
    DESCRIPTION
        "This SNMP trap is generated when Alarm 4 was triggered,
        SNMP trap enable is set and
        SNMP is enabled."
    -- NMS trap annotation
    --#TYPE "Thermo-Hygrometer Alarm 4"
    --#SUMMARY "Alarm 4: %s"
    --#ARGUMENTS {0}
    --#SEVERITY INFORMATIONAL
    --#TIMEINDEX 99
    --#STATE OPERATIONAL    
    ::= 34

wtWebGraphAnalogIn57643Alert5 TRAP-TYPE
    ENTERPRISE  wtWebGraphAnalogIn57643
    VARIABLES   { wtWebGraphAnalogIn57643AlarmTrapText }
    DESCRIPTION
        "This SNMP trap is generated when Alarm 5 was triggered,
        SNMP trap enable is set and
        SNMP is enabled."
    -- NMS trap annotation
    --#TYPE "Thermo-Hygrometer Alarm 5"
    --#SUMMARY "Alarm 5: %s"
    --#ARGUMENTS {0}
    --#SEVERITY INFORMATIONAL
    --#TIMEINDEX 99
    --#STATE OPERATIONAL    
    ::= 35

wtWebGraphAnalogIn57643Alert6 TRAP-TYPE
    ENTERPRISE  wtWebGraphAnalogIn57643
    VARIABLES   { wtWebGraphAnalogIn57643AlarmTrapText }
    DESCRIPTION
        "This SNMP trap is generated when Alarm 6 was triggered,
        SNMP trap enable is set and
        SNMP is enabled."
    -- NMS trap annotation
    --#TYPE "Thermo-Hygrometer Alarm 6"
    --#SUMMARY "Alarm 6: %s"
    --#ARGUMENTS {0}
    --#SEVERITY INFORMATIONAL
    --#TIMEINDEX 99
    --#STATE OPERATIONAL    
    ::= 36

wtWebGraphAnalogIn57643Alert7 TRAP-TYPE
    ENTERPRISE  wtWebGraphAnalogIn57643
    VARIABLES   { wtWebGraphAnalogIn57643AlarmTrapText }
    DESCRIPTION
        "This SNMP trap is generated when Alarm 7 was triggered,
        SNMP trap enable is set and
        SNMP is enabled."
    -- NMS trap annotation
    --#TYPE "Thermo-Hygrometer Alarm 7"
    --#SUMMARY "Alarm 7: %s"
    --#ARGUMENTS {0}
    --#SEVERITY INFORMATIONAL
    --#TIMEINDEX 99
    --#STATE OPERATIONAL    
    ::= 37

wtWebGraphAnalogIn57643Alert8 TRAP-TYPE
    ENTERPRISE  wtWebGraphAnalogIn57643
    VARIABLES   { wtWebGraphAnalogIn57643AlarmTrapText }
    DESCRIPTION
        "This SNMP trap is generated when Alarm 8 was triggered,
        SNMP trap enable is set and
        SNMP is enabled."
    -- NMS trap annotation
    --#TYPE "Thermo-Hygrometer Alarm 8"
    --#SUMMARY "Alarm 8: %s"
    --#ARGUMENTS {0}
    --#SEVERITY INFORMATIONAL
    --#TIMEINDEX 99
    --#STATE OPERATIONAL    
    ::= 38

    
wtWebGraphAnalogIn57643Alert9 TRAP-TYPE
    ENTERPRISE  wtWebGraphAnalogIn57643
    VARIABLES   { wtWebGraphAnalogIn57643AlarmClearTrapText }
    DESCRIPTION
        "This SNMP trap is generated when Alarm 1 was cleared,
        SNMP trap enable is set and
        SNMP is enabled."
    -- NMS trap annotation
    --#TYPE "Thermo-Hygrometer Release Alarm 1"
    --#SUMMARY "Release Alarm 1: %s"
    --#ARGUMENTS {0}
    --#SEVERITY INFORMATIONAL
    --#TIMEINDEX 99
    --#STATE OPERATIONAL    
    ::= 91

wtWebGraphAnalogIn57643Alert10 TRAP-TYPE
    ENTERPRISE  wtWebGraphAnalogIn57643
    VARIABLES   { wtWebGraphAnalogIn57643AlarmClearTrapText }
    DESCRIPTION
        "This SNMP trap is generated when Alarm 2 was cleared,
        SNMP trap enable is set and
        SNMP is enabled."
    -- NMS trap annotation
    --#TYPE "Thermo-Hygrometer Release Alarm 2"
    --#SUMMARY "Release Alarm 2: %s"
    --#ARGUMENTS {0}
    --#SEVERITY INFORMATIONAL
    --#TIMEINDEX 99
    --#STATE OPERATIONAL    
    ::= 92

wtWebGraphAnalogIn57643Alert11 TRAP-TYPE
    ENTERPRISE  wtWebGraphAnalogIn57643
    VARIABLES   { wtWebGraphAnalogIn57643AlarmClearTrapText }
    DESCRIPTION
        "This SNMP trap is generated when Alarm 3 was cleared,
        SNMP trap enable is set and
        SNMP is enabled."
    -- NMS trap annotation
    --#TYPE "Thermo-Hygrometer Release Alarm 3"
    --#SUMMARY "Release Alarm 3: %s"
    --#ARGUMENTS {0}
    --#SEVERITY INFORMATIONAL
    --#TIMEINDEX 99
    --#STATE OPERATIONAL    
    ::= 93

wtWebGraphAnalogIn57643Alert12 TRAP-TYPE
    ENTERPRISE  wtWebGraphAnalogIn57643
    VARIABLES   { wtWebGraphAnalogIn57643AlarmClearTrapText }
    DESCRIPTION
        "This SNMP trap is generated when Alarm 4 was cleared,
        SNMP trap enable is set and
        SNMP is enabled."
    -- NMS trap annotation
    --#TYPE "Thermo-Hygrometer Release Alarm 4"
    --#SUMMARY "Release Alarm 4: %s"
    --#ARGUMENTS {0}
    --#SEVERITY INFORMATIONAL
    --#TIMEINDEX 99
    --#STATE OPERATIONAL    
    ::= 94

wtWebGraphAnalogIn57643Alert13 TRAP-TYPE
    ENTERPRISE  wtWebGraphAnalogIn57643
    VARIABLES   { wtWebGraphAnalogIn57643AlarmClearTrapText }
    DESCRIPTION
        "This SNMP trap is generated when Alarm 5 was cleared,
        SNMP trap enable is set and
        SNMP is enabled."
    -- NMS trap annotation
    --#TYPE "Thermo-Hygrometer Release Alarm 5"
    --#SUMMARY "Release Alarm 5: %s"
    --#ARGUMENTS {0}
    --#SEVERITY INFORMATIONAL
    --#TIMEINDEX 99
    --#STATE OPERATIONAL    
    ::= 95

wtWebGraphAnalogIn57643Alert14 TRAP-TYPE
    ENTERPRISE  wtWebGraphAnalogIn57643
    VARIABLES   { wtWebGraphAnalogIn57643AlarmClearTrapText }
    DESCRIPTION
        "This SNMP trap is generated when Alarm 6 was cleared,
        SNMP trap enable is set and
        SNMP is enabled."
    -- NMS trap annotation
    --#TYPE "Thermo-Hygrometer Release Alarm 6"
    --#SUMMARY "Release Alarm 6: %s"
    --#ARGUMENTS {0}
    --#SEVERITY INFORMATIONAL
    --#TIMEINDEX 99
    --#STATE OPERATIONAL    
    ::= 96

wtWebGraphAnalogIn57643Alert15 TRAP-TYPE
    ENTERPRISE  wtWebGraphAnalogIn57643
    VARIABLES   { wtWebGraphAnalogIn57643AlarmClearTrapText }
    DESCRIPTION
        "This SNMP trap is generated when Alarm 7 was cleared,
        SNMP trap enable is set and
        SNMP is enabled."
    -- NMS trap annotation
    --#TYPE "Thermo-Hygrometer Release Alarm 7"
    --#SUMMARY "Release Alarm 7: %s"
    --#ARGUMENTS {0}
    --#SEVERITY INFORMATIONAL
    --#TIMEINDEX 99
    --#STATE OPERATIONAL    
    ::= 97

wtWebGraphAnalogIn57643Alert16 TRAP-TYPE
    ENTERPRISE  wtWebGraphAnalogIn57643
    VARIABLES   { wtWebGraphAnalogIn57643AlarmClearTrapText }
    DESCRIPTION
        "This SNMP trap is generated when Alarm 8 was cleared,
        SNMP trap enable is set and
        SNMP is enabled."
    -- NMS trap annotation
    --#TYPE "Thermo-Hygrometer Release Alarm 8"
    --#SUMMARY "Release Alarm 8: %s"
    --#ARGUMENTS {0}
    --#SEVERITY INFORMATIONAL
    --#TIMEINDEX 99
    --#STATE OPERATIONAL    
    ::= 98

wtWebGraphAnalogIn57643AlertDiag TRAP-TYPE
    ENTERPRISE  wtWebGraphAnalogIn57643
    VARIABLES   { 	
    		wtWebGraphAnalogIn57643DiagErrorIndex,
    	  	wtWebGraphAnalogIn57643DiagErrorMessage
    		}
    DESCRIPTION
        "This SNMP trap is generated when a diagnosis/error message was triggered,
        SNMP trap enable is set and
        SNMP is enabled."
    -- NMS trap annotation
    --#TYPE "Thermo-Hygrometer Diagnose Error"
    --#SUMMARY "Diagnose error index: %d, Message: %s."
    --#ARGUMENTS {0,1}
    --#SEVERITY MAJOR
    --#TIMEINDEX 99
    --#STATE DEGRADED    
    ::= 110 
 
END
