ELTEX-MES-TUNING-MIB DEFINITIONS ::= BEGIN

-- Title:      Eltex MES Tuning Private Extension
-- Version:    1.00
-- Date:       19 Dec 2014

IMPORTS
    eltMes                                                  FROM ELTEX-MES
    Unsigned32,
    MODULE-IDENTITY, OBJECT-TYPE, IpAddress                 FROM SNMPv2-SMI
    DisplayString, RowStatus, TruthValue,
    TEXTUAL-CONVENTION                                      FROM SNMPv2-TC;

eltMesTuning  MODULE-IDENTITY
           LAST-UPDATED "201412190000Z"
           ORGANIZATION "Eltex Ltd."
           CONTACT-INFO
                "eltex.nsk.ru"
           DESCRIPTION
                "The private MIB module definition for Eltex device tuning MIB."
           REVISION "201412190000Z"
           DESCRIPTION
                    "Added eltMesTcamTuning."
           ::= { eltMes 29 }


eltMesTcamTuning OBJECT IDENTIFIER ::= { eltMesTuning 1 }

eltMaxSelectiveQinqIngressRules OBJECT-TYPE
    SYNTAX      INTEGER
    MAX-ACCESS  read-only
    STATUS      current
    DESCRIPTION
      "Maximal number of ingress Selective QinQ rules supported."
    ::=  { eltMesTcamTuning 1 }

eltMaxSelectiveQinqIngressRulesAfterReset OBJECT-TYPE
    SYNTAX      INTEGER
    MAX-ACCESS  read-write
    STATUS      current
    DESCRIPTION
      "Future Maximal number of ingress Selective QinQ rules supported."
    ::=  { eltMesTcamTuning 2 }

eltMaxSelectiveQinqEgressRules OBJECT-TYPE
    SYNTAX      INTEGER
    MAX-ACCESS  read-only
    STATUS      current
    DESCRIPTION
      "Maximal number of egress Selective QinQ rules supported."
    ::=  { eltMesTcamTuning 3 }

eltMaxSelectiveQinqEgressRulesAfterReset OBJECT-TYPE
    SYNTAX      INTEGER
    MAX-ACCESS  read-write
    STATUS      current
    DESCRIPTION
      "Future Maximal number of egress Selective QinQ rules supported."
    ::=  { eltMesTcamTuning 4 }

-- next OBJECT IDENTIFIER ::= { eltMesTuning 2 }

END
