ELTEX-MES-SNMP-COMMUNITY-EXT-MIB DEFINITIONS ::= BEGIN

-- Title:      Eltex MES Snmp Community extended Configuration
-- Version:    1.0
-- Date:       17-Apr-2013

IMPORTS
    MODULE-IDENTITY, OBJECT-TYPE, Integer32              FROM SNMPv2-SMI
    snmpCommunityEntry                                   FROM SNMP-COMMUNITY-MIB
    eltMesSnmpCommExtMIB                                 FROM ELTEX-MES-MNG-MIB;

eltSnmpCommunityTable OBJECT-TYPE
    SYNTAX      SEQUENCE OF EltSnmpCommunityEntry
    MAX-ACCESS  not-accessible
    STATUS      current
    DESCRIPTION
        "The table of community strings configured in the SNMP
         engine's Local Configuration Datastore (LCD)."
    ::= { eltMesSnmpCommExtMIB 1 }

eltSnmpCommunityEntry OBJECT-TYPE
    SYNTAX      EltSnmpCommunityEntry
    MAX-ACCESS  not-accessible
    STATUS      current
    DESCRIPTION
        "Information about a particular community string."
    AUGMENTS { snmpCommunityEntry }
    ::= { eltSnmpCommunityTable 1 }

EltSnmpCommunityEntry ::= SEQUENCE {
    eltSnmpCommunityAccessList    Integer32
}

eltSnmpCommunityAccessList OBJECT-TYPE
    SYNTAX      Integer32
    MAX-ACCESS  read-create
    STATUS      current
    DESCRIPTION
        "Index assigned to the ACL for SNMP community to filter SNMP requests."
    ::= { eltSnmpCommunityEntry 1 }

END
