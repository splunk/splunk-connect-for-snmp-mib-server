-- ZyXEL Communications Corporation
-- Private Enterprise MIB definition 
  
-- This file describes the ZyXEL Communications Corporation Enterprise MIB.
-- It contains ZyXEL products OIDs, and common managed objects.

-- $Log: ZYXEL-MAC-PINNING-MIB.mib $ 
-- Revision 1.5  2013/12/06 07:07:12  ccho 
-- remove uncessary imports 
-- Revision 1.4  2012/10/29 08:38:53  Aga 
-- bug fix: remove enable status description 
-- Revision 1.3  2012/09/19 07:40:59  Kevin 
-- if it's leaf node, revise the vender name from zyxel to zy 
-- Revision 1.2  2012/07/05 06:23:38  Kevin 
-- 1. upgrade from SNMP to SNMPv2  
-- 2. clean warning 
-- Revision 1.1  2012/05/30 07:49:48  Kevin 
-- Initial revision 

ZYXEL-MAC-PINNING-MIB DEFINITIONS ::= BEGIN

    IMPORTS
	OBJECT-TYPE
		FROM SNMPv2-SMI			-- RFC2578	
		
	MODULE-IDENTITY
		FROM SNMPv2-SMI
	
	EnabledStatus
		FROM  P-BRIDGE-MIB

	dot1dBasePort
       	FROM BRIDGE-MIB

	esMgmt			
		FROM ZYXEL-ES-SMI;

	zyxelMacPinning MODULE-IDENTITY
		LAST-UPDATED	"201207010000Z"    
		ORGANIZATION "Enterprise Solution ZyXEL"     
		CONTACT-INFO
			""	   
		DESCRIPTION
			"The subtree for MAC Pinning"
		::= { esMgmt 92 }	

	zyxelMacPinningSetup   	OBJECT IDENTIFIER ::= { zyxelMacPinning 1 }
		
 -- ******************************************************************
-- *
-- 92. zyxelMacPinningSetup
-- *
-- ****************************************************************** 
                               
        zyMacPinningState OBJECT-TYPE
        SYNTAX  EnabledStatus
        MAX-ACCESS  read-write
        STATUS  current
        DESCRIPTION
        "Enable/Disable MAC pinning on the switch."
        ::= { zyxelMacPinningSetup 1 }

                                               
-- 		zyxelMacPinningPortTable

		zyxelMacPinningPortTable OBJECT-TYPE
		SYNTAX	SEQUENCE OF ZyxelMacPinningPortEntry
        MAX-ACCESS  not-accessible
        STATUS  current
        DESCRIPTION
        "The table contains MAC pinning port configuration."
        ::= { zyxelMacPinningSetup 2 }
        
		zyxelMacPinningPortEntry OBJECT-TYPE
        SYNTAX	ZyxelMacPinningPortEntry
        MAX-ACCESS	not-accessible
        STATUS	current
        DESCRIPTION    	
		"An entry contains MAC pinning port configuration."
        INDEX          	{ dot1dBasePort }
        ::= { zyxelMacPinningPortTable 1 }
     
		ZyxelMacPinningPortEntry ::=
		SEQUENCE {
			zyMacPinningPortState	 INTEGER
		}

        zyMacPinningPortState OBJECT-TYPE
        SYNTAX  EnabledStatus
        MAX-ACCESS  read-write
        STATUS  current
        DESCRIPTION
        "Enable/Disable MAC pinning on the port."
        ::= { zyxelMacPinningPortEntry 1 }

END
