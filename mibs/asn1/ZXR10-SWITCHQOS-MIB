--  ******************************************************
--  $Id: zxr10SwitchQoS.mib 14 2005-04-06 07:42:13Z taowq $
--
--  zxr10switchQoS.mib: ZXR10 Switch QoS MIB file
--  
--  Mar. 2005, Tao wenqiang
--   
--  Copyright(c) 2005 by ZTE Corporaton
--  All rights reservered
--
--  
--  ******************************************************
     ZXR10-SWITCHQOS-MIB DEFINITIONS ::= BEGIN

   IMPORTS
    RowStatus                           
                                                 FROM SNMPv2-TC
   MODULE-IDENTITY, OBJECT-TYPE,
      TimeTicks, enterprises,   IpAddress                      FROM SNMPv2-SMI;

 	zte OBJECT IDENTIFIER ::= { enterprises 3902 }
 	zxr10 OBJECT IDENTIFIER ::= { zte 3}
	zxr10switch OBJECT IDENTIFIER ::= { zxr10 102}
    zxr10swqos OBJECT IDENTIFIER ::= { zxr10switch 3}

      DisplayString ::= OCTET STRING
          --  This data type is used to model textual information taken
          --  from the NVT ASCII character set.  By convention, objects
          --  with this syntax are declared as having
          --
          --       SIZE (0..255)

       TrafficDropPriority ::= INTEGER
                        {
                            low(0),
                            medium(1),
							high(2)
                        }
						
	   TrafficColorMode ::= INTEGER
                        {
                            blind(0),
                            aware(1)
                        }
						
	   TrafficForward ::= INTEGER
                        {
                            forwardRed(1)
                        }
						
	   TrafficDrop ::= INTEGER
                        {
                            dropYellow(1)
                        }
						
       TrafficMirrorAction ::= INTEGER
	                    {
							cpu(1),
							interface(2)
						}

--switch qos mib define ,added by luyan 2005-2-2 9:35

    -- add for 2802c,songchan 2008,09,11					 	
        RedirectFlag ::= INTEGER							
						{
						     cpu(1),
						     interface(2),
						     next-hop(3),
							 next-hop-ipv6(4)
						}
	-- add for 2802c,songchan 2008,09,11	
	Packettype ::= INTEGER
		                {
						     all(0),						 
						     red(1) ,
							 yellow(2),
							 green(3)
						}
	-- add for 2802c,songchan 2008,09,11	
		Statisticstype ::= INTEGER
		                {
						     packet(0),
							  byte(1)
						     
						}
			   GreenOnlyType ::= INTEGER
                        {
                            green-only(1)
                        }
   InetAddressIPv6 ::= TEXTUAL-CONVENTION
     DISPLAY-HINT "2x:2x:2x:2x:2x:2x:2x:2x%4d"
     STATUS       current
     DESCRIPTION
     "Represents an IPv6 network address:

            octets   contents         encoding
             1-16    IPv6 address     network-byte order
            17-20    scope identifier network-byte order
		
          The corresponding InetAddressType value is ipv6(2).

          The scope identifier (bytes 17-20) MUST NOT be present
          for global IPv6 addresses. For non-global IPv6 addresses
          (e.g. link-local or site-local addresses), the scope
          identifier MUST always be present. It contains a link
          identifier for link-local and a site identifier for
          site-local IPv6 addresses.

          The scope identifier MUST disambiguate identical address
          values. For link-local addresses, the scope identifier will
          typically be the interface index (ifIndex as defined in the
          IF-MIB, RFC 2233) of the interface on which the address is
          configured.

          The scope identifier may contain the special value 0
          which refers to the default scope. The default scope
          may be used in cases where the valid scope identifier
          is not known (e.g., a management application needs to
          write a site-local InetAddressIPv6 address without
          knowing the site identifier value). The default scope
          SHOULD NOT be used as an easy way out in cases where
          the scope identifier for a non-global IPv6 is known."
     SYNTAX       OCTET STRING (SIZE (16|20))   

--switch qos mib define ,added by luyan 2005-2-2 9:35
--all description add for 2802c,songchan 2008-08-27

zxr10AclQosPriorityMarkTable  OBJECT-TYPE
              SYNTAX  SEQUENCE OF Zxr10AclQosPriorityMarkEntry
              MAX-ACCESS  not-accessible
              STATUS  current
              DESCRIPTION
                      "The description of zxr10 acl qos priority mark configuration.
             It is a list of acl qos priority mark entries."     
               ::= { zxr10swqos 1 }

    zxr10AclQosPriorityMarkEntry  OBJECT-TYPE
              SYNTAX  Zxr10AclQosPriorityMarkEntry
              MAX-ACCESS  not-accessible
              STATUS  current
              DESCRIPTION
                      "A acl qos Priority Mark entry containing objects that
             acl qos Priority Mark infomation,such as:
            dscp-value, dorp precedence etc."    
              INDEX  { zxr10AclQosPriorityMarkAclNo,
                       zxr10AclQosPriorityMarkRuleId }
              ::= { zxr10AclQosPriorityMarkTable 1 }

    Zxr10AclQosPriorityMarkEntry ::=
              SEQUENCE {
                zxr10AclQosPriorityMarkAclNo
                    INTEGER,
                zxr10AclQosPriorityMarkRuleId
                    INTEGER,
                -- add for 2802c,songchan 2008,09,11
	            zxr10AclQosPriorityMarkAclName
                   DisplayString,
                zxr10AclQosPriorityMarkDscpValue
                	INTEGER,
               	-- add for 2802c,songchan 2008,09,11
		       zxr10AclQosPriorityMarkCosValue
                	INTEGER,
                zxr10AclQosPriorityMarkLocalPrecedence
                	INTEGER,
                zxr10AclQosPriorityMarkDropPrecedence
                	TrafficDropPriority,
   -- add for 2802c,songchan 2008,09,11
        	  zxr10AclQosPriorityMarkOuterVlanId
		       INTEGER,
              zxr10AclQosPriorityMarkPrecedenceValue
                	INTEGER,
   -- add for 2802c,songchan 2008,09,11	
		    zxr10AclQosPriorityMarkRowStatus	                    
		     RowStatus
               
              }

   zxr10AclQosPriorityMarkAclNo  OBJECT-TYPE
              SYNTAX  INTEGER
              MAX-ACCESS  read-only --not-accessible
              STATUS  current
              DESCRIPTION
                      "The acl qos priority mark acl-number."  
              ::= { zxr10AclQosPriorityMarkEntry 1 }

   zxr10AclQosPriorityMarkRuleId  OBJECT-TYPE
              SYNTAX  INTEGER
              MAX-ACCESS  read-only
              STATUS  current
              DESCRIPTION
                      "The acl qos priority mark rule-id." 
              ::= { zxr10AclQosPriorityMarkEntry 2 }

  zxr10AclQosPriorityMarkAclName  OBJECT-TYPE
              SYNTAX  DisplayString
              MAX-ACCESS  read-only --not-accessible
              STATUS  current
              DESCRIPTION
                      "The acl qos priority mark acl-name." 
              ::= { zxr10AclQosPriorityMarkEntry 3 }

   zxr10AclQosPriorityMarkDscpValue OBJECT-TYPE
              SYNTAX  INTEGER
              MAX-ACCESS  read-create
              STATUS  current
              DESCRIPTION
                  "The acl qos priority mark dscp value, the valid value is 0-63"
             ::= { zxr10AclQosPriorityMarkEntry 4 }

    zxr10AclQosPriorityMarkCosValue OBJECT-TYPE
              SYNTAX  INTEGER
              MAX-ACCESS  read-create
              STATUS  current
              DESCRIPTION
                  "The acl qos priority mark cos value, the valid value is 0-7"
             ::= { zxr10AclQosPriorityMarkEntry 5 }

   zxr10AclQosPriorityMarkLocalPrecedence OBJECT-TYPE
              SYNTAX  INTEGER
              MAX-ACCESS  read-create
              STATUS  current
              DESCRIPTION
                  "The acl qos priority mark local precedence value,the valid value is 0-7"
             ::= { zxr10AclQosPriorityMarkEntry 6 }

   zxr10AclQosPriorityMarkDropPrecedence OBJECT-TYPE
              SYNTAX  TrafficDropPriority
              MAX-ACCESS  read-create
              STATUS  current
              DESCRIPTION
                  "THe acl qos priority mark dorp precedence value, the valid value is high(2), low(0), medium(1)"
             ::= { zxr10AclQosPriorityMarkEntry 7 }

   zxr10AclQosPriorityMarkOuterVlanId OBJECT-TYPE	
        SYNTAX  INTEGER
        MAX-ACCESS  read-create
        STATUS  current
        DESCRIPTION
            "The acl qos Priority Mark outer vlan id, the valid value is 1-4094.not support by 59 program"                   
        ::= { zxr10AclQosPriorityMarkEntry 8 }
			 
	zxr10AclQosPriorityMarkPrecedenceValue OBJECT-TYPE
              SYNTAX  INTEGER
              MAX-ACCESS  read-create
              STATUS  current
              DESCRIPTION
                  "The acl qos priority mark precedence value,the valid value is 0-7 " 
             ::= { zxr10AclQosPriorityMarkEntry 9 }
			 
	zxr10AclQosPriorityMarkRowStatus OBJECT-TYPE
        SYNTAX  RowStatus
        MAX-ACCESS  read-create
        STATUS  current
        DESCRIPTION
            "The acl qos Priority Mark item row status. if it is in valid status, it only 
             can change to invalid status, no other status.when you creat something, you should enter creatAndGo(4),
			 and when you want to delete it, you should enter destroy(6)."                  
            ::= { zxr10AclQosPriorityMarkEntry 10 }

-- traffic limit
     zxr10AclQosTrafficLimitTable  OBJECT-TYPE
             SYNTAX  SEQUENCE OF Zxr10AclQosTrafficLimitEntry
             MAX-ACCESS  not-accessible
             STATUS  current
             DESCRIPTION
                     "The description of zxr10 acl qos traffic limit configuration.
             It is a list of acl qos traffic limit entries."
              ::= { zxr10swqos 2 }

   zxr10AclQosTrafficLimitEntry  OBJECT-TYPE
             SYNTAX  Zxr10AclQosTrafficLimitEntry
             MAX-ACCESS  not-accessible
             STATUS  current
             DESCRIPTION
                     "A acl qos traffic limit entry containing objects that
             acl qos traffic limit infomation,such as:
             cbs value, ebs value, pir value, traffic limit mode etc."
             INDEX  { zxr10AclQosTrafficLimitAclNo,
                      zxr10AclQosTrafficLimitRuleId }
             ::= { zxr10AclQosTrafficLimitTable 1 }

   Zxr10AclQosTrafficLimitEntry ::=
             SEQUENCE {
               zxr10AclQosTrafficLimitAclNo
                   INTEGER,
               zxr10AclQosTrafficLimitRuleId
                   INTEGER,
			-- add for 2802c,songchan 2008,09,11
			   zxr10AclQosTrafficLimitAclName
                   DisplayString,
               zxr10AclQosTrafficLimitCir
               	INTEGER,
               zxr10AclQosTrafficLimitCbs
               	INTEGER,
               zxr10AclQosTrafficLimitEbs
               	INTEGER,
               zxr10AclQosTrafficLimitPir
               	INTEGER,
               zxr10AclQosTrafficLimitPbs
               	   INTEGER,
               zxr10AclQosTrafficLimitMode
               	   TrafficColorMode,
               zxr10AclQosTrafficLimitRedDscpValue
               	INTEGER,
               zxr10AclQosTrafficLimitYelDscpValue
               	INTEGER,
               zxr10AclQosTrafficLimitRedDp
               	   TrafficDropPriority,
               zxr10AclQosTrafficLimitYelDp
               	   TrafficDropPriority,  
               zxr10AclQosTrafficLimitForwadRed
               	   TrafficForward,
               zxr10AclQosTrafficLimitDropYellow
                   TrafficDrop,
			   -- add for 2802c,songchan 2008,09,11
	       zxr10AclQosTrafficLimitRowStatus
		   RowStatus
             }

  zxr10AclQosTrafficLimitAclNo  OBJECT-TYPE
             SYNTAX  INTEGER
             MAX-ACCESS  read-only
             STATUS  current
             DESCRIPTION
                     "The acl qos traffic limit acl number"
             ::= { zxr10AclQosTrafficLimitEntry 1 }

  zxr10AclQosTrafficLimitRuleId  OBJECT-TYPE
             SYNTAX  INTEGER
             MAX-ACCESS  read-only
             STATUS  current
             DESCRIPTION
                     "The acl qos traffic limit rule id"
             ::= { zxr10AclQosTrafficLimitEntry 2 }

	zxr10AclQosTrafficLimitAclName  OBJECT-TYPE
             SYNTAX   DisplayString 
             MAX-ACCESS  read-only             
			 STATUS  current
             DESCRIPTION
                     "The acl qos traffic limit acl name"
             ::= { zxr10AclQosTrafficLimitEntry 3 }


  zxr10AclQosTrafficLimitCir OBJECT-TYPE
             SYNTAX   INTEGER
             MAX-ACCESS  read-create
             STATUS  current
             DESCRIPTION
                     "The acl qos traffic limit cir value, the valid value is 1-32000000 in 89 program.but in 59 program is 64-32000000"
             ::= { zxr10AclQosTrafficLimitEntry 4 }

  zxr10AclQosTrafficLimitCbs OBJECT-TYPE
             SYNTAX  INTEGER
             MAX-ACCESS  read-create
             STATUS  current
             DESCRIPTION
                 "The acl qos traffic limit cbs value, the valid value is 1-16000.but in 59 program is 4-16000"
            ::= { zxr10AclQosTrafficLimitEntry 5 }

  zxr10AclQosTrafficLimitEbs OBJECT-TYPE
             SYNTAX  INTEGER
             MAX-ACCESS  read-create
             STATUS  current
             DESCRIPTION
                 "The acl qos traffic limit ebs value, the valid value is 4-16000."
            ::= { zxr10AclQosTrafficLimitEntry 6 }

  zxr10AclQosTrafficLimitPir OBJECT-TYPE
             SYNTAX  INTEGER
             MAX-ACCESS  read-create
             STATUS  current
             DESCRIPTION
                 "The acl qos traffic limit pir value, the valid value is 64-32000000."
            ::= { zxr10AclQosTrafficLimitEntry 7 }

  zxr10AclQosTrafficLimitPbs OBJECT-TYPE
            SYNTAX  INTEGER
            MAX-ACCESS  read-create
            STATUS  current
            DESCRIPTION
                "The acl qos traffic limit pbs value, the valid value is 4-16000."
            ::= { zxr10AclQosTrafficLimitEntry 8 }

  zxr10AclQosTrafficLimitMode OBJECT-TYPE
             SYNTAX  TrafficColorMode
             MAX-ACCESS  read-create
             STATUS  current
             DESCRIPTION
                 "The acl qos traffic limit work mode, the valid value is blind(0) or aware(1). "
            ::= { zxr10AclQosTrafficLimitEntry 9 }

  zxr10AclQosTrafficLimitRedDscpValue OBJECT-TYPE
             SYNTAX  INTEGER
             MAX-ACCESS  read-create
             STATUS  current
             DESCRIPTION
                 "The acl qos traffic limit red dscp value, the valid value is 0-63."
            ::= { zxr10AclQosTrafficLimitEntry 10 }

  zxr10AclQosTrafficLimitYelDscpValue OBJECT-TYPE
             SYNTAX  INTEGER
             MAX-ACCESS  read-create
             STATUS  current
             DESCRIPTION
                 "The acl qos traffic limit yellow dscp value, the valid value is 0-63."
            ::= { zxr10AclQosTrafficLimitEntry 11 }

  zxr10AclQosTrafficLimitRedDp OBJECT-TYPE
             SYNTAX  TrafficDropPriority
             MAX-ACCESS  read-create
             STATUS  current
             DESCRIPTION
                 "The acl qos traffic limit red drop, the valid value is high(2), low(0), medium(1)."
            ::= { zxr10AclQosTrafficLimitEntry 12 }

  zxr10AclQosTrafficLimitYelDp OBJECT-TYPE
             SYNTAX  TrafficDropPriority
             MAX-ACCESS  read-create
             STATUS  current
             DESCRIPTION
                 "The acl qos traffic limit yellow drop,the valid value is high(2), low(0), medium(1). "
            ::= { zxr10AclQosTrafficLimitEntry 13}

  zxr10AclQosTrafficLimitForwadRed OBJECT-TYPE
             SYNTAX  TrafficForward
             MAX-ACCESS  read-create
             STATUS  current
             DESCRIPTION
                 "The acl qos traffic forwad red,the valid value is forwad-red(1)."
            ::= { zxr10AclQosTrafficLimitEntry 14 }

  zxr10AclQosTrafficLimitDropYellow OBJECT-TYPE
             SYNTAX  TrafficDrop
             MAX-ACCESS  read-create
             STATUS  current
             DESCRIPTION
                 "The acl qos traffic limit drop yellow, the valid value is drop-yellow(1)."
            ::= { zxr10AclQosTrafficLimitEntry 15 }

			
  zxr10AclQosTrafficLimitRowStatus OBJECT-TYPE
        SYNTAX  RowStatus
        MAX-ACCESS  read-create
        STATUS  current
        DESCRIPTION
            "The acl qos Traffic Limit item row status. if it is in valid status, it only 
             can change to invalid status, no other status."       
            ::= {    zxr10AclQosTrafficLimitEntry 16 }

-- traffic mirror

   zxr10AclQosTrafficMirrorTable  OBJECT-TYPE
              SYNTAX  SEQUENCE OF Zxr10AclQosTrafficMirrorEntry
              MAX-ACCESS  not-accessible
              STATUS  current
              DESCRIPTION
                      "The description of zxr10 acl qos traffic mirror configuration.
             It is a list of acl qos traffic mirror entries."
               ::= { zxr10swqos 3 }

    zxr10AclQosTrafficMirrorEntry  OBJECT-TYPE
              SYNTAX  Zxr10AclQosTrafficMirrorEntry
              MAX-ACCESS  not-accessible
              STATUS  current
              DESCRIPTION
                      "A acl qos traffic mirror entry containing objects that
             acl qos traffic mirror infomation,such as:
             mirror action, interface name, row status etc."
              INDEX  { zxr10AclQosTrafficMirrorAclNo,
                       zxr10AclQosTrafficMirrorRuleId }
              ::= { zxr10AclQosTrafficMirrorTable 1 }

    Zxr10AclQosTrafficMirrorEntry ::=
              SEQUENCE {
                zxr10AclQosTrafficMirrorAclNo
                    INTEGER,
                zxr10AclQosTrafficMirrorRuleId
                    INTEGER,
		        -- add for 2802c,songchan 2008,09,11
		        zxr10AclQosTrafficMirrorAclName
                    DisplayString,
                zxr10AclQosTrafficMirrorAction
                    TrafficMirrorAction,
                zxr10AclQosTrafficMirrorIfName 
               	    DisplayString,
		         -- add for 2802c,songchan 2008,09,11
		        zxr10AclQosTrafficMirrorRowStatus
		    RowStatus
              }

   zxr10AclQosTrafficMirrorAclNo  OBJECT-TYPE
              SYNTAX  INTEGER
              MAX-ACCESS  read-only --not-accessible
              STATUS  current
              DESCRIPTION
                      "The acl qos traffic mirror acl number"
              ::= { zxr10AclQosTrafficMirrorEntry 1 }

   zxr10AclQosTrafficMirrorRuleId  OBJECT-TYPE
              SYNTAX  INTEGER
              MAX-ACCESS  read-only
              STATUS  current
              DESCRIPTION
                      "The acl qos traffic mirror ruler id"
              ::= { zxr10AclQosTrafficMirrorEntry 2 }

	zxr10AclQosTrafficMirrorAclName  OBJECT-TYPE
              SYNTAX  DisplayString
              MAX-ACCESS  read-only --not-accessible
              STATUS  current
              DESCRIPTION
                      "The acl qos traffic mirror acl name"
              ::= { zxr10AclQosTrafficMirrorEntry 3 }

   zxr10AclQosTrafficMirrorAction  OBJECT-TYPE
              SYNTAX   TrafficMirrorAction
              MAX-ACCESS  read-create
              STATUS  current
              DESCRIPTION
                      "The acl qos traffic mirror action,cpu 1, interface 2"
             ::= { zxr10AclQosTrafficMirrorEntry 4 }

  zxr10AclQosTrafficMirrorIfName OBJECT-TYPE
              SYNTAX  DisplayString
              MAX-ACCESS  read-create
              STATUS  current
              DESCRIPTION
                  "when traffic mirror to interface, this is the interface's name. and this only for 59 program"
             ::= { zxr10AclQosTrafficMirrorEntry 5 }

			 
   zxr10AclQosTrafficMirrorRowStatus OBJECT-TYPE
        SYNTAX  RowStatus
              MAX-ACCESS  read-create
              STATUS  current
              DESCRIPTION
            "The acl qos Traffic Mirror item row status. if it is in valid status, it only 
             can change to invalid status, no other status.when you creat something, you should enter creatAndGo(4),
			 and when you want to delete it, you should enter destroy(6)."         
             ::= { zxr10AclQosTrafficMirrorEntry 6 }

-- redirect

    zxr10AclQosRedirectTable  OBJECT-TYPE
              SYNTAX  SEQUENCE OF Zxr10AclQosRedirectEntry
              MAX-ACCESS  not-accessible
              STATUS  current
              DESCRIPTION
                      "The description of zxr10 acl qos redirect configuration.
             It is a list of acl qos redirect entries."
              ::= { zxr10swqos 4 }

    zxr10AclQosRedirectEntry  OBJECT-TYPE
              SYNTAX  Zxr10AclQosRedirectEntry
              MAX-ACCESS  not-accessible
              STATUS  current
              DESCRIPTION
                      "A acl qos redirect entry containing objects that
             acl qos redirect infomation,such as:
             globar port name, next-hop ip address, ip address priority etc."
              INDEX  { zxr10AclQosRedirectAclNo,
                       zxr10AclQosRedirectRuleId }
              ::= { zxr10AclQosRedirectTable 1 }

    Zxr10AclQosRedirectEntry ::=
              SEQUENCE {
                zxr10AclQosRedirectAclNo
                    INTEGER,
                zxr10AclQosRedirectRuleId
                    INTEGER,
		 -- add for 2802c,songchan 2008,09,11		  			
		zxr10AclQosRedirectAclName
                     DisplayString,
                zxr10AclQosRedirectFlag
                    RedirectFlag,
                --zxr10AclQosRedirectIndex  delete
                -- INTEGER, delete
                zxr10AclQosRedirectGPort
                    DisplayString,
                zxr10AclQosRedirectIpAddr1
                    IpAddress, 
                zxr10AclQosRedirectIpPri1
                    INTEGER,
                zxr10AclQosRedirectIpAddr2
                    IpAddress, 
                zxr10AclQosRedirectIpPri2
                    INTEGER,
                zxr10AclQosRedirectIpAddr3
                    IpAddress, 
                zxr10AclQosRedirectIpPri3
                    INTEGER,
                zxr10AclQosRedirectIpAddr4
                    IpAddress,   
                zxr10AclQosRedirectIpPri4
                    INTEGER,
                zxr10AclQosRedirectIpAddr5
                    IpAddress, 
                zxr10AclQosRedirectIpPri5
                    INTEGER,
                zxr10AclQosRedirectIpAddr6
                    IpAddress ,  
                zxr10AclQosRedirectIpPri6
                    INTEGER,
                zxr10AclQosRedirectIpAddr7
                    IpAddress, 
                zxr10AclQosRedirectIpPri7
                    INTEGER,
                zxr10AclQosRedirectIpAddr8
                    IpAddress,   
                zxr10AclQosRedirectIpPri8
                    INTEGER,   
				zxr10AclQosRedirectIPv6Addr
		            InetAddressIPv6,
				zxr10AclQosRedirectGreenOnly
		            GreenOnlyType,					
		-- add for 2802c,songchan 2008,09,11
		zxr10AclQosRedirectRowStatus
		            RowStatus

				
                }

   zxr10AclQosRedirectAclNo  OBJECT-TYPE
              SYNTAX  INTEGER
              MAX-ACCESS  read-only
              STATUS  current
              DESCRIPTION
                      "The acl qos redirect acl number"
              ::= { zxr10AclQosRedirectEntry 1 }

   zxr10AclQosRedirectRuleId  OBJECT-TYPE
              SYNTAX  INTEGER
              MAX-ACCESS  read-only
              STATUS  current
              DESCRIPTION
                      "The acl qos redirect Ruler id"
              ::= { zxr10AclQosRedirectEntry 2 }

    zxr10AclQosRedirectAclName  OBJECT-TYPE
              SYNTAX   DisplayString
              MAX-ACCESS  read-only
              STATUS  current
              DESCRIPTION
                      "The acl qos redirect acl name"
              ::= { zxr10AclQosRedirectEntry 3 }

   zxr10AclQosRedirectFlag
  			OBJECT-TYPE
              SYNTAX   RedirectFlag
              MAX-ACCESS  read-create
              STATUS  current
              DESCRIPTION
                      "The acl qos redirect flag,cpu 1, interface 2,next-hop 3, next-hop-ipv6(4)"
             ::= { zxr10AclQosRedirectEntry 4 }

   --zxr10AclQosRedirectIndex OBJECT-TYPE
              -- SYNTAX  INTEGER
              --MAX-ACCESS  read-create
              -- STATUS  current
              --DESCRIPTION
                 -- ""
              -- ::= { zxr10AclQosRedirectEntry 4 }

   zxr10AclQosRedirectGPort OBJECT-TYPE
              SYNTAX  DisplayString
              MAX-ACCESS  read-create
              STATUS  current
              DESCRIPTION
                  "The acl qos redirect interface name"
             ::= { zxr10AclQosRedirectEntry 5 } 
             
   zxr10AclQosRedirectIpAddr1 OBJECT-TYPE
              SYNTAX  IpAddress
              MAX-ACCESS  read-create
              STATUS  current
              DESCRIPTION
                  "The first redirect next-hop ip adderss"
             ::= { zxr10AclQosRedirectEntry 6 }    
             
   zxr10AclQosRedirectIpPri1 OBJECT-TYPE    
              SYNTAX  INTEGER
              MAX-ACCESS  read-create
              STATUS  current
              DESCRIPTION
                  "The priority of the firest ip address,0-7"
             ::= { zxr10AclQosRedirectEntry 7 }
             
   zxr10AclQosRedirectIpAddr2 OBJECT-TYPE
              SYNTAX  IpAddress
              MAX-ACCESS  read-create
              STATUS  current
              DESCRIPTION
                  "The second redirect next-hop ip adderss"
             ::= { zxr10AclQosRedirectEntry 8 }

   zxr10AclQosRedirectIpPri2 OBJECT-TYPE
              SYNTAX  INTEGER
              MAX-ACCESS  read-create
              STATUS  current
              DESCRIPTION
                  "The priority of the second ip address,0-7"
             ::= { zxr10AclQosRedirectEntry 9 }
          
   zxr10AclQosRedirectIpAddr3 OBJECT-TYPE
              SYNTAX  IpAddress
              MAX-ACCESS  read-create
              STATUS  current
              DESCRIPTION
                  "The third redirect next-hop ip adderss"
             ::= { zxr10AclQosRedirectEntry 10 }    
             
   zxr10AclQosRedirectIpPri3 OBJECT-TYPE    
              SYNTAX  INTEGER
              MAX-ACCESS  read-create
              STATUS  current
              DESCRIPTION
                  "The priority of the third ip address,0-7"
             ::= { zxr10AclQosRedirectEntry 11 }
             
   zxr10AclQosRedirectIpAddr4 OBJECT-TYPE
              SYNTAX  IpAddress
              MAX-ACCESS  read-create
              STATUS  current
              DESCRIPTION
                  "The fourth redirect next-hop ip adderss"
             ::= { zxr10AclQosRedirectEntry 12 }

   zxr10AclQosRedirectIpPri4 OBJECT-TYPE
              SYNTAX  INTEGER
              MAX-ACCESS  read-create
              STATUS  current
              DESCRIPTION
                  "The priority of the fourth ip address,0-7"
             ::= { zxr10AclQosRedirectEntry 13 }
  
   zxr10AclQosRedirectIpAddr5 OBJECT-TYPE
              SYNTAX  IpAddress
              MAX-ACCESS  read-create
              STATUS  current
              DESCRIPTION
                  "The fifth redirect next-hop ip adderss"
             ::= { zxr10AclQosRedirectEntry 14 }    
             
   zxr10AclQosRedirectIpPri5 OBJECT-TYPE    
              SYNTAX  INTEGER
              MAX-ACCESS  read-create
              STATUS  current
              DESCRIPTION
                  "The priority of the fifth ip address,0-7"
             ::= { zxr10AclQosRedirectEntry 15 }
             
   zxr10AclQosRedirectIpAddr6 OBJECT-TYPE
              SYNTAX  IpAddress
              MAX-ACCESS  read-create
              STATUS  current
              DESCRIPTION
                  "The sixth redirect next-hop ip adderss"
             ::= { zxr10AclQosRedirectEntry 16 }

   zxr10AclQosRedirectIpPri6 OBJECT-TYPE
              SYNTAX  INTEGER
              MAX-ACCESS  read-create
              STATUS  current
              DESCRIPTION
                  "The priority of the sixth ip address,0-7"
             ::= { zxr10AclQosRedirectEntry 17 }
      
   zxr10AclQosRedirectIpAddr7 OBJECT-TYPE
              SYNTAX  IpAddress
              MAX-ACCESS  read-create
              STATUS  current
              DESCRIPTION
                  "The seventh redirect next-hop ip adderss"
             ::= { zxr10AclQosRedirectEntry 18 }    
             
   zxr10AclQosRedirectIpPri7 OBJECT-TYPE    
              SYNTAX  INTEGER
              MAX-ACCESS  read-create
              STATUS  current
              DESCRIPTION
                  "The priority of the seventh ip address,0-7"
             ::= { zxr10AclQosRedirectEntry 19 }
             
   zxr10AclQosRedirectIpAddr8 OBJECT-TYPE
              SYNTAX  IpAddress
              MAX-ACCESS  read-create
              STATUS  current
              DESCRIPTION
                  "The eighth redirect next-hop ip adderss"
             ::= { zxr10AclQosRedirectEntry 20 }

   zxr10AclQosRedirectIpPri8 OBJECT-TYPE
              SYNTAX  INTEGER
              MAX-ACCESS  read-create
              STATUS  current
              DESCRIPTION
                  "The priority of the eighth ip address,0-7"
             ::= { zxr10AclQosRedirectEntry 21 }
                            
	zxr10AclQosRedirectIPv6Addr OBJECT-TYPE
              SYNTAX  InetAddressIPv6
              MAX-ACCESS   read-create
              STATUS  current
              DESCRIPTION
                  " The Redirect next-hop is IPv6 Address,support by 59 device."
             ::= { zxr10AclQosRedirectEntry 22}

	zxr10AclQosRedirectGreenOnly OBJECT-TYPE
              SYNTAX  GreenOnlyType
              MAX-ACCESS   read-create
              STATUS  current
              DESCRIPTION
                  "The Redirect action only to green packet, support by 59 device."
             ::= { zxr10AclQosRedirectEntry 23 }
                            
   zxr10AclQosRedirectRowStatus OBJECT-TYPE
        SYNTAX  RowStatus
        MAX-ACCESS  read-create
        STATUS  current
        DESCRIPTION
            "The acl qos Redirect item row status. if it is in valid status, it only 
             can change to invalid status, no other status.when you creat something, you should enter creatAndGo(4),
			 and when you want to delete it, you should enter destroy(6)."          
             ::= { zxr10AclQosRedirectEntry 24 }
	
	
-- traffic statistics
-- all add for 2802c,songchan 2008,09,11

   zxr10AclQosTrafficStatisticsTable  OBJECT-TYPE
              SYNTAX  SEQUENCE OF Zxr10AclQosTrafficStatisticsEntry
              MAX-ACCESS  not-accessible
              STATUS  current
              DESCRIPTION
                      "The description of zxr10 acl qos traffic statistics configuration.
             It is a list of acl qos traffic statistics entries."
               ::= { zxr10swqos 5 }

    zxr10AclQosTrafficStatisticsEntry  OBJECT-TYPE
              SYNTAX  Zxr10AclQosTrafficStatisticsEntry
              MAX-ACCESS  not-accessible
              STATUS  current
              DESCRIPTION
                      "A acl qos traffic statistics entry containing objects that
             acl qos traffic statistics infomation,such as:
             pkt-type, statistics type etc."
              INDEX  { zxr10AclQosTrafficStatisticsAclNo,
                       zxr10AclQosTrafficStatisticsRuleId }
              ::= { zxr10AclQosTrafficStatisticsTable 1 }

    Zxr10AclQosTrafficStatisticsEntry ::=
              SEQUENCE {
                zxr10AclQosTrafficStatisticsAclNo
                    INTEGER,
                zxr10AclQosTrafficStatisticsRuleId
                    INTEGER,
				zxr10AclQosTrafficStatisticsAclName
                    DisplayString,
                zxr10AclQosTrafficStatisticsPkttype
                    Packettype,                
                zxr10AclQosTrafficStatisticsStatype
                	Statisticstype,
				zxr10AclQosTrafficStatisticsRowStatus
				    RowStatus
              }

   zxr10AclQosTrafficStatisticsAclNo  OBJECT-TYPE
              SYNTAX   INTEGER
              MAX-ACCESS  read-only --not-accessible
              STATUS  current
              DESCRIPTION
                      "The acl qos traffic Statistics acl number"
              ::= { zxr10AclQosTrafficStatisticsEntry 1 }

   zxr10AclQosTrafficStatisticsRuleId  OBJECT-TYPE
              SYNTAX  INTEGER
              MAX-ACCESS  read-only
              STATUS  current
              DESCRIPTION
                      "The acl qos traffic Statistics ruler id"
              ::= { zxr10AclQosTrafficStatisticsEntry 2 }

	zxr10AclQosTrafficStatisticsAclName  OBJECT-TYPE
              SYNTAX   DisplayString
              MAX-ACCESS  read-only --not-accessible
              STATUS  current
              DESCRIPTION
                      "The acl qos traffic Statistics acl name"
              ::= { zxr10AclQosTrafficStatisticsEntry 3 }
			  
   zxr10AclQosTrafficStatisticsPkttype  OBJECT-TYPE
              SYNTAX   Packettype
              MAX-ACCESS  read-create
              STATUS  current
              DESCRIPTION
                      "The acl qos traffic Statistics pkt-type,all 0, green 1,red 2,yellow 3"
              ::= { zxr10AclQosTrafficStatisticsEntry 4 }

    zxr10AclQosTrafficStatisticsStatype OBJECT-TYPE
               SYNTAX  Statisticstype
               MAX-ACCESS  read-create
               STATUS  current
               DESCRIPTION
                   "The acl qos traffic Statistics statistics type :byte 1,packet 0"
              ::= { zxr10AclQosTrafficStatisticsEntry 5 }
			 
	zxr10AclQosTrafficStatisticsRowStatus OBJECT-TYPE
        SYNTAX  RowStatus
        MAX-ACCESS  read-create
        STATUS  current
        DESCRIPTION
            "The acl qos Traffic Statistics item row status. if it is in valid status, it only 
             can change to invalid status, no other status.when you creat something, you should enter creatAndGo(4),
			 and when you want to delete it, you should enter destroy(6)."         
             ::= {    zxr10AclQosTrafficStatisticsEntry 6 }	 
			 
	
                            
     END
