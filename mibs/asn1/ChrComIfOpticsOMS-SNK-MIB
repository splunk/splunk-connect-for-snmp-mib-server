ChrComIfOpticsOMS-SNK-MIB

--FORCE-INCLUDE	<mib.h>
--FORCE-INCLUDE	<snmpdefs.h>
--FORCE-INCLUDE	"mibhand.h"

	DEFINITIONS  ::=  BEGIN

IMPORTS
	OBJECT-TYPE, Counter32			FROM  SNMPv2-SMI
	Integer32, Unsigned32			FROM  SNMPv2-SMI
	chrComIfOptics				FROM  Chromatis-MIB
	chrComIfifIndex					FROM  ChrComIfifTable-MIB
	Agcppc					FROM  OTSControlTypes-MIB
	APSDSTATE				FROM  OpaAPSDSTATE-MIB
	TruthValue				FROM  ChrTyp-MIB
	LaserActivation				FROM  LaserActivation-MIB;

-- chrComIfOpticsOMS-SNK Table

chrComIfOpticsOMS-SNKTable		OBJECT-TYPE
	SYNTAX		SEQUENCE OF ChrComIfOpticsOMS-SNKEntry
	MAX-ACCESS	not-accessible
	STATUS		current
	DESCRIPTION
	"The OMS is managed only for the Ring side of the Metropolis Network (not for the Trib side)."
	::= { chrComIfOptics 3}

chrComIfOpticsOMS-SNKEntry		OBJECT-TYPE
	SYNTAX		ChrComIfOpticsOMS-SNKEntry
	MAX-ACCESS	not-accessible
	STATUS		current
	DESCRIPTION
	""
	INDEX  {  chrComIfifIndex }

--DEFAULT  get-function-async  MNIL_GetRoutine
--DEFAULT  set-function-async  MNIL_SetRoutine
--DEFAULT  next-function-async MNIL_NextRoutine
--DEFAULT  test-function-async MNIL_TestRoutine
--DEFAULT  cookie "OMS-SNK"
	::= { chrComIfOpticsOMS-SNKTable  1 }

ChrComIfOpticsOMS-SNKEntry  ::=
	SEQUENCE  {
	chrComIfOpticsOmsSnkNumOfPrecedingOPAs Integer32	(-1..32),
	chrComIfOpticsOmsSnkDWDMInputPower	Integer32	(-501..300),
	chrComIfOpticsOmsSnkOPALOOCThr	Integer32	(-501..300),
	chrComIfOpticsOmsSnkParamForOPALOOCThr Integer32	(-501..300),
	chrComIfOpticsOmsSnkLOOPThr		Integer32	(-501..300),
	chrComIfOpticsOmsSnkReceived1310Power	Integer32	(-501..300),
	chrComIfOpticsOmsSnkReceivedLambdaPower Integer32	(-501..300),
	chrComIfOpticsOmsSnkBackplaneAttenuatorLambda OCTET STRING	(SIZE (0..160)),
	chrComIfOpticsOmsSnkBackplaneAttenuator1310 Integer32	(-1..350),
	chrComIfOpticsOmsSnkParamForRxLambdaLOOCThr Integer32	(-501..300),
	chrComIfOpticsOmsSnkRxLambdaLOOCThr	Integer32	(-501..300),
	chrComIfOpticsOmsSnkRx1310LOOCThr	Integer32	(-501..300),
	chrComIfOpticsOmsSnkOchRRx1310LOOCThr	Integer32	(-501..300),
	chrComIfOpticsOmsSnkPreOPADWDMOutPower Integer32	(-501..300),
	chrComIfOpticsOmsSnkPreOPAOutLOOPThr	Integer32	(-501..300),
	chrComIfOpticsOmsSnkPreOPASafetyThr	Integer32	(-501..300),
	chrComIfOpticsOmsSnkOPAModeOfOperation Agcppc,
	chrComIfOpticsOmsSnkOPAExpectedGain	Integer32	(-1..350),
	chrComIfOpticsOmsSnkOPAActualGain	Integer32	(-1..350),
	chrComIfOpticsOmsSnkOPAExpectedPumpPower Integer32	(-1..2000),
	chrComIfOpticsOmsSnkOPAActualPumpPower Integer32	(-1..2000),
	chrComIfOpticsOmsSnkOPAAPSDState	APSDSTATE,
	chrComIfOpticsOmsSnkOPAPumpRestartAction TruthValue,
	chrComIfOpticsOmsSnkOPAPumpActivationStatus LaserActivation,
	chrComIfOpticsOmsSnkOPAExpectedAttenuatorAttenuation Integer32	(-1..4000),
	chrComIfOpticsOmsSnkOPAActualAttenuatorAttenuation Integer32	(-1..400),
	chrComIfOpticsOmsSnkOPAPumpTemperature Unsigned32	(99..500),
	chrComIfOpticsOmsSnkOPAPumpBiasCurrent Integer32	(-1..4000),
	chrComIfOpticsAlarmVector		Unsigned32	(0..4294967295),
	chrComIfOpticsAlarmSeverityProfileIndex Unsigned32	(0..4294967295)
}

chrComIfOpticsOmsSnkNumOfPrecedingOPAs 	OBJECT-TYPE
	SYNTAX		Integer32	(-1..32)
	MAX-ACCESS 	read-write
	STATUS 		current
	DESCRIPTION
	""
	::= { chrComIfOpticsOMS-SNKEntry  1 }

chrComIfOpticsOmsSnkDWDMInputPower 	OBJECT-TYPE
	SYNTAX		Integer32	(-501..300)
	MAX-ACCESS 	read-only
	STATUS 		current
	DESCRIPTION
	"The aggregated optical power of all the DWDM input channels (without the 1310nm channel)."
	::= { chrComIfOpticsOMS-SNKEntry  2 }

chrComIfOpticsOmsSnkOPALOOCThr 	OBJECT-TYPE
	SYNTAX		Integer32	(-501..300)
	MAX-ACCESS 	read-only
	STATUS 		current
	DESCRIPTION
	"Threshold for the OMS-SNK DWDM Input Power, indicating Loss Of Optical DWDM Channels at the input to the Pre-OPA/in-line-OPA."
	::= { chrComIfOpticsOMS-SNKEntry  3 }

chrComIfOpticsOmsSnkParamForOPALOOCThr 	OBJECT-TYPE
	SYNTAX		Integer32	(-501..300)
	MAX-ACCESS 	read-write
	STATUS 		current
	DESCRIPTION
	"Input parameter for calculating OMS-SNK LOOC Threshold (for pre-OPA/in-line-OPA only)."
	::= { chrComIfOpticsOMS-SNKEntry  4 }

chrComIfOpticsOmsSnkLOOPThr 	OBJECT-TYPE
	SYNTAX		Integer32	(-501..300)
	MAX-ACCESS 	read-write
	STATUS 		current
	DESCRIPTION
	"Threshold for the OMS-SNK DWDM Input Power indicating Loss Of Optical power in the DWDM band at the input to ADOM/OMDM."
	::= { chrComIfOpticsOMS-SNKEntry  5 }

chrComIfOpticsOmsSnkReceived1310Power 	OBJECT-TYPE
	SYNTAX		Integer32	(-501..300)
	MAX-ACCESS 	read-only
	STATUS 		current
	DESCRIPTION
	"The optical power monitored on 1310 Receive point.

"
	::= { chrComIfOpticsOMS-SNKEntry  6 }

chrComIfOpticsOmsSnkReceivedLambdaPower 	OBJECT-TYPE
	SYNTAX		Integer32	(-501..300)
	MAX-ACCESS 	read-only
	STATUS 		current
	DESCRIPTION
	"The optical power monitored on ADOM Lambda Receive point."
	::= { chrComIfOpticsOMS-SNKEntry  7 }

chrComIfOpticsOmsSnkBackplaneAttenuatorLambda 	OBJECT-TYPE
	SYNTAX		OCTET STRING	(SIZE (0..160))
	MAX-ACCESS 	read-write
	STATUS 		current
	DESCRIPTION
	"Attenuation in dB. 
Zero when no backplane Attenuator exists.
"
	::= { chrComIfOpticsOMS-SNKEntry  8 }

chrComIfOpticsOmsSnkBackplaneAttenuator1310 	OBJECT-TYPE
	SYNTAX		Integer32	(-1..350)
	MAX-ACCESS 	read-write
	STATUS 		current
	DESCRIPTION
	"Attenuation in dB. 
Zero when no backplane Attenuator exists.
"
	::= { chrComIfOpticsOMS-SNKEntry  9 }

chrComIfOpticsOmsSnkParamForRxLambdaLOOCThr 	OBJECT-TYPE
	SYNTAX		Integer32	(-501..300)
	MAX-ACCESS 	read-write
	STATUS 		current
	DESCRIPTION
	"Input parameter for calculating OMS-SNK Received lambda LOOC threshold"
	::= { chrComIfOpticsOMS-SNKEntry  10 }

chrComIfOpticsOmsSnkRxLambdaLOOCThr 	OBJECT-TYPE
	SYNTAX		Integer32	(-501..300)
	MAX-ACCESS 	read-only
	STATUS 		current
	DESCRIPTION
	"Loop Threshold of OMS-SNK Received lambda power. 

"
	::= { chrComIfOpticsOMS-SNKEntry  11 }

chrComIfOpticsOmsSnkRx1310LOOCThr 	OBJECT-TYPE
	SYNTAX		Integer32	(-501..300)
	MAX-ACCESS 	read-only
	STATUS 		current
	DESCRIPTION
	"Loop threshold of OMS-SNK Received 1310 Power. "
	::= { chrComIfOpticsOMS-SNKEntry  12 }

chrComIfOpticsOmsSnkOchRRx1310LOOCThr 	OBJECT-TYPE
	SYNTAX		Integer32	(-501..300)
	MAX-ACCESS 	read-write
	STATUS 		current
	DESCRIPTION
	"A duplication of the OCH-R Received 1310 Looc threshold."
	::= { chrComIfOpticsOMS-SNKEntry  13 }

chrComIfOpticsOmsSnkPreOPADWDMOutPower 	OBJECT-TYPE
	SYNTAX		Integer32	(-501..300)
	MAX-ACCESS 	read-only
	STATUS 		current
	DESCRIPTION
	"Total Optical Power Monitored at the output of a Pre-OPA.

"
	::= { chrComIfOpticsOMS-SNKEntry  14 }

chrComIfOpticsOmsSnkPreOPAOutLOOPThr 	OBJECT-TYPE
	SYNTAX		Integer32	(-501..300)
	MAX-ACCESS 	read-write
	STATUS 		current
	DESCRIPTION
	"This is a threshold on the output power of the pre-OPA."
	::= { chrComIfOpticsOMS-SNKEntry  15 }

chrComIfOpticsOmsSnkPreOPASafetyThr 	OBJECT-TYPE
	SYNTAX		Integer32	(-501..300)
	MAX-ACCESS 	read-write
	STATUS 		current
	DESCRIPTION
	"This is a threshold on the output power of the pre-OPA."
	::= { chrComIfOpticsOMS-SNKEntry  16 }

chrComIfOpticsOmsSnkOPAModeOfOperation 	OBJECT-TYPE
	SYNTAX		Agcppc
	MAX-ACCESS 	read-write
	STATUS 		current
	DESCRIPTION
	"§ (Automatic Gain Control   -AGC  Default)
§ Automatic Pump Power Control  PPC
"
	::= { chrComIfOpticsOMS-SNKEntry  17 }

chrComIfOpticsOmsSnkOPAExpectedGain 	OBJECT-TYPE
	SYNTAX		Integer32	(-1..350)
	MAX-ACCESS 	read-write
	STATUS 		current
	DESCRIPTION
	"Integer32, Units of 0.1 db.

0  35 db (10dB)
"
	::= { chrComIfOpticsOMS-SNKEntry  18 }

chrComIfOpticsOmsSnkOPAActualGain 	OBJECT-TYPE
	SYNTAX		Integer32	(-1..350)
	MAX-ACCESS 	read-only
	STATUS 		current
	DESCRIPTION
	"Integer32, Units of 0.1 db.

0  35 db
"
	::= { chrComIfOpticsOMS-SNKEntry  19 }

chrComIfOpticsOmsSnkOPAExpectedPumpPower 	OBJECT-TYPE
	SYNTAX		Integer32	(-1..2000)
	MAX-ACCESS 	read-write
	STATUS 		current
	DESCRIPTION
	"The Desired EDFA pump power of pre-/in-line-OPA module. "
	::= { chrComIfOpticsOMS-SNKEntry  20 }

chrComIfOpticsOmsSnkOPAActualPumpPower 	OBJECT-TYPE
	SYNTAX		Integer32	(-1..2000)
	MAX-ACCESS 	read-only
	STATUS 		current
	DESCRIPTION
	"The Actual EDFA pump power of pre-/in-line-OPA module. "
	::= { chrComIfOpticsOMS-SNKEntry  21 }

chrComIfOpticsOmsSnkOPAAPSDState 	OBJECT-TYPE
	SYNTAX		APSDSTATE
	MAX-ACCESS 	read-write
	STATUS 		current
	DESCRIPTION
	"Controlling the Automatic Pump Shut Down (APSD) mode. "
	::= { chrComIfOpticsOMS-SNKEntry  22 }

chrComIfOpticsOmsSnkOPAPumpRestartAction 	OBJECT-TYPE
	SYNTAX		TruthValue
	MAX-ACCESS 	read-write
	STATUS 		current
	DESCRIPTION
	"Enables remote operation which is equivalent to the restart push button of the pre-/in-line-OPA."
	::= { chrComIfOpticsOMS-SNKEntry  23 }

chrComIfOpticsOmsSnkOPAPumpActivationStatus 	OBJECT-TYPE
	SYNTAX		LaserActivation
	MAX-ACCESS 	read-only
	STATUS 		current
	DESCRIPTION
	"Pre-/in-line-OPA Pump Laser ON/OFF Actual status. "
	::= { chrComIfOpticsOMS-SNKEntry  24 }

chrComIfOpticsOmsSnkOPAExpectedAttenuatorAttenuation 	OBJECT-TYPE
	SYNTAX		Integer32	(-1..4000)
	MAX-ACCESS 	read-write
	STATUS 		current
	DESCRIPTION
	"The expected Attenuation of the attenuator at the output of the OPA  "
	::= { chrComIfOpticsOMS-SNKEntry  25 }

chrComIfOpticsOmsSnkOPAActualAttenuatorAttenuation 	OBJECT-TYPE
	SYNTAX		Integer32	(-1..400)
	MAX-ACCESS 	read-only
	STATUS 		current
	DESCRIPTION
	"The actual Attenuation of the attenuator at the output of the OPA"
	::= { chrComIfOpticsOMS-SNKEntry  26 }

chrComIfOpticsOmsSnkOPAPumpTemperature 	OBJECT-TYPE
	SYNTAX		Unsigned32	(99..500)
	MAX-ACCESS 	read-only
	STATUS 		current
	DESCRIPTION
	"The temperature of the module."
	::= { chrComIfOpticsOMS-SNKEntry  27 }

chrComIfOpticsOmsSnkOPAPumpBiasCurrent 	OBJECT-TYPE
	SYNTAX		Integer32	(-1..4000)
	MAX-ACCESS 	read-only
	STATUS 		current
	DESCRIPTION
	""
	::= { chrComIfOpticsOMS-SNKEntry  28 }

chrComIfOpticsAlarmVector 	OBJECT-TYPE
	SYNTAX		Unsigned32	(0..4294967295)
	MAX-ACCESS 	read-only
	STATUS 		current
	DESCRIPTION
	""
	::= { chrComIfOpticsOMS-SNKEntry  29 }

chrComIfOpticsAlarmSeverityProfileIndex 	OBJECT-TYPE
	SYNTAX		Unsigned32	(0..4294967295)
	MAX-ACCESS 	read-write
	STATUS 		current
	DESCRIPTION
	""
	::= { chrComIfOpticsOMS-SNKEntry  30 }


END
