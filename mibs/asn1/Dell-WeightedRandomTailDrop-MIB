Dell-WeightedRandomTailDrop-MIB DEFINITIONS ::= BEGIN

-- Title:      Dell Switch Interfaces Private
-- Version:    7.50
-- Date:       29 Sep 2009

IMPORTS
    rnd                                          FROM Dell-MIB
    OBJECT-TYPE, MODULE-IDENTITY                 FROM SNMPv2-SMI;

rlWeightedRandomTailDrop MODULE-IDENTITY
        LAST-UPDATED "200909290000Z"
        ORGANIZATION "Dell"
        CONTACT-INFO
              "www.dell.com"
        DESCRIPTION
            "<description>"
        REVISION "200909290000Z"
        DESCRIPTION
            "The private MIB module definition for Weighted Random Tail Drop MIB."
        ::= { rnd 146 }

rlWeightedRandomTailDropCurrentStatus OBJECT-TYPE
    SYNTAX  INTEGER {
        enable(0),
        disable(1)
    }
    MAX-ACCESS  read-only
    STATUS  current
    DESCRIPTION
        "Show the current Weighted Random Tail Drop status"
    ::= { rlWeightedRandomTailDrop 1 }

rlWeightedRandomTailDropStatusAfterReset OBJECT-TYPE
    SYNTAX  INTEGER {
        enable(0),
        disable(1)
    }
    MAX-ACCESS  read-write
    STATUS  current
    DESCRIPTION
        "Set the Weighted Random Tail Drop status after reset"
    ::= { rlWeightedRandomTailDrop 2 }

END
