-- ZyXEL Communications Corporation
-- Private Enterprise MIB definition 
  
-- This file describes the ZyXEL Communications Corporation Enterprise MIB.
-- It contains ZyXEL products OIDs, and common managed objects.

-- $Log: ZYXEL-POWER-ETHERNET-MIB.mib $
-- Revision 1.9  2013/12/06 07:08:05  ccho
-- remove uncessary imports
-- Revision 1.8  2013/11/06 05:42:16  ccho
-- fix mib style
-- Revision 1.7  2013/06/26 07:14:14  Mandy
-- Support notified trap for error recovered
-- Revision 1.6  2012/11/16 08:03:56  cfchen
-- user-defined max power
-- Revision 1.5  2012/10/25 03:50:41  Kevin
-- correct entry name
-- Revision 1.4  2012/09/19 07:44:41  Kevin
-- if it's leaf node, revise the vender name from zyxel to zy
-- Revision 1.3  2012/08/22 09:47:47  Kevin
-- clean warning for SNMPc
-- Revision 1.2  2012/07/05 06:24:22  Kevin
-- 1. upgrade from SNMP to SNMPv2 
-- 2. clean warning
-- Revision 1.1  2012/05/30 07:50:26  Kevin
-- Initial revision

ZYXEL-POWER-ETHERNET-MIB DEFINITIONS ::= BEGIN

    IMPORTS
	OBJECT-TYPE
		FROM SNMPv2-SMI			-- RFC2578	
		
	MODULE-IDENTITY
		FROM SNMPv2-SMI

	dot1dBasePort
       	FROM BRIDGE-MIB

    ifIndex
    	FROM IF-MIB					-- RFC2863

    NOTIFICATION-TYPE
        FROM SNMPv2-SMI
 
 	esMgmt			
		FROM ZYXEL-ES-SMI;

	zyxelPoe MODULE-IDENTITY
		LAST-UPDATED	"201207010000Z"    
		ORGANIZATION "Enterprise Solution ZyXEL"     
		CONTACT-INFO
			""	   
		DESCRIPTION
			"The subtree for Power over Ethernet (PoE)"
		::= { esMgmt 59 } 

	zyxelPoeSetup     		OBJECT IDENTIFIER ::= { zyxelPoe 1 } 
	zyxelPoeStatus     		OBJECT IDENTIFIER ::= { zyxelPoe 2 } 
	zyxelPoeTrapInfoObject     	OBJECT IDENTIFIER ::= { zyxelPoe 3 }
	zyxelPoeNotifications   OBJECT IDENTIFIER ::= { zyxelPoe 4 }


-- *******************************************************************
-- *
-- * zyxelPoeSetup
-- *
-- *******************************************************************

-- zyxelPoeMode
		zyPoeMode OBJECT-TYPE
        SYNTAX  INTEGER{
			consumption(0),
			classification(1)
		}
        MAX-ACCESS  read-write
        STATUS  current
        DESCRIPTION
                    "Set POE Mode Setup Consumption mode (0), Classification mode (1)."
        ::= { zyxelPoeSetup 1 }

-- zyxelPoePsePortTable
        zyxelPoePsePortTable OBJECT-TYPE
        SYNTAX	SEQUENCE OF ZyxelPoePsePortEntry
        MAX-ACCESS  not-accessible
        STATUS  current
        DESCRIPTION
					"The table contains power ethernet port information. "
        ::= { zyxelPoeSetup 2 }

		zyxelPoePsePortEntry OBJECT-TYPE
        SYNTAX	ZyxelPoePsePortEntry
        MAX-ACCESS	not-accessible
        STATUS	current
        DESCRIPTION    	
					"An entry contains power ethernet port information. "
        INDEX          	{ dot1dBasePort }
        ::= { zyxelPoePsePortTable 1 }	
		
        ZyxelPoePsePortEntry ::=
		SEQUENCE {
        	zyPoePsePortMaxPower	INTEGER
        }

		zyPoePsePortMaxPower OBJECT-TYPE
        SYNTAX	INTEGER
        MAX-ACCESS	read-write
        STATUS	current
        DESCRIPTION    	
						"PoE PSE port user-defined max power expressed in milliwatt,
						 Valid value should be between 1000 and 33000,in steps of 200.
						 Value 0(Default) means to disable user-defined max power."
						 
        ::= { zyxelPoePsePortEntry 1 }  		
		
		
-- zyxelPoePsePortInfoTable
        zyxelPoePsePortInfoTable OBJECT-TYPE
        SYNTAX	SEQUENCE OF ZyxelPoePsePortInfoEntry
        MAX-ACCESS  not-accessible
        STATUS  current
        DESCRIPTION
					"The table contains power ethernet port information. "
        ::= { zyxelPoeStatus 1 }

		zyxelPoePsePortInfoEntry OBJECT-TYPE
        SYNTAX	ZyxelPoePsePortInfoEntry
        MAX-ACCESS	not-accessible
        STATUS	current
        DESCRIPTION    	
					"An entry contains power ethernet port information. "
        INDEX          	{ dot1dBasePort }
        ::= { zyxelPoePsePortInfoTable 1 }	
		
        ZyxelPoePsePortInfoEntry ::=
		SEQUENCE {
        	zyPoePsePortInfoPowerConsumption	INTEGER
        }

		zyPoePsePortInfoPowerConsumption OBJECT-TYPE
        SYNTAX	INTEGER
        MAX-ACCESS	read-only
        STATUS	current
        DESCRIPTION    	
						"PoE PSE port power consumption expressed in milliwatt."
        ::= { zyxelPoePsePortInfoEntry 1 }  
        
    	zyPoeTrapPsePowerSupplyFailedReason OBJECT-TYPE
        SYNTAX  INTEGER { 
			internalPowerSupplyForPoeFailed(0), 
			rpsForPoeFailed(1), 
			rpsFanFailed(2), 
			rpsOverTemperature(3)  
			}
        MAX-ACCESS  not-accessible
        STATUS  current
        DESCRIPTION
			"Internal-power-supply-for-PoE-failed(0): Internal power supply for PoE  has failed.
			RPS-for-PoE-failed(1): External power supply for PoE (RPS) has failed.
			RPS-fan-failed(2): RPS fan has failed.
			RPS-over-temperature(3): RPS temperature is out of the normal operation range."             
        ::= { zyxelPoeTrapInfoObject 1 }   
              

        zyPoePowerPortOverload NOTIFICATION-TYPE
        OBJECTS {
			ifIndex
        }
        STATUS  current
        DESCRIPTION
			"Port is off, due to the overload state according to 802.3af."
		::= { zyxelPoeNotifications 1 } 
		
		zyPoePowerPortShortCircuit NOTIFICATION-TYPE
        OBJECTS {
			ifIndex
        }
        STATUS  current
        DESCRIPTION
			"Port is off, due to short circuit."
		::= { zyxelPoeNotifications 2 }
		 
		zyPoePowerPortOverSystemBudget NOTIFICATION-TYPE
        OBJECTS {
			ifIndex
        }
        STATUS  current
        DESCRIPTION
			"Port is off, due to over system budget."
		::= { zyxelPoeNotifications 3 } 
				   
        zyPoePsePowerSupplyFailed  NOTIFICATION-TYPE
        OBJECTS {
			zyPoeTrapPsePowerSupplyFailedReason
        }
        STATUS  current
        DESCRIPTION
			"PSE power supply failed, due to the reason of zyxelPoeTrapPsePowerSupplyFailedReason."
		::= { zyxelPoeNotifications 4 } 	   		   
		              
        zyPoePowerPortOverloadRecovered NOTIFICATION-TYPE
        OBJECTS {
			ifIndex
        }
        STATUS  current
        DESCRIPTION
			"Port is on, since recovered from overload state."
		::= { zyxelPoeNotifications 5 } 
		
		zyPoePowerPortShortCircuitRecovered NOTIFICATION-TYPE
        OBJECTS {
			ifIndex
        }
        STATUS  current
        DESCRIPTION
			"Port is on, since recovered from short circuit."
		::= { zyxelPoeNotifications 6 }
		 
		zyPoePowerPortOverSystemBudgetRecovered NOTIFICATION-TYPE
        OBJECTS {
			ifIndex
        }
        STATUS  current
        DESCRIPTION
			"Port is on, since recovered from over system budget."
		::= { zyxelPoeNotifications 7 } 
		
END
