--
-- OPTIX-SONET-SYS-MIB.mib
-- MIB generated by MG-SOFT Visual MIB Builder Version 3.0 Build 253
-- Wednesday, February 22, 2006 at 18:32:27
--

-- =================================================================
-- Copyright (C) 2006 by HUAWEI TECHNOLOGIES. All rights reserved
-- 
-- Description:
-- Reference:
-- Version: V1.00
-- History:
-- <author>,<date>,<contents>
-- =================================================================
-- 

	OPTIX-SONET-SYS-MIB DEFINITIONS ::= BEGIN
 
		IMPORTS
			optixCommonSonet			
				FROM OPTIX-OID-MIB			
			OBJECT-GROUP, MODULE-COMPLIANCE			
				FROM SNMPv2-CONF			
			OBJECT-TYPE, MODULE-IDENTITY			
				FROM SNMPv2-SMI;
	
	
		optixSonetSystem MODULE-IDENTITY 
			LAST-UPDATED "200602250000Z"
			ORGANIZATION 
				"Huawei Technologies co.,Ltd."
			CONTACT-INFO 
				"R&D Building
				Huawei Technologies Co., Ltd.
				Bantian, Longgang District 
				Shenzhen, P. R. China
				http://www.huawei.com
				Zip:518129
				E-mail:support@huawei.com
				"
			DESCRIPTION 
				"Description."
			REVISION "200602250000Z"
			DESCRIPTION
				"The initial revision of this MIB module."
			::= { optixCommonSonet 30 }
		
	
--
-- Node definitions
--
	
--  PM data          
		-- 1.3.6.1.4.1.2011.2.25.3.20.30.10
		alwMsgAll OBJECT IDENTIFIER ::= { optixSonetSystem 10 }
		
--  ---------------------------------------------------------------------
-- Network element Events
-- ----------------------------------------------------------------------
-- DBCHG NOTIFICATION-TYPE 
--    OBJECTS{ 
--               evtdate,
--               evttime,
--               evtsource,
--               evtuserid,
--               evtdbchgseq,
--               evtcommand
--           }
--    STATUS current 
--   DESCRIPTION "Report Database Change: This is an automatic message 
--                 generated by the NE to inform the OS of the change of database. 
--                 DBCHG is reported when any command except RTRV is completed or 
--                 when a board is plugged in or unplugged. REPT DBCHG message 
--                 will be reported to all logging users.
--                 " 
-- ::= { evtNEEvents  1 } 
-- *************************************************************************
--  System
-- -------------------------------------------------------------------------
--    ALW-MSG-ALL / INH-MSG-ALL
-- -------------------------------------------------------------------------
		-- 1.3.6.1.4.1.2011.2.25.3.20.30.10.10
		setMsgAll OBJECT-TYPE
			SYNTAX INTEGER
				{
				enabled(1),
				disabled(2)
				}
			MAX-ACCESS read-write
			STATUS current
			DESCRIPTION
				"Allow or inhibit automatic report alarms and events"
			::= { alwMsgAll 10 }
		
--  Allow or inhibit automatic report alarms and evnets
		-- 1.3.6.1.4.1.2011.2.25.3.20.30.20
		alwPMReptAll OBJECT IDENTIFIER ::= { optixSonetSystem 20 }
		
--  -------------------------------------------------------------------------
-- ALW-PMREPT-ALL / INH-PMREPT-ALL
-- -------------------------------------------------------------------------
		-- 1.3.6.1.4.1.2011.2.25.3.20.30.20.10
		setPMReptAll OBJECT-TYPE
			SYNTAX INTEGER
				{
				enabled(1),
				disabled(2)
				}
			MAX-ACCESS read-write
			STATUS current
			DESCRIPTION
				"Allow or inhibit Automatic report PM datas"
			::= { alwPMReptAll 10 }
		
		-- 1.3.6.1.4.1.2011.2.25.3.20.30.30
		optixSonetSystemConformance OBJECT IDENTIFIER ::= { optixSonetSystem 30 }
		
		-- 1.3.6.1.4.1.2011.2.25.3.20.30.30.1
		optixSonetSystemGroups OBJECT IDENTIFIER ::= { optixSonetSystemConformance 1 }
		
		-- 1.3.6.1.4.1.2011.2.25.3.20.30.30.1.1
		optixSonetObjectGroup OBJECT-GROUP
			OBJECTS { setMsgAll, setPMReptAll }
			STATUS current
			DESCRIPTION 
				"Enter the description of the created OBJECT-GROUP."
			::= { optixSonetSystemGroups 1 }
		
		-- 1.3.6.1.4.1.2011.2.25.3.20.30.30.2
		optixSonetSystemCompliances OBJECT IDENTIFIER ::= { optixSonetSystemConformance 2 }
		
		-- 1.3.6.1.4.1.2011.2.25.3.20.30.30.2.1
		optixSonetBasicCompliance MODULE-COMPLIANCE
			STATUS current
			DESCRIPTION 
				"Enter the description of the created MODULE-COMPLIANCE."
			MODULE -- this module
				MANDATORY-GROUPS { optixSonetObjectGroup }
			::= { optixSonetSystemCompliances 1 }
		
	
	END

--
-- OPTIX-SONET-SYS-MIB.mib
--
