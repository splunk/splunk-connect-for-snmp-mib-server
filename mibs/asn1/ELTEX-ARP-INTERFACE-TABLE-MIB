ELTEX-ARP-INTERFACE-TABLE-MIB DEFINITIONS ::= BEGIN

-- Title:      Eltex IP Router Private Extension
-- Version:    1.0
-- Date:       09 Jul 2015

IMPORTS
	rsArpInterfaceEntry                         FROM RADLAN-IP
    OBJECT-TYPE                                 FROM SNMPv2-SMI
    eltMesArpSpec                               FROM ELTEX-MES-IP;

eltArpInterfaceTable OBJECT-TYPE
    SYNTAX  SEQUENCE OF EltArpInterfaceEntry
    MAX-ACCESS  not-accessible
    STATUS  current
    DESCRIPTION
         ""
    ::= { eltMesArpSpec 1 }

eltArpInterfaceEntry OBJECT-TYPE
    SYNTAX  EltArpInterfaceEntry
    MAX-ACCESS  not-accessible
    STATUS  current
    DESCRIPTION
        "Each entry contains L2 Interface specific configuration
         for ARP Application."
    AUGMENTS   { rsArpInterfaceEntry }
              ::= { eltArpInterfaceTable 1 }

EltArpInterfaceEntry ::= SEQUENCE {
	eltArpInterfaceArpLocalProxy          INTEGER
}

eltArpInterfaceArpLocalProxy OBJECT-TYPE
    SYNTAX INTEGER {
       enable(1),
       disable(2)
    }
    MAX-ACCESS read-write
    STATUS     current
    DESCRIPTION
         "When Local ARP Proxy is enabled, the router can respond to
          ARP requests for nodes located on a same sub-net,
          provided they are it its network table. The router responds
          with its own MAC address.
          When ARP Proxy is disabled, the router responds only
          to ARP requests for its own IP addresses."
    DEFVAL  { disable }
    ::= { eltArpInterfaceEntry 1  }


END
