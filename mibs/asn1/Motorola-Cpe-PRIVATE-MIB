-- *****************************************************************
-- Cambium Networks-Cpe-PRIVATE: - VERSION 1.0.12
-- *****************************************************************

Motorola-Cpe-PRIVATE-MIB	DEFINITIONS ::= BEGIN
	IMPORTS
		DisplayString, DateAndTime, RowStatus
			FROM SNMPv2-TC
		ifIndex, ifAdminStatus, ifOperStatus
			FROM IF-MIB
		MODULE-IDENTITY, OBJECT-TYPE, Unsigned32, enterprises, Integer32, IpAddress, NOTIFICATION-TYPE
			FROM SNMPv2-SMI;

	gemtekDevCpe	MODULE-IDENTITY
		LAST-UPDATED	"201006291431Z"
		ORGANIZATION	"Cambium Networks"
		CONTACT-INFO	"PMP Technical Support
           email : support@cambiumnetworks.com"
		DESCRIPTION		"PMP 320 CPE MIB tree"
		::=  {  gemtek  300  }

	gemtek	OBJECT IDENTIFIER
		::=  {  enterprises  10529  }

	gemtekDevCpeStatus	OBJECT IDENTIFIER
		::=  {  gemtekDevCpe  1  }

	gemtekDevCpeControl	OBJECT IDENTIFIER
		::=  {  gemtekDevCpe  2  }

	gemtekDevCpeTrap	OBJECT IDENTIFIER
		::=  {  gemtekDevCpe  3  }

	gemtekDevCpeDate	OBJECT IDENTIFIER
		::=  {  gemtekDevCpe  4  }

	gemtekDevCpeAccountManagement	OBJECT IDENTIFIER
		::=  {  gemtekDevCpe  5  }

	gemtekDevCpeScanner	OBJECT IDENTIFIER
		::=  {  gemtekDevCpe  6  }

	gemtekDevCpeAuthentication	OBJECT IDENTIFIER
		::=  {  gemtekDevCpe  7  }

	gemtekDevCpeNetworkMode	OBJECT IDENTIFIER
		::=  {  gemtekDevCpe  8  }

	gemtekDevCpeFirewall	OBJECT IDENTIFIER
		::=  {  gemtekDevCpe  9  }

	gemtekDevCpeServiceFlow	OBJECT IDENTIFIER
		::=  {  gemtekDevCpe  11  }

	gemtekDevCpeSyslog	OBJECT IDENTIFIER
		::=  {  gemtekDevCpe  12  }

	gemtekDevCpeMaxTxPower	OBJECT IDENTIFIER
		::=  {  gemtekDevCpe  13  }

	gemtekDevCpePullFtpUpgrade	OBJECT IDENTIFIER
		::=  {  gemtekDevCpe  21  }

	gemtekDevCpePushFtpUpgrade	OBJECT IDENTIFIER
		::=  {  gemtekDevCpe  22  }  

	gemtekDevCpeTftpUpgrade	OBJECT IDENTIFIER
		::=  {  gemtekDevCpe  69  }

	wirelessStatus	OBJECT IDENTIFIER
		::=  {  gemtekDevCpeStatus  1  }

	networkStatus	OBJECT IDENTIFIER
		::=  {  gemtekDevCpeStatus  2  }

	deviceStatus	OBJECT IDENTIFIER
		::=  {  gemtekDevCpeStatus  3  }

	rebootWithResponse	OBJECT-TYPE	
		SYNTAX			INTEGER  { rebootRequired ( 1 ) , rebootNotRequired ( 0 ) , reboot ( 255 ) } 
		MAX-ACCESS		read-write
		STATUS			current
		DESCRIPTION		"If reading this OID, rebootRequired(1)
						indicates a reboot is currently required, 
						else, returns rebootNotRequired(0)."
		::=  {  gemtekDevCpeControl  1  }

	isRebootRequired	OBJECT-TYPE	
		SYNTAX			INTEGER  { rebootRequired ( 1 ) , rebootNotRequired ( 0 ) } 
		MAX-ACCESS		read-only
		STATUS			current
		DESCRIPTION		"If reading this OID, rebootRequired(1) 
						indicates a reboot is currently required, 
						else, returns rebootNotRequired(0)."
		::=  {  gemtekDevCpeControl  2  }

	autoSaveConfig	OBJECT-TYPE	
		SYNTAX			INTEGER  { autoSaveEnabled ( 1 ) , autoSaveDisabled ( 0 ) } 
		MAX-ACCESS		read-write
		STATUS			current
		DESCRIPTION		"OID to enable/disable the system save to flash automatically.
						 Change setting will save configuraition immediately.
						 Set autoSaveConfig = 0 can save configuraition immediately and 
						 don't turn on auto save."
		::=  {  gemtekDevCpeControl  3  }

	autoSavePeriod	OBJECT-TYPE	
		SYNTAX			Unsigned32
		MAX-ACCESS		read-write
		STATUS			obsolete
		DESCRIPTION		"The variable is deprecated.
						An OID to set the auto save period in seconds."
		::=  {  gemtekDevCpeControl  4  }

	startStopWimax	OBJECT-TYPE	
		SYNTAX			INTEGER  { start ( 1 ) , stop ( 0 ) } 
		MAX-ACCESS		read-write
		STATUS			current
		DESCRIPTION		"Start/Stop WiMAX"
		::=  {  gemtekDevCpeControl  5  }

	snmpBuzzerConfig	OBJECT-TYPE	
		SYNTAX			INTEGER  { snmpBuzzerDisabled ( 0 ) , snmpBuzzerEnabled ( 1 ) , snmpBuzzerDemo ( 2 ) } 
		MAX-ACCESS		read-write
		STATUS			current
		DESCRIPTION		"OID to enable/disable/demo the system buzzer."
		::=  {  gemtekDevCpeControl  6  }

	snmpBuzzerDisableDelay	OBJECT-TYPE	
		SYNTAX			Unsigned32
		MAX-ACCESS		read-write
		STATUS			current
		DESCRIPTION		"An OID to set the auto disable the buzzer in how many seconds after CPE operational.(0~1800)"
		::=  {  gemtekDevCpeControl  7  }
		
	gemtekDevCpeSnmpReadCommunity	OBJECT-TYPE	
		SYNTAX			OCTET STRING  ( SIZE ( 0 .. 32  ) )
		MAX-ACCESS		read-write
		STATUS			current
		DESCRIPTION		"An OID to set/get the SNMP Read community."
		::=  {  gemtekDevCpeControl  8  }
 
 	gemtekDevCpeSnmpSetCommunity	OBJECT-TYPE	
		SYNTAX			OCTET STRING  ( SIZE ( 0 .. 32  ) )
		MAX-ACCESS		read-write
		STATUS			current
		DESCRIPTION		"An OID to set/get the SNMP Set community."
		::=  {  gemtekDevCpeControl  9  }      

 	gemtekDevCpeRestFactoryDefault	OBJECT-TYPE	
		SYNTAX			INTEGER  { disabled ( 0 ) , enabled ( 1 ) }
		MAX-ACCESS		read-write
		STATUS			current
		DESCRIPTION		"Reset to factory default setting."
		::=  {  gemtekDevCpeControl  10  }

 	gemtekDevCpeAutoFirmwareRollback	OBJECT-TYPE	
		SYNTAX			INTEGER  { disabled ( 0 ) , levelOne ( 1 ), levelTwo ( 2 ) }
		MAX-ACCESS		read-write
		STATUS			current
		DESCRIPTION		"Auto firmware rollback Disable/Level 1/Level 2.(default:Disable)"
		::=  {  gemtekDevCpeControl  11  }
		
 	gemtekDevCpeFirmwareValidationTime	OBJECT-TYPE	
		SYNTAX			Unsigned32
		MAX-ACCESS		read-write
		STATUS			current
		DESCRIPTION		"Auto firmware rollback Level 1: The duration of firmware validation test time(0~99999 seconds)."
		::=  {  gemtekDevCpeControl  12  }

 	gemtekDevCpeFirmwareValidationCount	OBJECT-TYPE	
		SYNTAX			Unsigned32
		MAX-ACCESS		read-write
		STATUS			current
		DESCRIPTION		"Auto firmware rollback Level 2: Failure count in firmware validation test(0~999)."
		::=  {  gemtekDevCpeControl  13  }

 	gemtekDevCpeSnmpAccessFromLan	OBJECT-TYPE	
		SYNTAX			INTEGER  { disabled ( 0 ) , enabled ( 1 ) }
		MAX-ACCESS		read-write
		STATUS			current
		DESCRIPTION		"Allow SNMP access from LAN enabled/disabled.(Default:disabled)
						 Setting will take effect immediately."
		::=  {  gemtekDevCpeControl  14  }

	gemtekDevCpeDynamicMaxTxPowerBpsk	OBJECT-TYPE
		SYNTAX			OCTET STRING  ( SIZE ( 0 .. 32  ) )
		MAX-ACCESS		read-only
		STATUS			current
		DESCRIPTION		"BPSK Dynamic Max Tx Power(dBm)"
		::=  {  gemtekDevCpeControl  15  }

	gemtekDevCpeDynamicMaxTxPowerQpsk	OBJECT-TYPE	
		SYNTAX			OCTET STRING  ( SIZE ( 0 .. 32  ) )
		MAX-ACCESS		read-only
		STATUS			current
		DESCRIPTION		"QPSK Dynamic Max Tx Power(dBm)"
		::=  {  gemtekDevCpeControl  16  }

	gemtekDevCpeDynamicMaxTxPowerQam16	OBJECT-TYPE	
		SYNTAX			OCTET STRING  ( SIZE ( 0 .. 32  ) )
		MAX-ACCESS		read-only
		STATUS			current
		DESCRIPTION		"QAM16 Dynamic Max Tx Power(dBm)"
		::=  {  gemtekDevCpeControl  17  }

	gemtekDevCpeDynamicMaxTxPowerQam64	OBJECT-TYPE	
		SYNTAX			OCTET STRING  ( SIZE ( 0 .. 32  ) )
		MAX-ACCESS		read-only
		STATUS			current
		DESCRIPTION		"QAM64 Dynamic Max Tx Power(dBm)"
		::=  {  gemtekDevCpeControl  18  }

	gemtekDevCpeSnmpAccessDomain	OBJECT IDENTIFIER
		::=  {  gemtekDevCpeControl  19  }
 
 	gemtekDevCpeSnmpAccessDomainEnable	OBJECT-TYPE	
		SYNTAX			INTEGER  { disabled ( 0 ) , enabled ( 1 ) } 
		MAX-ACCESS		read-write
		STATUS			current
		DESCRIPTION		"Enable/Disable SNMP access domain(Default:Disable)
						 Setting will take effect until save and reboot."
		::=  {  gemtekDevCpeSnmpAccessDomain  1  }

	gemtekDevCpeSnmpAccessDomainIp	OBJECT-TYPE	
		SYNTAX			IpAddress
		MAX-ACCESS		read-write
		STATUS			current
		DESCRIPTION		"SNMP access domain IP"
		::=  {  gemtekDevCpeSnmpAccessDomain  2  }

	gemtekDevCpeSnmpAccessDomainNetmask	OBJECT-TYPE	
		SYNTAX			IpAddress
		MAX-ACCESS		read-write
		STATUS			current
		DESCRIPTION		"SNMP access domain netmask
						 EX: gemtekDevCpeSnmpAccessDomainIp = 192.168.1.1
						     gemtekDevCpeSnmpAccessDomainNetmask = 255.255.255.0
						 SNMP access domain = 192.168.1.0"
		::=  {  gemtekDevCpeSnmpAccessDomain  3  }

	gemtekDevCpeTrapServer	OBJECT IDENTIFIER
		::=  {  gemtekDevCpeTrap  1  }

	gemtekDevCpeTrapPrefix	OBJECT IDENTIFIER
		::=  {  gemtekDevCpeTrap  2  }

	gemtekDevCpeSystemDate	OBJECT-TYPE	
		SYNTAX			OCTET STRING
		MAX-ACCESS		read-only
		STATUS			current
		DESCRIPTION		"CPE system Date"
		::=  {  gemtekDevCpeDate  1  }

	gemtekDevCpeNtpServerEnable	OBJECT-TYPE	
		SYNTAX			INTEGER  { disabled ( 0 ) , enabled ( 1 ) } 
		MAX-ACCESS		read-write
		STATUS			current
		DESCRIPTION		"NTP Server Enable/Disable"
		::=  {  gemtekDevCpeDate  2  }

	gemtekDevCpeNtpServer	OBJECT-TYPE	
		SYNTAX			OCTET STRING  ( SIZE ( 0 .. 64  ) )
		MAX-ACCESS		read-write
		STATUS			current
		DESCRIPTION		"NTP Server configuration"
		::=  {  gemtekDevCpeDate  3  }

	gemtekDevCpeNtpServerFromDHCP	OBJECT-TYPE	
		SYNTAX			INTEGER  { disabled ( 0 ) , enabled ( 1 ) } 
		MAX-ACCESS		read-write
		STATUS			current
		DESCRIPTION		"NTP Server From DHCP"
		::=  {  gemtekDevCpeDate  4  }

	gemtekDevCpeTimeZone	OBJECT-TYPE	
		SYNTAX			Integer32  ( 0 .. 86  ) 
		MAX-ACCESS		read-write
		STATUS			current
		DESCRIPTION		"CPE Time Zone configuration:
						0  (GMT-12:00) International Date Line West ,
						1  (GMT-11:00) Midway Island, Samoa ,
						2  (GMT-10:00) Hawaii ,
						3  (GMT-09:00) Alaska ,
						4  (GMT-08:00) Pacific Time (US and Canada) ,
						5  (GMT-08:00) Tijuana, Baja California ,
						6  (GMT-07:00) Arizona ,
						7  (GMT-07:00) Chihuahua, La Paz, Mazatlan - New ,
						8  (GMT-07:00) Chihuahua, La Paz, Mazatlan - Old ,
						9  (GMT-07:00) Mountain Time (US and Canada) ,
						10 (GMT-06:00) Central America ,
						11 (GMT-06:00) Central Time (US and Canada) ,
						12 (GMT-06:00) Guadalajara, Mexico City, Monterrey - New ,
						13 (GMT-06:00) Guadalajara, Mexico City, Monterrey - Old ,
						14 (GMT-06:00) Saskatchewan ,
						15 (GMT-05:00) Bogota, Lima, Quito, Rio Branco ,
						16 (GMT-05:00) Eastern Time (US and Canada) ,
						17 (GMT-05:00) Indiana (East) ,
						18 (GMT-04:30) Caracas ,
						19 (GMT-04:00) Atlantic Time (Canada) ,
						20 (GMT-04:00) Caracas, La Paz ,
						21 (GMT-04:00) Manaus ,
						22 (GMT-04:00) Santiago ,
						23 (GMT-03:30) Newfoundland ,
						24 (GMT-03:00) Brasilia ,
						25 (GMT-03:00) Buenos Aires, Georgetown ,
						26 (GMT-03:00) Greenland ,
						27 (GMT-03:00) Montevideo ,
						28 (GMT-02:00) Mid-Atlantic ,
						29 (GMT-01:00) Azores ,
						30 (GMT-01:00) Cape Verde Is. ,
						31 (GMT) Casablanca, Monrovia, Reykjavik ,
						32 (GMT) Greenwich Mean Time - Dublin, Edinburgh, Lisbon, London ,
						33 (GMT+01:00) Amsterdam, Berlin, Bern, Rome, Stockholm, Vienna ,
						34 (GMT+01:00) Belgrade, Bratislava, Budapest, Ljubljana, Prague ,
						35 (GMT+01:00) Brussels, Copenhagen, Madrid, Paris ,
						36 (GMT+01:00) Sarajevo, Skopje, Warsaw, Zagreb ,
						37 (GMT+01:00) West Central Africa ,
						38 (GMT+02:00) Amman ,
						39 (GMT+02:00) Athens, Bucharest, Istanbul ,
						40 (GMT+02:00) Beirut ,
						41 (GMT+02:00) Cairo ,
						42 (GMT+02:00) Harare, Pretoria ,
						43 (GMT+02:00) Helsinki, Kyiv, Riga, Sofia, Tallinn, Vilnius ,
						44 (GMT+02:00) Jerusalem ,
						45 (GMT+02:00) Minsk ,
						46 (GMT+02:00) Windhoek ,
						47 (GMT+03:00) Baghdad ,
						48 (GMT+03:00) Kuwait, Riyadh ,
						49 (GMT+03:00) Moscow, St. Petersburg, Volgograd ,
						50 (GMT+03:00) Nairobi ,
						51 (GMT+03:00) Tbilisi ,
						52 (GMT+03:30) Tehran ,
						53 (GMT+04:00) Abu Dhabi, Muscat ,
						54 (GMT+04:00) Baku ,
						55 (GMT+04:00) Caucasus Standard Time ,
						56 (GMT+04:00) Yerevan ,
						57 (GMT+04:30) Kabul ,
						58 (GMT+05:00) Yekaterinburg ,
						59 (GMT+05:00) Islamabad, Karachi, Tashkent ,
						60 (GMT+05:30) Chennai, Kolkata, Mumbai, New Delhi ,
						61 (GMT+05:30) Sri Jayawardenapura-Kotte ,
						62 (GMT+05:45) Kathmandu ,
						63 (GMT+06:00) Almaty, Novosibirsk ,
						64 (GMT+06:00) Astana, Dhaka ,
						65 (GMT+06:30) Yangon (Rangoon) ,
						66 (GMT+07:00) Bangkok, Hanoi, Jakarta ,
						67 (GMT+07:00) Krasnoyarsk ,
						68 (GMT+08:00) Beijing, Chongqing, Hong Kong, Urumqi ,
						69 (GMT+08:00) Irkutsk, Ulaan Bataar ,
						70 (GMT+08:00) Kuala Lumpur, Singapore ,
						71 (GMT+08:00) Perth ,
						72 (GMT+08:00) Taipei ,
						73 (GMT+09:00) Osaka, Sapporo, Tokyo ,
						74 (GMT+09:00) Seoul ,
						75 (GMT+09:00) Yakutsk ,
						76 (GMT+09:30) Adelaide ,
						77 (GMT+09:30) Darwin ,
						78 (GMT+10:00) Brisbane ,
						79 (GMT+10:00) Canberra, Melbourne, Sydney ,
						80 (GMT+10:00) Guam, Port Moresby ,
						81 (GMT+10:00) Hobart ,
						82 (GMT+10:00) Vladivostok ,
						83 (GMT+11:00) Magadan, Solomon Is., New Caledonia ,
						84 (GMT+12:00) Auckland, Wellington ,
						85 (GMT+12:00) Fiji, Kamchatka, Marshall Is. ,
						86 (GMT+13:00) Nuku`alofa "
		::=  {  gemtekDevCpeDate  5  }

	gemtekDevCpeDaylightSaving	OBJECT-TYPE	
		SYNTAX			INTEGER  { disabled ( 0 ) , enabled ( 1 ) } 
		MAX-ACCESS		read-write
		STATUS			current
		DESCRIPTION		"Daylight Saving Enable configuration"
		::=  {  gemtekDevCpeDate  6  }

	administratorUsername	OBJECT-TYPE	
		SYNTAX			OCTET STRING  ( SIZE ( 1 .. 32  ) ) 
		MAX-ACCESS		read-write
		STATUS			current
		DESCRIPTION		"set/get WEB administrator username"
		::=  {  gemtekDevCpeAccountManagement  1  }

	administratorPassword	OBJECT-TYPE	
		SYNTAX			OCTET STRING  ( SIZE ( 1 .. 32  ) ) 
		MAX-ACCESS		read-write
		STATUS			current
		DESCRIPTION		"set-only WEB administrator password"
		::=  {  gemtekDevCpeAccountManagement  2  }


	administratorEnable	OBJECT-TYPE	
		SYNTAX			INTEGER  { disabled ( 0 ) , enabled ( 1 ) }
		MAX-ACCESS		read-write
		STATUS			current
		DESCRIPTION		"set/get WEB administrator eabled/disabled"
		::=  {  gemtekDevCpeAccountManagement  3  }

	operatorUsername	OBJECT-TYPE	
		SYNTAX			OCTET STRING  ( SIZE ( 1 .. 32  ) ) 
		MAX-ACCESS		read-write
		STATUS			current
		DESCRIPTION		"set/get WEB operator username"
		::=  {  gemtekDevCpeAccountManagement  4  }

	operatorPassword	OBJECT-TYPE	
		SYNTAX			OCTET STRING  ( SIZE ( 1 .. 32  ) ) 
		MAX-ACCESS		read-write
		STATUS			current
		DESCRIPTION		"set-only WEB operator password"
		::=  {  gemtekDevCpeAccountManagement  5  }


	operatorEnable	OBJECT-TYPE	
		SYNTAX			INTEGER  { disabled ( 0 ) , enabled ( 1 ) }
		MAX-ACCESS		read-write
		STATUS			current
		DESCRIPTION		"set/get WEB operator eabled/disabled"
		::=  {  gemtekDevCpeAccountManagement  6  }


	adminUsername	OBJECT-TYPE	
		SYNTAX			OCTET STRING  ( SIZE ( 1 .. 32  ) ) 
		MAX-ACCESS		read-write
		STATUS			current
		DESCRIPTION		"set/get WEB admin username"
		::=  {  gemtekDevCpeAccountManagement  7  }

	adminPassword	OBJECT-TYPE	
		SYNTAX			OCTET STRING  ( SIZE ( 1 .. 32  ) ) 
		MAX-ACCESS		read-write
		STATUS			current
		DESCRIPTION		"set-only WEB admin password"
		::=  {  gemtekDevCpeAccountManagement  8  }


	adminEnable	OBJECT-TYPE	
		SYNTAX			INTEGER  { disabled ( 0 ) , enabled ( 1 ) }
		MAX-ACCESS		read-write
		STATUS			current
		DESCRIPTION		"set/get WEB admin eabled/disabled"
		::=  {  gemtekDevCpeAccountManagement  9  }

	gemtekDevCpeChannelBandwidthRang	OBJECT-TYPE	
		SYNTAX			INTEGER  { threeToFive ( 0 ) , sixToTen ( 1 ) }
		MAX-ACCESS		read-write
		STATUS			deprecated
		DESCRIPTION		"No function for this OID since f03b00-5.8.8Moto
						 Select the Channel Bandwidth Rang.
						 0: threeToFive 3MHz ~ 5MHz => 3MHz, 3.5MHz, 5MHz
						 1: sixToTen 6MHz ~ 10MHz => 6MHz, 7MHz, 8.75MHz, 10MHz"
		::=  {  gemtekDevCpeScanner  1  }
		
	gemtekDevCpeChannelApplyLoadOrSave	OBJECT-TYPE	
		SYNTAX			INTEGER  { load ( 0 ), save ( 1 ) }
		MAX-ACCESS		read-write
		STATUS			current
		DESCRIPTION		"Channel Scanner Setting load or save (defualut:0).
						 Saved channel Table will take effect until reboot."
		::=  {  gemtekDevCpeScanner  2  }

	gemtekDevCpeChannelTable	OBJECT-TYPE
		SYNTAX		SEQUENCE  OF  GemtekDevCpeChannelEntry
		MAX-ACCESS	not-accessible
		STATUS		current
		DESCRIPTION	"Channel Table"
		::=  { gemtekDevCpeScanner  3 }

	gemtekDevCpeFrequencyRangeSetting	OBJECT IDENTIFIER
		::=  {  gemtekDevCpeScanner  4  }

	gemtekDevCpeAPPreferredList	OBJECT IDENTIFIER
		::=  {  gemtekDevCpeScanner  5  }

	gemtekDevCpeLockFrequencyRangeMin		OBJECT-TYPE
		SYNTAX			Unsigned32
		MAX-ACCESS		read-only
		STATUS			current
		DESCRIPTION		"CPE lock frequency range Min(kHz)"
		::=  {  gemtekDevCpeFrequencyRangeSetting  1  }

	gemtekDevCpeLockFrequencyRangeMax		OBJECT-TYPE	
		SYNTAX			Unsigned32
		MAX-ACCESS		read-only
		STATUS			current
		DESCRIPTION		"CPE lock frequency range Max(kHz)"
		::=  {  gemtekDevCpeFrequencyRangeSetting  2  }

 	gemtekDevCpeLockFrequencyRange	OBJECT-TYPE	
		SYNTAX			INTEGER  { unlock(0), lock ( 1 ) }
		MAX-ACCESS		read-only
		STATUS			current
		DESCRIPTION		"Lock/Unlock frequency range state."
		::=  {  gemtekDevCpeFrequencyRangeSetting  3  }

	gemtekDevCpeModelFrequencyRangeMin		OBJECT-TYPE	
		SYNTAX			Unsigned32
		MAX-ACCESS		read-only
		STATUS			current
		DESCRIPTION		"CPE model frequency range Min(kHz)"
		::=  {  gemtekDevCpeFrequencyRangeSetting  4  }

	gemtekDevCpeModelFrequencyRangeMax		OBJECT-TYPE	
		SYNTAX			Unsigned32
		MAX-ACCESS		read-only
		STATUS			current
		DESCRIPTION		"CPE Model frequency range Max(kHz)"
		::=  {  gemtekDevCpeFrequencyRangeSetting  5  }

	gemtekDevCpeAPPreferredSelectionEnable	OBJECT-TYPE
		SYNTAX			INTEGER  { disabled ( 0 ) , enabled ( 1 ) }
		MAX-ACCESS		read-write
		STATUS			current
		DESCRIPTION		"AP Preferred Selection eabled/disabled"
		::=  {  gemtekDevCpeAPPreferredList  1  }
	
	gemtekDevCpeAPPreferredBsIdListLocked	OBJECT-TYPE	
		SYNTAX			INTEGER  { disabled ( 0 ) , enabled ( 1 ) }
		MAX-ACCESS		read-write
		STATUS			current
		DESCRIPTION		"Configured BsId List Locked eabled/disabled"
		::=  {  gemtekDevCpeAPPreferredList  2  }
	
	gemtekDevCpeAPPreferredPriorityOneBsId	OBJECT-TYPE	
		SYNTAX			OCTET STRING  ( SIZE ( 0 .. 17 ) )
		MAX-ACCESS		read-write
		STATUS			current
		DESCRIPTION		"Priority 1 BsId Address"
		::=  {  gemtekDevCpeAPPreferredList  3  }
	
	gemtekDevCpeAPPreferredPriorityTwoBsId	OBJECT-TYPE	
		SYNTAX			OCTET STRING  ( SIZE ( 0 .. 17 ) ) 
		MAX-ACCESS		read-write
		STATUS			current
		DESCRIPTION		"Priority 2 BsId Address"
		::=  {  gemtekDevCpeAPPreferredList  4  }
	
	gemtekDevCpeAPPreferredPriorityThreeBsId	OBJECT-TYPE	
		SYNTAX			OCTET STRING  ( SIZE ( 0 .. 17 ) ) 
		MAX-ACCESS		read-write
		STATUS			current
		DESCRIPTION		"Priority 3 BsId Address"
		::=  {  gemtekDevCpeAPPreferredList  5  }
	
	gemtekDevCpeAPPreferredPriorityFourBsId	OBJECT-TYPE	
		SYNTAX			OCTET STRING  ( SIZE ( 0 .. 17 ) ) 
		MAX-ACCESS		read-write
		STATUS			current
		DESCRIPTION		"Priority 4 BsId Address"
		::=  {  gemtekDevCpeAPPreferredList  6  }
					
	gemtekDevCpeChannelEntry	OBJECT-TYPE
		SYNTAX		GemtekDevCpeChannelEntry
		MAX-ACCESS	not-accessible
		STATUS		current
		DESCRIPTION	"Channel Entry"
		INDEX		{  gemtekDevCpeChannelIndex  }
		::=  { gemtekDevCpeChannelTable 1 }

	GemtekDevCpeChannelEntry  ::=  SEQUENCE {
		gemtekDevCpeChannelIndex  Integer32,
		gemtekDevCpeChannelActive  INTEGER,
		gemtekDevCpeChannelFrequency  Unsigned32,
		gemtekDevCpeChannelBandwidth  Integer32,
		gemtekDevCpeChannelRssi  OCTET STRING,
		gemtekDevCpeChannelCinr  OCTET STRING,
		gemtekDevCpeChannelEntryEnable  INTEGER,
		gemtekDevCpeChannelRowstatus  RowStatus,
		gemtekDevCpeChannelBsId  OCTET STRING,
		gemtekDevCpeChannelPreambelIndex  OCTET STRING
		}


	gemtekDevCpeChannelIndex	OBJECT-TYPE	
		SYNTAX			Integer32
		MAX-ACCESS		read-only
		STATUS			current
		DESCRIPTION		"Channel Index"
		::=  {  gemtekDevCpeChannelEntry  1  }


	gemtekDevCpeChannelActive	OBJECT-TYPE	
		SYNTAX			INTEGER  { disactive ( 0 ) , active ( 1 ) } 
		MAX-ACCESS		read-only
		STATUS			current
		DESCRIPTION		"Channel Active/Disactive"
		::=  {  gemtekDevCpeChannelEntry  2  }


	gemtekDevCpeChannelFrequency	OBJECT-TYPE	
		SYNTAX			Unsigned32
		MAX-ACCESS		read-create
		STATUS			current                           
		DESCRIPTION		"Channel Frequency configuration (kHz)"
		::=  {  gemtekDevCpeChannelEntry  3  }


	gemtekDevCpeChannelBandwidth	OBJECT-TYPE	
		SYNTAX			Integer32 
		MAX-ACCESS		read-create
		STATUS			current
		DESCRIPTION		"Channel Bandwidth configuration(kHz)
										3.5MHz = 3500kHz
										5MHz = 5000kHz
										7MHz = 7000kHz
										10MHz = 10000kHz"
		::=  {  gemtekDevCpeChannelEntry  4  }

	gemtekDevCpeChannelRssi	OBJECT-TYPE	
		SYNTAX			OCTET STRING  ( SIZE ( 0 .. 32  ) ) 
		MAX-ACCESS		read-only
		STATUS			current
		DESCRIPTION		"Channel RSSI (dBm)"
		::=  {  gemtekDevCpeChannelEntry  5  }

	gemtekDevCpeChannelCinr	OBJECT-TYPE	
		SYNTAX			OCTET STRING  ( SIZE ( 0 .. 32  ) ) 
		MAX-ACCESS		read-only
		STATUS			current
		DESCRIPTION		"Channel CINR(dB)"
		::=  {  gemtekDevCpeChannelEntry  6  }


	gemtekDevCpeChannelEntryEnable	OBJECT-TYPE	
		SYNTAX			INTEGER  { disabled ( 0 ) , enabled ( 1 ) } 
		MAX-ACCESS		read-create
		STATUS			current
		DESCRIPTION		"Channel Entry Enable(Disable/Enable)"
		::=  {  gemtekDevCpeChannelEntry  7  }


	gemtekDevCpeChannelRowstatus	OBJECT-TYPE	
		SYNTAX			RowStatus
		MAX-ACCESS		read-create
		STATUS			current
		DESCRIPTION		"active(1) to active the row and save setting to memory.
						 createAndWait(5) to create a row in the bottom.
						 destroy(6) to delete a row."
		::=  {  gemtekDevCpeChannelEntry  8  }


	gemtekDevCpeChannelBsId	OBJECT-TYPE	
		SYNTAX			OCTET STRING  ( SIZE ( 0 .. 18  ) ) 
		MAX-ACCESS		read-only
		STATUS			current
		DESCRIPTION		"Channel Bs Id"
		::=  {  gemtekDevCpeChannelEntry  9  }


	gemtekDevCpeChannelPreambelIndex	OBJECT-TYPE	
		SYNTAX			OCTET STRING  ( SIZE ( 0 .. 4  ) ) 
		MAX-ACCESS		read-only
		STATUS			current
		DESCRIPTION		"Channel Preamble Index"
		::=  {  gemtekDevCpeChannelEntry  10  }


	gemtekDevCpeAuthenticationSelectionPhase1	OBJECT-TYPE	
		SYNTAX			INTEGER  { none ( 0 ) , eapTtls ( 1 ) , eapTls ( 2 ) } 
		MAX-ACCESS		read-write
		STATUS			current
		DESCRIPTION		"Authentication Selection Phase1(None/EAP-TLS/EAP-TTLS)
						 EAP-TLS needs at least one Device certificate file.
						 Please upload a device certificate file to CPE then you can set EAP-TLS."
		::=  {  gemtekDevCpeAuthentication  1  }

	eapIdentityType	OBJECT-TYPE	
		SYNTAX			INTEGER  { noIdentity ( 0 ) , manaulIdentity ( 1 ) , randomIdentity ( 2 ) } 
		MAX-ACCESS		read-write
		STATUS			current
		DESCRIPTION		"EAP-TLS/EAP-TTLS Identity type
						0: no Identity(Use realm)
						1: manaul Identity
						2: random Identity"
		::=  {  gemtekDevCpeAuthentication  2  }

	eapIdentityUseRealm	OBJECT-TYPE	
		SYNTAX			INTEGER  { disabled ( 0 ) , enabled ( 1 ) } 
		MAX-ACCESS		read-write
		STATUS			current
		DESCRIPTION		"EAP-TLS/EAP-TTLS Identity use realm Enable/Disable"
		::=  {  gemtekDevCpeAuthentication  3  }

	eapIdentityString	OBJECT-TYPE	
		SYNTAX			OCTET STRING  ( SIZE ( 0 .. 64  ) ) 
		MAX-ACCESS		read-write
		STATUS			current
		DESCRIPTION		"EAP-TLS/EAP-TTLS Identity String configuration"
		::=  {  gemtekDevCpeAuthentication  4  }

	eapRealmString	OBJECT-TYPE	
		SYNTAX			OCTET STRING  ( SIZE ( 0 .. 32) )
		MAX-ACCESS		read-write
		STATUS			current
		DESCRIPTION		"EAP-TLS/EAP-TTLS Identity String configuration"
		::=  {  gemtekDevCpeAuthentication  5  }

	eapValidateTheDateDurationOfCaCertificate	OBJECT-TYPE	
		SYNTAX			INTEGER  { disabled ( 0 ) , enabled ( 1 ) } 
		MAX-ACCESS		read-write
		STATUS			current
		DESCRIPTION		"EAP-TLS/EAP-TTLS Validate the date duration of CA certificate(Disable/Enable)"
		::=  {  gemtekDevCpeAuthentication  6  }

	eapValidateTheServerCertificate	OBJECT-TYPE	
		SYNTAX			INTEGER  { disabled ( 0 ) , enabled ( 1 ) } 
		MAX-ACCESS		read-write
		STATUS			current
		DESCRIPTION		"EAP-TLS/EAP-TTLS Validate the server certificate(Disable/Enable)
						 It needs at least one CA certificate file.
						 Please upload a CA certificate file to CPE then you can set it enabled."
		::=  {  gemtekDevCpeAuthentication  7  }

	gemtekDevCpeAuthenticationEAPTLS	OBJECT IDENTIFIER
		::=  {  gemtekDevCpeAuthentication  8  }

	gemtekDevCpeAuthenticationEAPTTLS	OBJECT IDENTIFIER
		::=  {  gemtekDevCpeAuthentication  9  }

	gemtekDevCpeCertificationFileManagement	OBJECT IDENTIFIER
		::=  {  gemtekDevCpeAuthentication  10  }
	
	gemtekDevCpeCertificateUpload	OBJECT IDENTIFIER
		::=  {  gemtekDevCpeCertificationFileManagement  1  }

	gemtekDevCpeCACertificateFileName	OBJECT-TYPE	
		SYNTAX			OCTET STRING  ( SIZE ( 1 .. 32  ) )
		MAX-ACCESS		read-write
		STATUS			current
		DESCRIPTION		"specify the CA certificate file name on the FTP server."
		::=  {  gemtekDevCpeCertificateUpload  1  }
		
	gemtekDevCpeCACertificateFileUpload	OBJECT-TYPE	
		SYNTAX			INTEGER  { default ( 0 ) , upload ( 1 ) } 
		MAX-ACCESS		read-write
		STATUS			current
		DESCRIPTION		"check and upload the CA certificate file."
		::=  {  gemtekDevCpeCertificateUpload  2  }

	gemtekDevCpeUserCertificateFileName	OBJECT-TYPE	
		SYNTAX			OCTET STRING  ( SIZE ( 1 .. 32  ) )
		MAX-ACCESS		read-write
		STATUS			current
		DESCRIPTION		"specify the user certificate file name on the FTP server."
		::=  {  gemtekDevCpeCertificateUpload  3  }
		
	gemtekDevCpeUserCertificateFileUpload	OBJECT-TYPE	
		SYNTAX			INTEGER  { default ( 0 ) , upload ( 1 ) } 
		MAX-ACCESS		read-write
		STATUS			current
		DESCRIPTION		"check and upload the user certificate file."
		::=  {  gemtekDevCpeCertificateUpload  4  }
		
	gemtekDevCpeCACertificateFileDelete	OBJECT-TYPE	
		SYNTAX			INTEGER  { fileOne ( 1 ) , fileTwo ( 2 ) } 
		MAX-ACCESS		read-write
		STATUS			current
		DESCRIPTION		"delete the CA certificate file.
						 Validate the server certificate needs at least one CA certificate file.
						 If you delete all CA certificate files, 
						 it will change eapValidateTheServerCertificate to disabled."
		::=  {  gemtekDevCpeCertificationFileManagement  2  }

	gemtekDevCpeUserCertificateFileDelete	OBJECT-TYPE	
		SYNTAX			INTEGER  { fileOne ( 1 ) , fileTwo ( 2 ) } 
		MAX-ACCESS		read-write
		STATUS			current
		DESCRIPTION		"delete the user certificate file.
						EAP-TLS needs at least one device certificate file.
						If you delete all user certificate files, 
						it will change gemtekDevCpeAuthenticationSelectionPhase1 to EAP-TTLS,
						and use device certificate disabled."
		::=  {  gemtekDevCpeCertificationFileManagement  3  }
	
	gemtekDevCpeCACertificateFileTable	OBJECT-TYPE
		SYNTAX		SEQUENCE  OF  GemtekDevCpeCACertificateFileEntry
		MAX-ACCESS	not-accessible
		STATUS		current
		DESCRIPTION	"CA certificate file table"
		::=  { gemtekDevCpeCertificationFileManagement  4 }

	gemtekDevCpeCACertificateFileEntry	OBJECT-TYPE
		SYNTAX		GemtekDevCpeCACertificateFileEntry
		MAX-ACCESS	not-accessible
		STATUS		current
		DESCRIPTION	"CA certificate file entry"
		INDEX		{  gemtekDevCpeCACertificateIndex  }
		::=  { gemtekDevCpeCACertificateFileTable 1 }

	GemtekDevCpeCACertificateFileEntry  ::=  SEQUENCE {
		gemtekDevCpeCACertificateIndex		Integer32,
		gemtekDevCpeCACertificateSize		Unsigned32,
		gemtekDevCpeCACertificateIssuer		OCTET STRING,
		gemtekDevCpeCAValidityDateBegin		OCTET STRING,
		gemtekDevCpeCAValidityDateEnd		OCTET STRING,
		gemtekDevCpeCACertificateSubject	OCTET STRING
	}
	
	gemtekDevCpeCACertificateIndex	OBJECT-TYPE	
		SYNTAX			Integer32
		MAX-ACCESS		read-only
		STATUS			current
		DESCRIPTION		"CA certificate file Table Index"
		::=  {  gemtekDevCpeCACertificateFileEntry  1  }


	gemtekDevCpeCACertificateSize	OBJECT-TYPE	
		SYNTAX			Unsigned32 
		MAX-ACCESS		read-only
		STATUS			current
		DESCRIPTION		"CA certificate file size(Byte)"
		::=  {  gemtekDevCpeCACertificateFileEntry  2  }


	gemtekDevCpeCACertificateIssuer	OBJECT-TYPE	
		SYNTAX			OCTET STRING	( SIZE ( 0 .. 256  ) )
		MAX-ACCESS		read-only
		STATUS			current                           
		DESCRIPTION		"CA certificate file issuer"
		::=  {  gemtekDevCpeCACertificateFileEntry  3  }


	gemtekDevCpeCAValidityDateBegin	OBJECT-TYPE	
		SYNTAX			OCTET STRING	( SIZE ( 0 .. 32  ) ) 
		MAX-ACCESS		read-only
		STATUS			current
		DESCRIPTION		"CA certificate file validity date begin"
		::=  {  gemtekDevCpeCACertificateFileEntry  4  }

	gemtekDevCpeCAValidityDateEnd	OBJECT-TYPE	
		SYNTAX			OCTET STRING	( SIZE ( 0 .. 32  ) ) 
		MAX-ACCESS		read-only
		STATUS			current
		DESCRIPTION		"CA certificate file validity date end"
		::=  {  gemtekDevCpeCACertificateFileEntry  5  }

	gemtekDevCpeCACertificateSubject	OBJECT-TYPE	
		SYNTAX			OCTET STRING  ( SIZE ( 0 .. 256  ) ) 
		MAX-ACCESS		read-only
		STATUS			current
		DESCRIPTION		"CA certificate file subject"
		::=  {  gemtekDevCpeCACertificateFileEntry  6  }

	gemtekDevCpeUserCertificateFileTable	OBJECT-TYPE
		SYNTAX		SEQUENCE  OF  GemtekDevCpeUserCertificateFileEntry
		MAX-ACCESS	not-accessible
		STATUS		current
		DESCRIPTION	"User certificate file table"
		::=  { gemtekDevCpeCertificationFileManagement  5 }

	gemtekDevCpeUserCertificateFileEntry	OBJECT-TYPE
		SYNTAX		GemtekDevCpeUserCertificateFileEntry
		MAX-ACCESS	not-accessible
		STATUS		current
		DESCRIPTION	"User certificate file entry"
		INDEX		{  gemtekDevCpeUserCertificateIndex  }
		::=  { gemtekDevCpeUserCertificateFileTable 1 }

	GemtekDevCpeUserCertificateFileEntry  ::=  SEQUENCE {
		gemtekDevCpeUserCertificateIndex	Integer32,
		gemtekDevCpeUserCertificateSize		Unsigned32,
		gemtekDevCpeUserCertificateIssuer	OCTET STRING,
		gemtekDevCpeUserValidityDateBegin	OCTET STRING,
		gemtekDevCpeUserValidityDateEnd		OCTET STRING,
		gemtekDevCpeUserCertificateSubject	OCTET STRING
	}
	
	gemtekDevCpeUserCertificateIndex	OBJECT-TYPE	
		SYNTAX			Integer32
		MAX-ACCESS		read-only
		STATUS			current
		DESCRIPTION		"User certificate file Table Index"
		::=  {  gemtekDevCpeUserCertificateFileEntry  1  }


	gemtekDevCpeUserCertificateSize	OBJECT-TYPE	
		SYNTAX			Unsigned32 
		MAX-ACCESS		read-only
		STATUS			current
		DESCRIPTION		"User certificate file size(Byte)"
		::=  {  gemtekDevCpeUserCertificateFileEntry  2  }


	gemtekDevCpeUserCertificateIssuer	OBJECT-TYPE	
		SYNTAX			OCTET STRING	( SIZE ( 0 .. 256  ) )
		MAX-ACCESS		read-only
		STATUS			current                           
		DESCRIPTION		"User certificate file issuer"
		::=  {  gemtekDevCpeUserCertificateFileEntry  3  }


	gemtekDevCpeUserValidityDateBegin	OBJECT-TYPE	
		SYNTAX			OCTET STRING	( SIZE ( 0 .. 32  ) ) 
		MAX-ACCESS		read-only
		STATUS			current
		DESCRIPTION		"User certificate file validity date begin"
		::=  {  gemtekDevCpeUserCertificateFileEntry  4  }

	gemtekDevCpeUserValidityDateEnd	OBJECT-TYPE	
		SYNTAX			OCTET STRING	( SIZE ( 0 .. 32  ) ) 
		MAX-ACCESS		read-only
		STATUS			current
		DESCRIPTION		"User certificate file validity date end"
		::=  {  gemtekDevCpeUserCertificateFileEntry  5  }

	gemtekDevCpeUserCertificateSubject	OBJECT-TYPE	
		SYNTAX			OCTET STRING  ( SIZE ( 0 .. 256  ) ) 
		MAX-ACCESS		read-only
		STATUS			current
		DESCRIPTION		"User certificate file subject"
		::=  {  gemtekDevCpeUserCertificateFileEntry  6  }
		
	gemtekDevCpeNetoworkOperatingMode	OBJECT-TYPE	
		SYNTAX			INTEGER  { nat ( 0 ) , bridge ( 1 ) } 
		MAX-ACCESS		read-write
		STATUS			current
		DESCRIPTION		"Netowork Operating Mode(Bridge/NAT)"
		::=  {  gemtekDevCpeNetworkMode  1  }

	gemtekDevCpeBridgeMode	OBJECT IDENTIFIER
		::=  {  gemtekDevCpeNetworkMode  2  }

	gemtekDevCpeNatMode	OBJECT IDENTIFIER
		::=  {  gemtekDevCpeNetworkMode  3  }

	gemtekDevCpeAllowWebAccessingFromWan	OBJECT-TYPE	
		SYNTAX			INTEGER  { disabled ( 0 ) , enabled ( 1 ) } 
		MAX-ACCESS		read-write
		STATUS			current
		DESCRIPTION		"Allow Web Accessing From WAN(disable/enable)"
		::=  {  gemtekDevCpeFirewall  1  }

	gemtekDevCpeAllowTelnetAccessingFromWan	OBJECT-TYPE	
		SYNTAX			INTEGER  { disabled ( 0 ) , enabled ( 1 ) } 
		MAX-ACCESS		read-write
		STATUS			current
		DESCRIPTION		"Allow Telnet Accessing From WAN(disable/enable)"
		::=  {  gemtekDevCpeFirewall  2  }

	gemtekDevCpeDmzEnable	OBJECT-TYPE	
		SYNTAX			INTEGER  { disabled ( 0 ) , enabled ( 1 ) } 
		MAX-ACCESS		read-write
		STATUS			current
		DESCRIPTION		"DMZ Enable/Disable"
		::=  {  gemtekDevCpeFirewall  3  }

	gemtekDevCpeDmzIpAddress	OBJECT-TYPE	
		SYNTAX			IpAddress
		MAX-ACCESS		read-write
		STATUS			current
		DESCRIPTION		"DMZ IP Address"
		::=  {  gemtekDevCpeFirewall  4  }

	gemtekDevCpeRedirectIcmpToTheDmzHostEnable	OBJECT-TYPE	
		SYNTAX			INTEGER  { disabled ( 0 ) , enabled ( 1 ) } 
		MAX-ACCESS		read-write
		STATUS			current
		DESCRIPTION		"Redirect ICMP packets to the DMZ host Enable/Disable"
		::=  {  gemtekDevCpeFirewall  5  }

	gemtekDevCpeFirewallEnable	OBJECT-TYPE	
		SYNTAX			INTEGER  { disabled ( 0 ) , enabled ( 1 ) } 
		MAX-ACCESS		read-write
		STATUS			current
		DESCRIPTION		"Firewall Enable/Disable"
		::=  {  gemtekDevCpeFirewall  6  }

	gemtekDevCpeFirewallTable	OBJECT-TYPE
		SYNTAX		SEQUENCE  OF  GemtekDevCpeFirewallEntry
		MAX-ACCESS	not-accessible
		STATUS		current
		DESCRIPTION	"Firewall Table"
		::=  { gemtekDevCpeFirewall  7 }

	gemtekDevCpeFirewallEntry	OBJECT-TYPE
		SYNTAX		GemtekDevCpeFirewallEntry
		MAX-ACCESS	not-accessible
		STATUS		current
		DESCRIPTION	"Firewall Entry"
		INDEX		{  gemtekDevCpeFirewallIndex  }
		::=  { gemtekDevCpeFirewallTable 1 }

	GemtekDevCpeFirewallEntry  ::=  SEQUENCE {
		gemtekDevCpeFirewallIndex  Integer32,
		gemtekDevCpeFirewallName  OCTET STRING,
		gemtekDevCpeFirewallAction  INTEGER,
		gemtekDevCpeFirewallInterface  INTEGER,
		gemtekDevCpeFirewallProtocol  INTEGER,
		gemtekDevCpeFirewallPriority  INTEGER,
		gemtekDevCpeFirewallEntryEnable  INTEGER,
		gemtekDevCpeFirewallSrcMac  OCTET STRING,
		gemtekDevCpeFirewallDstMac  OCTET STRING,
		gemtekDevCpeFirewallSrcIpAddress  IpAddress,
		gemtekDevCpeFirewallDstIpAddress  IpAddress,
		gemtekDevCpeFirewallSrcPortRangeBegin  Integer32,
		gemtekDevCpeFirewallSrcPortRangeEnd  Integer32,
		gemtekDevCpeFirewallDstPortRangeBegin  Integer32,
		gemtekDevCpeFirewallDstPortRangeEnd  Integer32,
		gemtekDevCpeFirewallRowstatus  RowStatus
		}


	gemtekDevCpeFirewallIndex	OBJECT-TYPE	
		SYNTAX			Integer32
		MAX-ACCESS		read-only
		STATUS			current
		DESCRIPTION		"Firewall Index"
		::=  {  gemtekDevCpeFirewallEntry  1  }


	gemtekDevCpeFirewallName	OBJECT-TYPE	
		SYNTAX			OCTET STRING
		MAX-ACCESS		read-create
		STATUS			current
		DESCRIPTION		"Firewall Name"
		::=  {  gemtekDevCpeFirewallEntry  2  }


	gemtekDevCpeFirewallAction	OBJECT-TYPE	
		SYNTAX			INTEGER  { deny ( 0 ) , allow ( 1 ) } 
		MAX-ACCESS		read-create
		STATUS			current
		DESCRIPTION		"Firewall Action(Deny/Allow)"
		::=  {  gemtekDevCpeFirewallEntry  3  }


	gemtekDevCpeFirewallInterface	OBJECT-TYPE	
		SYNTAX			INTEGER  {  ethernet ( 0 ) , wimax ( 1 ) } 
		MAX-ACCESS		read-create
		STATUS			current
		DESCRIPTION		"Firewall Interface(Ethernet/Wimax)"
		::=  {  gemtekDevCpeFirewallEntry  4  }


	gemtekDevCpeFirewallProtocol	OBJECT-TYPE	
		SYNTAX			INTEGER  { any ( 0 ) , icmp ( 1 ) , tcp ( 6 ) , udp ( 17 ) } 
		MAX-ACCESS		read-create
		STATUS			current
		DESCRIPTION		"Firewall Protocol"
		::=  {  gemtekDevCpeFirewallEntry  5  }


	gemtekDevCpeFirewallPriority	OBJECT-TYPE	
		SYNTAX			INTEGER  { hi ( 1 ) , two ( 2 ) , three ( 3 ) , four ( 4 ) , five ( 5 ) , six ( 6 ) , seven ( 7 ) , eight ( 8 ) , nine ( 9 ) , lo ( 10 ) } 
		MAX-ACCESS		read-create
		STATUS			current
		DESCRIPTION		"Firewall Entry Priority"
		::=  {  gemtekDevCpeFirewallEntry  6  }


	gemtekDevCpeFirewallEntryEnable	OBJECT-TYPE	
		SYNTAX			INTEGER  { disabled ( 0 ) , enabled ( 1 ) } 
		MAX-ACCESS		read-create
		STATUS			current
		DESCRIPTION		"Firewall Entry Enable/Disable"
		::=  {  gemtekDevCpeFirewallEntry  7  }


	gemtekDevCpeFirewallSrcMac	OBJECT-TYPE	
		SYNTAX			OCTET STRING  ( SIZE ( 0 .. 17 ) ) 
		MAX-ACCESS		read-create
		STATUS			current
		DESCRIPTION		"Firewall Source MAC Address"
		::=  {  gemtekDevCpeFirewallEntry  8  }


	gemtekDevCpeFirewallDstMac	OBJECT-TYPE	
		SYNTAX			OCTET STRING  ( SIZE ( 0 .. 17 ) ) 
		MAX-ACCESS		read-create
		STATUS			current
		DESCRIPTION		"Firewall Destination MAC Address"
		::=  {  gemtekDevCpeFirewallEntry  9  }


	gemtekDevCpeFirewallSrcIpAddress	OBJECT-TYPE	
		SYNTAX			IpAddress
		MAX-ACCESS		read-create
		STATUS			current
		DESCRIPTION		"Firewall Source IP Address"
		::=  {  gemtekDevCpeFirewallEntry  10  }


	gemtekDevCpeFirewallDstIpAddress	OBJECT-TYPE	
		SYNTAX			IpAddress
		MAX-ACCESS		read-create
		STATUS			current
		DESCRIPTION		"Firewall Destination IP Address"
		::=  {  gemtekDevCpeFirewallEntry  11  }


	gemtekDevCpeFirewallSrcPortRangeBegin	OBJECT-TYPE	
		SYNTAX			Integer32
		MAX-ACCESS		read-create
		STATUS			current
		DESCRIPTION		"Firewall Source Port Range Begin(1~65535)"
		::=  {  gemtekDevCpeFirewallEntry  12  }


	gemtekDevCpeFirewallSrcPortRangeEnd	OBJECT-TYPE	
		SYNTAX			Integer32
		MAX-ACCESS		read-create
		STATUS			current
		DESCRIPTION		"Firewall Source Port Range End(1~65535)"
		::=  {  gemtekDevCpeFirewallEntry  13  }


	gemtekDevCpeFirewallDstPortRangeBegin	OBJECT-TYPE	
		SYNTAX			Integer32
		MAX-ACCESS		read-create
		STATUS			current
		DESCRIPTION		"Firewall Destination Port Range Begin(1~65535)"
		::=  {  gemtekDevCpeFirewallEntry  14  }


	gemtekDevCpeFirewallDstPortRangeEnd	OBJECT-TYPE	
		SYNTAX			Integer32
		MAX-ACCESS		read-create
		STATUS			current
		DESCRIPTION		"Firewall Destination Port Range End(1~65535)"
		::=  {  gemtekDevCpeFirewallEntry  15  }


	gemtekDevCpeFirewallRowstatus	OBJECT-TYPE	
		SYNTAX			RowStatus
		MAX-ACCESS		read-create
		STATUS			current
		DESCRIPTION		"active(1) to active the row and save setting to memory.
						 createAndWait(5) to create a row in the bottom.
						 destroy(6) to delete a row."
		::=  {  gemtekDevCpeFirewallEntry  16  }

	gemtekDevCpeTelnetEnable	OBJECT-TYPE	
		SYNTAX			INTEGER  { disabled ( 0 ) , enabled ( 1 ) } 
		MAX-ACCESS		read-write
		STATUS			current
		DESCRIPTION		"Telnet Enable/Disable"
		::=  {  gemtekDevCpeFirewall  8  }
		
	gemtekDevCpeFirewallEtherTypeFilterOneEnable	OBJECT-TYPE	
		SYNTAX			INTEGER  { disabled ( 0 ) , enabled ( 1 ) } 
		MAX-ACCESS		read-write
		STATUS			current
		DESCRIPTION		"Firewall Ether-Type Filter Group One Enable/Disable"
		::=  {  gemtekDevCpeFirewall  9  }

	gemtekDevCpeFirewallEtherTypeFilterOneTypeDeny	OBJECT-TYPE	
		SYNTAX			OCTET STRING	( SIZE ( 0 .. 4  ) ) 
		MAX-ACCESS		read-write
		STATUS			current
		DESCRIPTION		"Firewall Ether-Type Filter Group One Type Deny"
		::=  {  gemtekDevCpeFirewall  10  }

	gemtekDevCpeFirewallEtherTypeFilterTwoEnable	OBJECT-TYPE	
		SYNTAX			INTEGER  { disabled ( 0 ) , enabled ( 1 ) } 
		MAX-ACCESS		read-write
		STATUS			current
		DESCRIPTION		"Firewall Ether-Type Filter Group Two Enable/Disable"
		::=  {  gemtekDevCpeFirewall  11  }

	gemtekDevCpeFirewallEtherTypeFilterTwoTypeDeny	OBJECT-TYPE	
		SYNTAX			OCTET STRING	( SIZE ( 0 .. 4  ) ) 
		MAX-ACCESS		read-write
		STATUS			current
		DESCRIPTION		"Firewall Ether-Type Filter Group Two Type Deny"
		::=  {  gemtekDevCpeFirewall  12  }

	gemtekDevCpeFirewallEtherTypeFilterThreeEnable	OBJECT-TYPE	
		SYNTAX			INTEGER  { disabled ( 0 ) , enabled ( 1 ) } 
		MAX-ACCESS		read-write
		STATUS			current
		DESCRIPTION		"Firewall Ether-Type Filter Group Three Enable/Disable"
		::=  {  gemtekDevCpeFirewall  13  }

	gemtekDevCpeFirewallEtherTypeFilterThreeTypeDeny	OBJECT-TYPE	
		SYNTAX			OCTET STRING	( SIZE ( 0 .. 4  ) ) 
		MAX-ACCESS		read-write
		STATUS			current
		DESCRIPTION		"Firewall Ether-Type Filter Group Three Type Deny"
		::=  {  gemtekDevCpeFirewall  14  }

	gemtekDevCpeFirewallEtherTypeFilterFourEnable	OBJECT-TYPE	
		SYNTAX			INTEGER  { disabled ( 0 ) , enabled ( 1 ) } 
		MAX-ACCESS		read-write
		STATUS			current
		DESCRIPTION		"Firewall Ether-Type Filter Group Four Enable/Disable"
		::=  {  gemtekDevCpeFirewall  15  }

	gemtekDevCpeFirewallEtherTypeFilterFourTypeDeny	OBJECT-TYPE	
		SYNTAX			OCTET STRING	( SIZE ( 0 .. 4  ) ) 
		MAX-ACCESS		read-write
		STATUS			current
		DESCRIPTION		"Firewall Ether-Type Filter Group Four Type Deny"
		::=  {  gemtekDevCpeFirewall  16  }

	gemtekDevCpeFirewallEtherTypeFilterFiveEnable	OBJECT-TYPE	
		SYNTAX			INTEGER  { disabled ( 0 ) , enabled ( 1 ) } 
		MAX-ACCESS		read-write
		STATUS			current
		DESCRIPTION		"Firewall Ether-Type Filter Group Five Enable/Disable"
		::=  {  gemtekDevCpeFirewall  17  }

	gemtekDevCpeFirewallEtherTypeFilterFiveTypeDeny	OBJECT-TYPE	
		SYNTAX			OCTET STRING	( SIZE ( 0 .. 4  ) ) 
		MAX-ACCESS		read-write
		STATUS			current
		DESCRIPTION		"Firewall Ether-Type Filter Group Five Type Deny"
		::=  {  gemtekDevCpeFirewall  18  }

	gemtekDevCpeFirewallPPPoEEnable	OBJECT-TYPE
		SYNTAX			INTEGER  { disabled ( 0 ) , enabled ( 1 ) } 
		MAX-ACCESS		read-write
		STATUS			current
		DESCRIPTION		"PPPoE Enable/Disable
						(Only allow PPPoE traffic pass through)"
		::=  {  gemtekDevCpeFirewall  19  }

	gemtekDevCpeServiceFlowTable	OBJECT-TYPE
		SYNTAX		SEQUENCE  OF  GemtekDevCpeServiceFlowEntry
		MAX-ACCESS	not-accessible
		STATUS		current
		DESCRIPTION	"gemtekDevCpeServiceFlowTable"
		::=  { gemtekDevCpeServiceFlow  1 }

	gemtekDevCpeServiceFlowEntry	OBJECT-TYPE
		SYNTAX		GemtekDevCpeServiceFlowEntry
		MAX-ACCESS	not-accessible
		STATUS		current
		DESCRIPTION	"gemtekDevCpeServiceFlowEntry"
		INDEX		{  gemtekDevCpeServiceFlowIndex  }
		::=  { gemtekDevCpeServiceFlowTable 1 }

	GemtekDevCpeServiceFlowEntry  ::=  SEQUENCE {
		gemtekDevCpeServiceFlowIndex  Integer32,
		gemtekDevCpeServiceFlowSFID  Unsigned32,
		gemtekDevCpeServiceFlowCID  Unsigned32,
		gemtekDevCpeServiceFlowBCID  Unsigned32,
		gemtekDevCpeServiceFlowType  INTEGER,
		gemtekDevCpeServiceFlowState  INTEGER,
		gemtekDevCpeServiceFlowDirection  INTEGER,
		gemtekDevCpeServiceFlowEnable  INTEGER,
		gemtekDevCpeServiceFlowScheduling  INTEGER,
		gemtekDevCpeServiceFlowMaxRate  Unsigned32,
		gemtekDevCpeServiceFlowARQ  INTEGER,
		gemtekDevCpeServiceFlowHARQ  INTEGER,
		gemtekDevCpeServiceFlowRules  Unsigned32
		}


	gemtekDevCpeServiceFlowIndex	OBJECT-TYPE	
		SYNTAX			Integer32
		MAX-ACCESS		read-only
		STATUS			current
		DESCRIPTION		"Service Flow Index"
		::=  {  gemtekDevCpeServiceFlowEntry  1  }


	gemtekDevCpeServiceFlowSFID	OBJECT-TYPE	
		SYNTAX			Unsigned32
		MAX-ACCESS		read-only
		STATUS			current
		DESCRIPTION		"Service Flow SFID"
		::=  {  gemtekDevCpeServiceFlowEntry  2  }


	gemtekDevCpeServiceFlowCID	OBJECT-TYPE	
		SYNTAX			Unsigned32
		MAX-ACCESS		read-only
		STATUS			current
		DESCRIPTION		"Service Flow CID"
		::=  {  gemtekDevCpeServiceFlowEntry  3  }


	gemtekDevCpeServiceFlowBCID	OBJECT-TYPE	
		SYNTAX			Unsigned32
		MAX-ACCESS		read-only
		STATUS			current
		DESCRIPTION		"Service Flow Basic CID"
		::=  {  gemtekDevCpeServiceFlowEntry  4  }
 
 
 	gemtekDevCpeServiceFlowType	OBJECT-TYPE	
		SYNTAX			INTEGER   { basic ( 0 ) , primary ( 1 ) , secondary ( 2 ) , data ( 3 ) , multicast ( 4 )  }
		MAX-ACCESS		read-only
		STATUS			current
		DESCRIPTION		"Service Flow Type:
						0:basic
						1:primary
						2:secondary
						3:data
						4multicast"
		::=  {  gemtekDevCpeServiceFlowEntry  5  }


	gemtekDevCpeServiceFlowState	OBJECT-TYPE	
		SYNTAX			INTEGER  { provisioned ( 0 ) , admitted ( 1 ) , active ( 2 )  }
		MAX-ACCESS		read-only
		STATUS			current
		DESCRIPTION		"Service Flow State:
						0:provisioned
						1:admitted
						2:active"
		::=  {  gemtekDevCpeServiceFlowEntry  6  }


	gemtekDevCpeServiceFlowDirection	OBJECT-TYPE	
		SYNTAX			INTEGER  { uplink ( 1 ) , downlink ( 2 ) , bidirectional ( 3 )  }
		MAX-ACCESS		read-only
		STATUS			current
		DESCRIPTION		"Service Flow Direction
						1:uplink
						2:downlink
						3:bidirectional"
		::=  {  gemtekDevCpeServiceFlowEntry  7  }


	gemtekDevCpeServiceFlowEnable	OBJECT-TYPE	
		SYNTAX			INTEGER  { disable ( 0 ) , enable ( 1 ) }
		MAX-ACCESS		read-only
		STATUS			current
		DESCRIPTION		"Service Flow Enable/Disable"
		::=  {  gemtekDevCpeServiceFlowEntry  8  }


	gemtekDevCpeServiceFlowScheduling	OBJECT-TYPE	
		SYNTAX			INTEGER  { bestEffort ( 2 ) ,  nrtps( 3 ) , rtps ( 4 ) , ertps ( 5 ) , ugs ( 6 )  }
		MAX-ACCESS		read-only
		STATUS			current
		DESCRIPTION		"Service Flow Scheduling type"
		::=  {  gemtekDevCpeServiceFlowEntry  9  }


	gemtekDevCpeServiceFlowMaxRate	OBJECT-TYPE	
		SYNTAX			Unsigned32
		MAX-ACCESS		read-only
		STATUS			current                                                                         
		DESCRIPTION		"Service Flow Max Rate(bit/s)"
		::=  {  gemtekDevCpeServiceFlowEntry  10  }


	gemtekDevCpeServiceFlowARQ	OBJECT-TYPE	
		SYNTAX			INTEGER { no ( 0 ) , yes ( 1 ) }
		MAX-ACCESS		read-only
		STATUS			current
		DESCRIPTION		"Service Flow ARQ Enable yes/no"
		::=  {  gemtekDevCpeServiceFlowEntry  11  }


	gemtekDevCpeServiceFlowHARQ	OBJECT-TYPE	
		SYNTAX			INTEGER { no ( 0 ) , yes ( 1 ) }
		MAX-ACCESS		read-only
		STATUS			current
		DESCRIPTION		"Service Flow HARQ Enable yes/no"
		::=  {  gemtekDevCpeServiceFlowEntry  12  }

	gemtekDevCpeServiceFlowRules	OBJECT-TYPE	
		SYNTAX			Unsigned32
		MAX-ACCESS		read-only
		STATUS			current
		DESCRIPTION		"Service Flow calssifier rule numbers"
		::=  {  gemtekDevCpeServiceFlowEntry  13  }

	gemtekDevCpePullFtpServerIP	OBJECT-TYPE	
		SYNTAX			IpAddress
		MAX-ACCESS		read-write
		STATUS			current
		DESCRIPTION		"FTP upgrade server IP"
		::=  {  gemtekDevCpePullFtpUpgrade  1  }

	gemtekDevCpePullFtpServerUserName	OBJECT-TYPE	
		SYNTAX			OCTET STRING  ( SIZE ( 0 .. 32 ) ) 
		MAX-ACCESS		read-write
		STATUS			current
		DESCRIPTION		"Ftp Server User Name"
		::=  {  gemtekDevCpePullFtpUpgrade  2  }

	gemtekDevCpePullFtpServerPassword	OBJECT-TYPE	
		SYNTAX			OCTET STRING  ( SIZE ( 0 .. 32 ) ) 
		MAX-ACCESS		read-write
		STATUS			current
		DESCRIPTION		"Ftp Server Password"
		::=  {  gemtekDevCpePullFtpUpgrade  3  }

	gemtekDevCpePullFtpFilePath	OBJECT-TYPE	
		SYNTAX			OCTET STRING  ( SIZE ( 0 .. 256  ) ) 
		MAX-ACCESS		read-write
		STATUS			current
		DESCRIPTION		"Ftp File Path"
		::=  {  gemtekDevCpePullFtpUpgrade  4  }

	gemtekDevCpePullFtpFileName	OBJECT-TYPE	
		SYNTAX			OCTET STRING  ( SIZE ( 0 .. 255 ) )
		MAX-ACCESS		read-write
		STATUS			current
		DESCRIPTION		"Ftp File Name"
		::=  {  gemtekDevCpePullFtpUpgrade  5  }

	gemtekDevCpePullFtpUpgradeCmd	OBJECT-TYPE	
		SYNTAX			INTEGER  { default ( 0 ) , downloadAndUpgrade ( 1 ) , rollback ( 2 ) } 
		MAX-ACCESS		read-write
		STATUS			current
		DESCRIPTION		"Control FTP upgrade"
		::=  {  gemtekDevCpePullFtpUpgrade  6  }

	gemtekDevCpePullFtpUpgradeAdminStatus	OBJECT-TYPE	
		SYNTAX			INTEGER  { ready ( 0 ) , downloading ( 1 ) , installing ( 2 ) , error ( 3 ) , success ( 4 ) } 
		MAX-ACCESS		read-only
		STATUS			current
		DESCRIPTION		"Device status information on the progress of the upgrade."
		::=  {  gemtekDevCpePullFtpUpgrade  7  }

	gemtekDevCpeCurrentSwVersion	OBJECT-TYPE	
		SYNTAX			OCTET STRING  ( SIZE ( 0 .. 255  ) ) 
		MAX-ACCESS		read-only
		STATUS			current
		DESCRIPTION		"This value identifies the version of software currently running in the CPE"
		::=  {  gemtekDevCpePushFtpUpgrade  1  }
		
	gemtekDevCpePreviousSwVersion	OBJECT-TYPE	
		SYNTAX			OCTET STRING  ( SIZE ( 0 .. 255  ) ) 
		MAX-ACCESS		read-only
		STATUS			current
		DESCRIPTION		"This value identifies the previous software version in the CPE"
		::=  {  gemtekDevCpePushFtpUpgrade  2  }

	gemtekDevCpeDownloadSwVersion	OBJECT-TYPE	
		SYNTAX			OCTET STRING  ( SIZE ( 0 .. 255  ) ) 
		MAX-ACCESS		read-write
		STATUS			current
		DESCRIPTION		"This value identifies the version of software to download"
		::=  {  gemtekDevCpePushFtpUpgrade  3  }

	gemtekDevCpePushFtpUpgradeCmd	OBJECT-TYPE	
		SYNTAX			INTEGER  { default ( 0 ) , download ( 1 ) , upgrade ( 2 ) , rollback ( 3 ) } 
		MAX-ACCESS		read-write
		STATUS			current
		DESCRIPTION		"Control FTP upgrade process"
		::=  {  gemtekDevCpePushFtpUpgrade  4  }

	gemtekDevCpePushFtpUpgradeAdminStatus	OBJECT-TYPE	
		SYNTAX			INTEGER  { ready ( 0 ) , installing ( 1 ) , error ( 2 ) , success ( 3 ) } 
		MAX-ACCESS		read-only
		STATUS			current
		DESCRIPTION		"Device status information on the progress of the upgrade."
		::=  {  gemtekDevCpePushFtpUpgrade  5  }

	gemtekDevCpeWimaxRssi	OBJECT-TYPE	
		SYNTAX			OCTET STRING  ( SIZE ( 0 .. 32  ) ) 
		MAX-ACCESS		read-only
		STATUS			current
		DESCRIPTION		"RSSI Report(dBm)"
		::=  {  wirelessStatus  1  }

	gemtekDevCpeWimaxCinr	OBJECT-TYPE	
		SYNTAX			OCTET STRING  ( SIZE ( 0 .. 32  ) ) 
		MAX-ACCESS		read-only
		STATUS			current
		DESCRIPTION		"CINR Report(dB)"
		::=  {  wirelessStatus  2  }

	gemtekDevCpeWimaxTxPower	OBJECT-TYPE	
		SYNTAX			OCTET STRING  ( SIZE ( 0 .. 32  ) ) 
		MAX-ACCESS		read-only
		STATUS			current
		DESCRIPTION		"Tx Power Report(dBm)"
		::=  {  wirelessStatus  3  }

	gemtekDevCpeWimaxMaxTxPower	OBJECT-TYPE	
		SYNTAX			OCTET STRING  ( SIZE ( 0 .. 32  ) ) 
		MAX-ACCESS		read-only
		STATUS			current
		DESCRIPTION		"MAX Tx Power Report(dBm)"
		::=  {  wirelessStatus  4  }

	gemtekDevCpeWimaxUpLinkModulation	OBJECT-TYPE	
		SYNTAX			OCTET STRING  ( SIZE ( 0 .. 255  ) ) 
		MAX-ACCESS		read-only
		STATUS			current
		DESCRIPTION		"Up Link Modulation Type :
						QPSK [CC] 1/2
						QPSK [CC] 3/4
						16-QAM [CC] 1/2
						16-QAM [CC] 3/4
						64-QAM [CC] 1/2
						64-QAM [CC] 2/3
						64-QAM [CC] 3/4
						QPSK [BTC] 1/2
						QPSK [BTC] 3/4
						16-QAM [BTC] 3/5
						16-QAM [BTC] 4/5
						64-QAM [BTC] 5/8
						64-QAM [BTC] 4/5
						QPSK [CTC] 1/2
						Reserved
						QPSK [CTC] 3/4
						16-QAM [CTC] 1/2
						16-QAM [CTC] 3/4
						64-QAM [CTC] 1/2
						64-QAM [CTC] 2/3
						64-QAM [CTC] 3/4
						64-QAM [CTC] 5/6
						QPSK [ZT CC] 1/2
						QPSK [ZT CC] 3/4
						16-QAM [ZT CC] 1/2
						16-QAM [ZT CC] 3/4
						64-QAM [ZT CC] 1/2
						64-QAM [ZT CC] 2/3
						64-QAM [ZT CC] 3/4
						QPSK [LDPC] 1/2
						QPSK [LDPC] 2/3 A code
						QPSK [LDPC] 3/4 A code
						16-QAM [LDPC] 1/2
						16-QAM [LDPC] 2/3 A code
						16-QAM [LDPC] 3/4 A code
						64-QAM [LDPC] 1/2
						64-QAM [LDPC] 2/3 A code
						64-QAM [LDPC] 3/4 A code
						QPSK [CC with optional interleaver] 1/2
						QPSK [CC with optional interleaver] 3/4
						16-QAM [CC with optional interleaver] 1/2
						16-QAM [CC with optional interleaver] 3/4
						64-QAM [CC with optional interleaver] 2/3
						64-QAM [CC with optional interleaver] 3/4
						QPSK [LDPC] 5/6
						16-QAM [LDPC] 5/6
						64-QAM [LDPC] 5/6"
		::=  {  wirelessStatus  5  }

	gemtekDevCpeWimaxDownLinkModulation	OBJECT-TYPE	
		SYNTAX			OCTET STRING  ( SIZE ( 0 .. 255  ) ) 
		MAX-ACCESS		read-only
		STATUS			current
		DESCRIPTION		"Down Link Modulation Type :
						QPSK [CC] 1/2
						QPSK [CC] 3/4
						16-QAM [CC] 1/2
						16-QAM [CC] 3/4
						64-QAM [CC] 1/2
						64-QAM [CC] 2/3
						64-QAM [CC] 3/4
						QPSK [BTC] 1/2
						QPSK [BTC] 3/4 or 2/3
						16-QAM [BTC] 3/5
						16-QAM [BTC] 4/5
						64-QAM [BTC] 2/3 or 5/8
						64-QAM [BTC] 5/6 or 4/5
						QPSK [CTC] 1/2
						Reserved
						QPSK [CTC] 3/4
						16-QAM [CTC] 1/2
						16-QAM [CTC] 3/4
						64-QAM [CTC] 1/2
						64-QAM [CTC] 2/3
						64-QAM [CTC] 3/4
						64-QAM [CTC] 5/6
						QPSK [ZT CC] 1/2
						QPSK [ZT CC] 3/4
						16-QAM [ZT CC] 1/2
						16-QAM [ZT CC] 3/4
						64-QAM [ZT CC] 1/2
						64-QAM [ZT CC] 2/3
						64-QAM [ZT CC] 3/4
						QPSK [LDPC] 1/2
						QPSK [LDPC] 2/3 A code
						QPSK [LDPC] 3/4 A code
						16-QAM [LDPC] 1/2
						16-QAM [LDPC] 2/3 A code
						16-QAM [LDPC] 3/4 A code
						64-QAM [LDPC] 1/2
						64-QAM [LDPC] 2/3 A code
						64-QAM [LDPC] 3/4 A code
						QPSK [LDPC] 2/3 B code
						QPSK [LDPC] 3/4 B code
						16-QAM [LDPC] 2/3 B code
						16-QAM [LDPC] 3/4 B code
						64-QAM [LDPC] 2/3 B code
						64-QAM [LDPC] 3/4 B code
						QPSK [CC with optional interleaver] 1/2
						QPSK [CC with optional interleaver] 3/4
						16-QAM [CC with optional interleaver] 1/2
						16-QAM [CC with optional interleaver] 3/4
						64-QAM [CC with optional interleaver] 2/3
						64-QAM [CC with optional interleaver] 3/4
						QPSK [LDPC] 5/6
						16-QAM [LDPC] 5/6
						64-QAM [LDPC] 5/6"
		::=  {  wirelessStatus  6  }

	gemtekDevCpeWimaxBsid	OBJECT-TYPE	
		SYNTAX			OCTET STRING  ( SIZE ( 0 .. 18  ) ) 
		MAX-ACCESS		read-only
		STATUS			current
		DESCRIPTION		"Base Station MAC Address"
		::=  {  wirelessStatus  7  }

	gemtekDevCpeWimaxFrequency	OBJECT-TYPE	
		SYNTAX			Unsigned32
		MAX-ACCESS		read-only
		STATUS			current
		DESCRIPTION		"Center Frequency (kHz)"
		::=  {  wirelessStatus  8  }

	gemtekDevCpeWimaxUpLinkDataRate	OBJECT-TYPE	
		SYNTAX			OCTET STRING  ( SIZE ( 0 .. 32  ) )
		MAX-ACCESS		read-only
		STATUS			current
		DESCRIPTION		"Up Link Data Rate Report(Kbps)"
		::=  {  wirelessStatus  9  }

	gemtekDevCpeWimaxDownLinkDataRate	OBJECT-TYPE	
		SYNTAX			OCTET STRING  ( SIZE ( 0 .. 32  ) )
		MAX-ACCESS		read-only
		STATUS			current
		DESCRIPTION		"Down Link Data Rate Report(Kbps)"
		::=  {  wirelessStatus  10  }

	gemtekDevCpeWimaxTotalUpLinkDataByte	OBJECT-TYPE	
		SYNTAX			Unsigned32
		MAX-ACCESS		read-only
		STATUS			current
		DESCRIPTION		"Total Up Link Data Bytes Report(Bytes)"
		::=  {  wirelessStatus  11  }

	gemtekDevCpeWimaxTotalDownLinkDataByte	OBJECT-TYPE	
		SYNTAX			Unsigned32
		MAX-ACCESS		read-only
		STATUS			current
		DESCRIPTION		"Total Down Link Data Bytes Report(Bytes)"
		::=  {  wirelessStatus  12  }

	gemtekDevCpeWimaxCpeState	OBJECT-TYPE	
		SYNTAX			OCTET STRING  ( SIZE ( 0 .. 255  ) ) 
		MAX-ACCESS		read-only
		STATUS			current
		DESCRIPTION		"CPE State"
		::=  {  wirelessStatus  13  }

	gemtekDevCpeWimaxCinrReuse1	OBJECT-TYPE	
		SYNTAX			OCTET STRING  ( SIZE ( 0 .. 32  ) ) 
		MAX-ACCESS		read-only
		STATUS			current
		DESCRIPTION		"CINR Reuse1 Report(dB)"
		::=  {  wirelessStatus  14  }

	gemtekDevCpeWimaxCinrReuse3	OBJECT-TYPE	
		SYNTAX			OCTET STRING  ( SIZE ( 0 .. 32  ) ) 
		MAX-ACCESS		read-only
		STATUS			current
		DESCRIPTION		"CINR Reuse3 Report(dB)"
		::=  {  wirelessStatus  15  }

	gemtekDevCpeWimaxBandwidth	OBJECT-TYPE	
		SYNTAX			Integer32
		MAX-ACCESS		read-only
		STATUS			current
		DESCRIPTION		"CPE Bandwidth(kHz)"
		::=  {  wirelessStatus  16  } 

	gemtekDevCpeWimaxZoneCinrChannelZero	OBJECT-TYPE	
		SYNTAX			OCTET STRING  ( SIZE ( 0 .. 32  ) ) 
		MAX-ACCESS		read-only
		STATUS			current
		DESCRIPTION		"Zone CINR channel 0 Report(dB)"
		::=  {  wirelessStatus  17 }

	gemtekDevCpeWimaxMimoMode	OBJECT-TYPE	
		SYNTAX			INTEGER  { siso ( 0 ) , mimoMatrixA ( 1 ) , mimoMatrixB ( 2 ), disconnect ( 4 ) }  
		MAX-ACCESS		read-only
		STATUS			current
		DESCRIPTION		"MIMO mode status"
		::=  {  wirelessStatus  18 }
		 
	gemtekDevCpeLanMacAddresss	OBJECT-TYPE	
		SYNTAX			OCTET STRING  ( SIZE ( 0 .. 18  ) ) 
		MAX-ACCESS		read-only
		STATUS			current
		DESCRIPTION		"CPE LAN MAC Address"
		::=  {  networkStatus  1  }

	gemtekDevCpeLanTotalDownLinkDataByte	OBJECT-TYPE	
		SYNTAX			Unsigned32
		MAX-ACCESS		read-only
		STATUS			current
		DESCRIPTION		"Total Down Link Data Bytes Report(Bytes)"
		::=  {  networkStatus  2  }

	gemtekDevCpeLanTotalUpLinkDataByte	OBJECT-TYPE	
		SYNTAX			Unsigned32
		MAX-ACCESS		read-only
		STATUS			current
		DESCRIPTION		"Total Up Link Data Bytes Report(Bytes)"
		::=  {  networkStatus  3  }

	gemtekDevCpeLanTotalDownLinkDataPackets	OBJECT-TYPE	
		SYNTAX			Unsigned32
		MAX-ACCESS		read-only
		STATUS			current
		DESCRIPTION		"LAN Total Down Link Data Packets Report(Packets)"
		::=  {  networkStatus  4  }

	gemtekDevCpeLanTotalUpLinkDataPackets	OBJECT-TYPE	
		SYNTAX			Unsigned32
		MAX-ACCESS		read-only
		STATUS			current
		DESCRIPTION		"LAN Total Up Link Data Packets Report(Packets)"
		::=  {  networkStatus  5  }

	gemtekDevCpeWanMacAddresss	OBJECT-TYPE	
		SYNTAX			OCTET STRING  ( SIZE ( 0 .. 18  ) ) 
		MAX-ACCESS		read-only
		STATUS			current
		DESCRIPTION		"CPE WAN MAC Address"
		::=  {  networkStatus  6  }

	gemtekDevCpeWanTotalDownLinkDataPackets	OBJECT-TYPE	
		SYNTAX			Unsigned32
		MAX-ACCESS		read-only
		STATUS			current
		DESCRIPTION		"WAN Total Down Link Data Packets Report(Packets)"
		::=  {  networkStatus  7  }

	gemtekDevCpeWanTotalUpLinkDataPackets	OBJECT-TYPE	
		SYNTAX			Unsigned32
		MAX-ACCESS		read-only
		STATUS			current
		DESCRIPTION		"WAN Total Up Link Data Packets Report(Packets)"
		::=  {  networkStatus  8  }

	gemtekDevCpeHardwareModel	OBJECT-TYPE	
		SYNTAX			OCTET STRING  ( SIZE ( 0 .. 255  ) ) 
		MAX-ACCESS		read-only
		STATUS			current
		DESCRIPTION		"Hardware Model of CPE"
		::=  {  deviceStatus  1  }

	gemtekDevCpeFirmwareVersion	OBJECT-TYPE	
		SYNTAX			OCTET STRING  ( SIZE ( 0 .. 255  ) ) 
		MAX-ACCESS		read-only
		STATUS			current
		DESCRIPTION		"Firmware Version of CPE"
		::=  {  deviceStatus  2  }

	gemtekDevCpeFirmwareCreationDate	OBJECT-TYPE	
		SYNTAX			OCTET STRING  ( SIZE ( 0 .. 255  ) ) 
		MAX-ACCESS		read-only
		STATUS			current
		DESCRIPTION		"Firmware Creation Date"
		::=  {  deviceStatus  3  }

	gemtekDevCpeFrequencyRange	OBJECT-TYPE	
		SYNTAX			OCTET STRING  ( SIZE ( 0 .. 255  ) ) 
		MAX-ACCESS		read-only
		STATUS			current
		DESCRIPTION		"Frequency Range of CPE"
		::=  {  deviceStatus  4  }

	gemtekDevCpeSerialNumber	OBJECT-TYPE	
		SYNTAX			OCTET STRING  ( SIZE ( 0 .. 255  ) ) 
		MAX-ACCESS		read-only
		STATUS			current
		DESCRIPTION		"Serial Number of CPE"
		::=  {  deviceStatus  5  }

	gemtekDevCpeLatitude	OBJECT-TYPE	
		SYNTAX			OCTET STRING  ( SIZE ( 0 .. 16 ) ) 
		MAX-ACCESS		read-write
		STATUS			current
		DESCRIPTION		"CPE Latitude Report"
		::=  {  deviceStatus  6  }

	gemtekDevCpeLongitude	OBJECT-TYPE	
		SYNTAX			OCTET STRING  ( SIZE ( 0 .. 16 ) ) 
		MAX-ACCESS		read-write
		STATUS			current
		DESCRIPTION		"CPE Longitude Report"
		::=  {  deviceStatus  7  }

	gemtekDevCpeHeight	OBJECT-TYPE	
		SYNTAX			OCTET STRING  ( SIZE ( 0 .. 16 ) ) 
		MAX-ACCESS		read-write
		STATUS			current
		DESCRIPTION		"CPE Height Report"
		::=  {  deviceStatus  8  }

	gemtekDevCpeMibsVersion	OBJECT-TYPE	
		SYNTAX			OCTET STRING  ( SIZE ( 0 .. 255  ) ) 
		MAX-ACCESS		read-only
		STATUS			current
		DESCRIPTION		"MIBs Version of CPE"
		::=  {  deviceStatus  9  }
		
	gemtekDevCpeBootromVersion	OBJECT-TYPE	
		SYNTAX			OCTET STRING  ( SIZE ( 0 .. 255  ) ) 
		MAX-ACCESS		read-only
		STATUS			current
		DESCRIPTION		"Bootrom Version of CPE"
		::=  {  deviceStatus  10  }
 
 	gemtekDevCpeBootromCreationDate	OBJECT-TYPE	
		SYNTAX			OCTET STRING  ( SIZE ( 0 .. 255  ) ) 
		MAX-ACCESS		read-only
		STATUS			current
		DESCRIPTION		"Bootrom Creation Date"
		::=  {  deviceStatus  11  }
		
	gemtekDevCpeProductVersion	OBJECT-TYPE	
		SYNTAX			OCTET STRING  ( SIZE ( 0 .. 255  ) ) 
		MAX-ACCESS		read-only
		STATUS			current
		DESCRIPTION		"Product Version of CPE"
		::=  {  deviceStatus  12  }

	trapServerEnable	OBJECT-TYPE	
		SYNTAX			INTEGER  { disabled ( 0 ) , enabled ( 1 ) } 
		MAX-ACCESS		read-write
		STATUS			current
		DESCRIPTION		"Enables/disables trap. Default: Disable"
		::=  {  gemtekDevCpeTrapServer  1  }

	trapServerIp	OBJECT-TYPE	
		SYNTAX			IpAddress
		MAX-ACCESS		read-write
		STATUS			current
		DESCRIPTION		"trap server"
		::=  {  gemtekDevCpeTrapServer  2  }

	trapServerPort	OBJECT-TYPE	
		SYNTAX			Integer32
		MAX-ACCESS		read-write
		STATUS			current
		DESCRIPTION		"trap port"
		::=  {  gemtekDevCpeTrapServer  3  }

	trapServerCommunity	OBJECT-TYPE	
		SYNTAX			OCTET STRING  ( SIZE ( 0 .. 32 ) ) 
		MAX-ACCESS		read-write
		STATUS			current
		DESCRIPTION		"trap community"
		::=  {  gemtekDevCpeTrapServer  4  }

	coldStart	NOTIFICATION-TYPE
		STATUS			current
		DESCRIPTION		"A coldStart trap signifies that the SNMP entity, supporting 
						a notification originator application, is reinitializing itself 
						and that its configuration may have been altered."
		::=  {  gemtekDevCpeTrapPrefix  1  }

	warmStart	NOTIFICATION-TYPE
		STATUS			current
		DESCRIPTION		"A warmStart trap signifies that the SNMP entity, supporting 
						a notification originator application, is reinitializing itself 
						such that its configuration is unaltered."
		::=  {  gemtekDevCpeTrapPrefix  2  }

	fatalErrorRestart	NOTIFICATION-TYPE
		STATUS			current
		DESCRIPTION		"A fatalErrorRestart trap signifies that the SNMP entity, supporting 
						a notification originator application, is reinitializing itself 
						such that fatal error may have occured."
		::=  {  gemtekDevCpeTrapPrefix  3  }

	linkUp	NOTIFICATION-TYPE
		OBJECTS			{ ifIndex, ifAdminStatus, ifOperStatus }
		STATUS			current
		DESCRIPTION		"A linkUp trap signifies that the SNMP entity, acting in an 
						agent role, has detected that the ifOperStatus object for one 
						of its communication links left the down state and transitioned 
						into some other state (but not into the notPresent state).  
						This other state is indicated by the included value of ifOperStatus."
		::=  {  gemtekDevCpeTrapPrefix  4  }
	
	notTheHightestPriorityAP	NOTIFICATION-TYPE
		STATUS			current
		DESCRIPTION		"When the AP preferred selection mode is enabled and the PMP320CPE synchronizes 
						to an AP that is not the highest priority AP in the BSID list, the CPE 
						shall send an SNMP trap after initial service flows and PMP320CPE 
						management IP connectivity are established."
		::=  {  gemtekDevCpeTrapPrefix  5  }
	
	eapTlsPrivateKeyPassword	OBJECT-TYPE	
		SYNTAX			OCTET STRING   ( SIZE ( 0 .. 32 ) )
		MAX-ACCESS		read-write
		STATUS			current
		DESCRIPTION		"EAP-TLS Private key password"
		::=  {  gemtekDevCpeAuthenticationEAPTLS  1  }

	eapTtlsPhase2	OBJECT-TYPE	
		SYNTAX			INTEGER  { pap ( 1 ) , chap ( 2 ) , mschap ( 3 ) , mschapV2 ( 4 ) , md5 ( 5 ) } 
		MAX-ACCESS		read-write
		STATUS			current
		DESCRIPTION		"EAP-TTLS Phase2(PAP/CHAP/MSCHAP/MSCHAPV2/MD5)"
		::=  {  gemtekDevCpeAuthenticationEAPTTLS  1  }

	eapTtlsUsername	OBJECT-TYPE	
		SYNTAX			OCTET STRING   ( SIZE ( 0 .. 32 ) )
		MAX-ACCESS		read-write
		STATUS			current
		DESCRIPTION		"EAP-TTLS Username"
		::=  {  gemtekDevCpeAuthenticationEAPTTLS  2  }

	eapTtlsPassword	OBJECT-TYPE	
		SYNTAX			OCTET STRING   ( SIZE ( 0 .. 32 ) )
		MAX-ACCESS		read-write
		STATUS			current
		DESCRIPTION		"EAP-TTLS Password"
		::=  {  gemtekDevCpeAuthenticationEAPTTLS  3  }

	eapTtlsUseDeviceCertificate	OBJECT-TYPE	
		SYNTAX			INTEGER  { disabled ( 0 ) , enabled ( 1 ) } 
		MAX-ACCESS		read-write
		STATUS			current
		DESCRIPTION		"EAP-TTLS Use device certificate(Disable/Enable)
						 It needs at least one user certificate file.
 						 Please upload a user certificate file to CPE then you can set it enabled."
		::=  {  gemtekDevCpeAuthenticationEAPTTLS  4  }

	eapTtlsPrivateKeyPassword	OBJECT-TYPE	
		SYNTAX			OCTET STRING   ( SIZE ( 0 .. 32 ) )
		MAX-ACCESS		read-write
		STATUS			current
		DESCRIPTION		"EAP-TTLS Private key password(the same as EAP-TLS)."
		::=  {  gemtekDevCpeAuthenticationEAPTTLS  5  }

	gemtekDevCpeBridgeIpType	OBJECT-TYPE	
		SYNTAX			INTEGER  { static ( 0 ) , dhcp ( 1 ) } 
		MAX-ACCESS		read-write
		STATUS			current
		DESCRIPTION		"Bridge IP Type(Static/DHCP)"
		::=  {  gemtekDevCpeBridgeMode  1  }

	gemtekDevCpeBridgeIpAddress	OBJECT-TYPE	
		SYNTAX			IpAddress
		MAX-ACCESS		read-write
		STATUS			current
		DESCRIPTION		"Bridge Mode Static IP Address configuration"
		::=  {  gemtekDevCpeBridgeMode  2  }

	gemtekDevCpeBridgeNetmask	OBJECT-TYPE	
		SYNTAX			IpAddress
		MAX-ACCESS		read-write
		STATUS			current
		DESCRIPTION		"Bridge Mode Static Netmask configuration"
		::=  {  gemtekDevCpeBridgeMode  3  }

	gemtekDevCpeBridgeGateway	OBJECT-TYPE	
		SYNTAX			IpAddress
		MAX-ACCESS		read-write
		STATUS			current
		DESCRIPTION		"Bridge Mode Static IP Gateway"
		::=  {  gemtekDevCpeBridgeMode  4  }
		
	gemtekDevCpeBridgeDhcpLeaseTime	OBJECT-TYPE	
		SYNTAX			Unsigned32 
		MAX-ACCESS		read-only
		STATUS			current
		DESCRIPTION		"Bridge Mode DHCP IP Lease time(sec)."
		::=  {  gemtekDevCpeBridgeMode  5  }

	gemtekDevCpeBridgeDhcpRenewalTime	OBJECT-TYPE	
		SYNTAX			Unsigned32 
		MAX-ACCESS		read-only
		STATUS			current
		DESCRIPTION		"Bridge Mode DHCP IP Renewal time(sec)."
		::=  {  gemtekDevCpeBridgeMode  6  }

	gemtekDevCpeBridgeDhcpRebindTime	OBJECT-TYPE	
		SYNTAX			Unsigned32 
		MAX-ACCESS		read-only
		STATUS			current
		DESCRIPTION		"Bridge Mode DHCP IP Rebind time(sec)."
		::=  {  gemtekDevCpeBridgeMode  7  }
	
 	gemtekDevCpeMVLAN	OBJECT IDENTIFIER
		::=  {  gemtekDevCpeBridgeMode  8  }

 
 	gemtekDevCpeMgmtVlan	OBJECT IDENTIFIER
		::=  {  gemtekDevCpeMVLAN  1  }

 	gemtekDevCpeDataVlan	OBJECT IDENTIFIER
		::=  {  gemtekDevCpeMVLAN  2  }
		
	gemtekDevCpeVlanMembershipTable	OBJECT-TYPE
		SYNTAX		SEQUENCE  OF  GemtekDevCpeVlanMembershipEntry
		MAX-ACCESS	not-accessible
		STATUS		current
		DESCRIPTION	"VLAN Membership Table"
		::=  { gemtekDevCpeMVLAN  3 }

	gemtekDevCpeVlanMembershipEntry	OBJECT-TYPE
		SYNTAX		GemtekDevCpeVlanMembershipEntry
		MAX-ACCESS	not-accessible
		STATUS		current
		DESCRIPTION	"VLAN Membership Entry"
		INDEX		{  gemtekDevCpeVlanMembershipIndex  }
		::=  { gemtekDevCpeVlanMembershipTable 1 }

	GemtekDevCpeVlanMembershipEntry  ::=  SEQUENCE {
		gemtekDevCpeVlanMembershipIndex			Integer32,
		gemtekDevCpeVlanMembershipVidBegin  	Unsigned32,
		gemtekDevCpeVlanMembershipVidEnd		Unsigned32,
		gemtekDevCpeVlanMembershipVidRowstatus	RowStatus
		}
		
 	gemtekDevCpeDscpToVp	OBJECT IDENTIFIER
		::=  {  gemtekDevCpeMVLAN  4  }
			
 	gemtekDevCpePktCounter	OBJECT IDENTIFIER
		::=  {  gemtekDevCpeMVLAN  5  }

	gemtekDevCpeMgmtVlanEnalbe	OBJECT-TYPE	
		SYNTAX			INTEGER  { disabled ( 0 ) , enabled ( 1 ) } 
		MAX-ACCESS		read-write
		STATUS			current
		DESCRIPTION		"Management VLAN (Enabled/Disabled)"
		::=  {  gemtekDevCpeMgmtVlan  1  }
 
 	gemtekDevCpeMgmtVlanVid		OBJECT-TYPE	
		SYNTAX			Unsigned32 
		MAX-ACCESS		read-write
		STATUS			current
		DESCRIPTION		"Setting Management VLAN VID(0~4095)."
		::=  {  gemtekDevCpeMgmtVlan  2  }

 	gemtekDevCpeMgmtVlanVp		OBJECT-TYPE	
		SYNTAX			Unsigned32 
		MAX-ACCESS		read-only
		STATUS			current
		DESCRIPTION		"Management VLAN VP."
		::=  {  gemtekDevCpeMgmtVlan  3  }
 
 	gemtekDevCpeDataVlanEnalbe	OBJECT-TYPE	
		SYNTAX			INTEGER  { disabled ( 0 ) , enabled ( 1 ) } 
		MAX-ACCESS		read-write
		STATUS			current
		DESCRIPTION		"Data VLAN (Enabled/Disabled)"
		::=  {  gemtekDevCpeDataVlan  1  }
 
 	gemtekDevCpeDataVlanVid		OBJECT-TYPE	
		SYNTAX			Unsigned32 
		MAX-ACCESS		read-write
		STATUS			current
		DESCRIPTION		"Setting Data VLAN VID(0~4095)."
		::=  {  gemtekDevCpeDataVlan  2  }

 	gemtekDevCpeAllowPacketType	OBJECT-TYPE	
		SYNTAX			INTEGER  { all ( 0 ) , taggedOnly ( 1 ) , untaggedOnly ( 2 )} 
		MAX-ACCESS		read-write
		STATUS			current
		DESCRIPTION		"Data VLN allow packet type"
		::=  {  gemtekDevCpeDataVlan  3  }
 
	gemtekDevCpeVlanMembershipIndex	OBJECT-TYPE	
		SYNTAX			Integer32
		MAX-ACCESS		read-only
		STATUS			current
		DESCRIPTION		"VLAN Membership Index"
		::=  {  gemtekDevCpeVlanMembershipEntry  1  }

	gemtekDevCpeVlanMembershipVidBegin	OBJECT-TYPE	
		SYNTAX			Unsigned32
		MAX-ACCESS		read-create
		STATUS			current
		DESCRIPTION		"VLAN Membership VLAN VID Begin(0~4095)."
		::=  {  gemtekDevCpeVlanMembershipEntry  2  }

	gemtekDevCpeVlanMembershipVidEnd	OBJECT-TYPE	
		SYNTAX			Unsigned32
		MAX-ACCESS		read-create
		STATUS			current
		DESCRIPTION		"VLAN Membership VLAN VID End(0~4095)."
		::=  {  gemtekDevCpeVlanMembershipEntry  3  }

	gemtekDevCpeVlanMembershipVidRowstatus	OBJECT-TYPE	
		SYNTAX			RowStatus
		MAX-ACCESS		read-create
		STATUS			current
		DESCRIPTION		"active(1) to active the row and save setting to memory.
						 createAndWait(5) to create a row in the bottom.
						 destroy(6) to delete a row.
						 Every row can't overlap(Begin,End).
						 "
		::=  {  gemtekDevCpeVlanMembershipEntry  4  }		

 	gemtekDevCpeDscpToVpMapping		OBJECT-TYPE	
		SYNTAX			OCTET STRING  ( SIZE ( 0 .. 64 ) ) 
		MAX-ACCESS		read-write
		STATUS			current
		DESCRIPTION		"DSCP To VP Mapping, CP00~CP63,CP00=0,CP48=6,CP56=7."
		::=  {  gemtekDevCpeDscpToVp  1  }

	gemtekDevCpeTaggedPkts	OBJECT-TYPE	
		SYNTAX			Unsigned32
		MAX-ACCESS		read-only
		STATUS			current
		DESCRIPTION		"CPE tagged packets."
		::=  {  gemtekDevCpePktCounter  1  }		

  	gemtekDevCpeTaggedPktsReset	OBJECT-TYPE	
		SYNTAX			INTEGER  { default ( 0 ) , reset ( 1 ) } 
		MAX-ACCESS		read-write
		STATUS			current
		DESCRIPTION		"Reset CPE tagged packets."
		::=  {  gemtekDevCpePktCounter  2  }
		
	gemtekDevCpeUntaggedPkts	OBJECT-TYPE	
		SYNTAX			Unsigned32
		MAX-ACCESS		read-only
		STATUS			current
		DESCRIPTION		"CPE tagged packets."
		::=  {  gemtekDevCpePktCounter  3  }

  	gemtekDevCpeUntaggedPktsReset	OBJECT-TYPE	
		SYNTAX			INTEGER  { default ( 0 ) , reset ( 1 ) } 
		MAX-ACCESS		read-write
		STATUS			current
		DESCRIPTION		"Reset CPE untagged packets."
		::=  {  gemtekDevCpePktCounter  4  }
		
	gemtekDevCpeNonmemberPkts	OBJECT-TYPE	
		SYNTAX			Unsigned32
		MAX-ACCESS		read-only
		STATUS			current
		DESCRIPTION		"CPE Non-member packets."
		::=  {  gemtekDevCpePktCounter  5  }

  	gemtekDevCpeNonmemberPktsReset	OBJECT-TYPE	
		SYNTAX			INTEGER  { default ( 0 ) , reset ( 1 ) } 
		MAX-ACCESS		read-write
		STATUS			current
		DESCRIPTION		"Reset CPE Non-member packets."
		::=  {  gemtekDevCpePktCounter  6  }

	gemtekDevCpeNatWanIpType	OBJECT-TYPE	
		SYNTAX			INTEGER  { static ( 0 ) , dhcp ( 1 ) } 
		MAX-ACCESS		read-write
		STATUS			current
		DESCRIPTION		"NAT WAN IP Type(Static/DHCP)"
		::=  {  gemtekDevCpeNatMode  1  }

	gemtekDevCpeNatWanIpAddress	OBJECT-TYPE	
		SYNTAX			IpAddress
		MAX-ACCESS		read-write
		STATUS			current
		DESCRIPTION		"NAT Static WAN IP Address configuration"
		::=  {  gemtekDevCpeNatMode  2  }

	gemtekDevCpeNatWanNetmask	OBJECT-TYPE	
		SYNTAX			IpAddress
		MAX-ACCESS		read-write
		STATUS			current
		DESCRIPTION		"NAT Static WAN Netmask configuration"
		::=  {  gemtekDevCpeNatMode  3  }

	gemtekDevCpeNatWanGateway	OBJECT-TYPE	
		SYNTAX			IpAddress
		MAX-ACCESS		read-write
		STATUS			current
		DESCRIPTION		"NAT Static WAN Gateway configuration"
		::=  {  gemtekDevCpeNatMode  4  }
 
	gemtekDevCpeNatWanDhcpLeaseTime	OBJECT-TYPE	
		SYNTAX			Unsigned32 
		MAX-ACCESS		read-only
		STATUS			current
		DESCRIPTION		"NAT Mode DHCP IP Lease time(sec)."
		::=  {  gemtekDevCpeNatMode  14  }

	gemtekDevCpeNatWanDhcpRenewalTime	OBJECT-TYPE	
		SYNTAX			Unsigned32 
		MAX-ACCESS		read-only
		STATUS			current
		DESCRIPTION		"NAT Mode DHCP IP Renewal time(sec)."
		::=  {  gemtekDevCpeNatMode  15  }

	gemtekDevCpeNatWanDhcpRebindTime	OBJECT-TYPE	
		SYNTAX			Unsigned32 
		MAX-ACCESS		read-only
		STATUS			current
		DESCRIPTION		"NAT Mode DHCP IP Rebind time(sec)."
		::=  {  gemtekDevCpeNatMode  16  }
 
 	gemtekDevCpeNatLanIpType	OBJECT-TYPE	
		SYNTAX			INTEGER  { static ( 0 ) , dhcp ( 1 ) } 
		MAX-ACCESS		read-only
		STATUS			current
		DESCRIPTION		"NAT LAN IP Type(Static/DHCP)"
		::=  {  gemtekDevCpeNatMode  5  } 
 
	gemtekDevCpeNatLanIpAddress	OBJECT-TYPE	
		SYNTAX			IpAddress
		MAX-ACCESS		read-write
		STATUS			current
		DESCRIPTION		"NAT LAN IP Address configuration"
		::=  {  gemtekDevCpeNatMode  6  }

	gemtekDevCpeNatLanNetmask	OBJECT-TYPE	
		SYNTAX			IpAddress
		MAX-ACCESS		read-write
		STATUS			current
		DESCRIPTION		"NAT LAN Netmask configuration"
		::=  {  gemtekDevCpeNatMode  7  }

	gemtekDevCpeNatMtu	OBJECT-TYPE	
		SYNTAX			Integer32
		MAX-ACCESS		read-write
		STATUS			current
		DESCRIPTION		"NAT Ethernet MTU size(Default:1476)"
		::=  {  gemtekDevCpeNatMode  8  }

	gemtekDevCpeDhcpServer	OBJECT IDENTIFIER
		::=  {  gemtekDevCpeNatMode  9  }

	gemtekDevCpePortForwarding	OBJECT IDENTIFIER
		::=  {  gemtekDevCpeNatMode  10  }

	gemtekDevCpePortTrigger	OBJECT IDENTIFIER
		::=  {  gemtekDevCpeNatMode  11  }

	gemtekDevCpeDhcpClientList	OBJECT IDENTIFIER
		::=  {  gemtekDevCpeNatMode  12  }
 
 	gemtekDevCpeDscpConfiguration	OBJECT IDENTIFIER
		::=  {  gemtekDevCpeNatMode  13  }

	gemtekDevCpeNatModeVLAN	OBJECT IDENTIFIER
		::=  {  gemtekDevCpeNatMode  17  }   
		           
	gemtekDevCpeNatModeMgmtVlan	OBJECT IDENTIFIER
		::=  {  gemtekDevCpeNatModeVLAN  1  }

 	gemtekDevCpeNatModeDataVlan	OBJECT IDENTIFIER
		::=  {  gemtekDevCpeNatModeVLAN  2  }
	
	gemtekDevCpeNatModeMgmtVlanEnalbe	OBJECT-TYPE	
		SYNTAX			INTEGER  { disabled ( 0 ) , enabled ( 1 ) } 
		MAX-ACCESS		read-write
		STATUS			current
		DESCRIPTION		"[Nat Mode] Management VLAN (Enabled/Disabled)"
		::=  {  gemtekDevCpeNatModeMgmtVlan  1  }
 
 	gemtekDevCpeNatModeMgmtVlanVid		OBJECT-TYPE	
		SYNTAX			Unsigned32 
		MAX-ACCESS		read-write
		STATUS			current
		DESCRIPTION		"[Nat Mode] Setting Management VLAN VID(1~4095)."
		::=  {  gemtekDevCpeNatModeMgmtVlan  2  }

 	gemtekDevCpeNatModeMgmtVlanVp		OBJECT-TYPE	
		SYNTAX			Unsigned32 
		MAX-ACCESS		read-write
		STATUS			current
		DESCRIPTION		"[Nat Mode] Setting Management VLAN VP(0~7)."
		::=  {  gemtekDevCpeNatModeMgmtVlan  3  }
 
 	gemtekDevCpeNatModeDataVlanEnalbe	OBJECT-TYPE	
		SYNTAX			INTEGER  { disabled ( 0 ) , enabled ( 1 ) } 
		MAX-ACCESS		read-write
		STATUS			current
		DESCRIPTION		"[Nat Mode] Data VLAN (Enabled/Disabled)"
		::=  {  gemtekDevCpeNatModeDataVlan  1  }
 
 	gemtekDevCpeNatModeDataVlanVid		OBJECT-TYPE	
		SYNTAX			Unsigned32 
		MAX-ACCESS		read-write
		STATUS			current
		DESCRIPTION		"[Nat Mode] Setting Data VLAN VID(1~4095)."
		::=  {  gemtekDevCpeNatModeDataVlan  2  }
					                               
	gemtekDevCpeNatModeDataVlanVp		OBJECT-TYPE	
		SYNTAX			Unsigned32 
		MAX-ACCESS		read-write
		STATUS			current
		DESCRIPTION		"[Nat Mode] Setting Data VLAN VP(0~7)."
		::=  {  gemtekDevCpeNatModeDataVlan  3  }
						                               
	gemtekDevCpeDhcpServerEnable	OBJECT-TYPE	
		SYNTAX			INTEGER  { disabled ( 0 ) , enabled ( 1 ) } 
		MAX-ACCESS		read-write
		STATUS			current
		DESCRIPTION		"DHCP Server Enable/Disable"
		::=  {  gemtekDevCpeDhcpServer  1  }

	gemtekDevCpeDhcpServerStartIp	OBJECT-TYPE	
		SYNTAX			IpAddress
		MAX-ACCESS		read-write
		STATUS			current
		DESCRIPTION		"DHCP Server Start IP"
		::=  {  gemtekDevCpeDhcpServer  2  }

	gemtekDevCpeDhcpServerEndIp	OBJECT-TYPE	
		SYNTAX			IpAddress
		MAX-ACCESS		read-write
		STATUS			current
		DESCRIPTION		"DHCP Server End IP"
		::=  {  gemtekDevCpeDhcpServer  3  }

	gemtekDevCpeDhcpServerPrimaryDnsIp	OBJECT-TYPE	
		SYNTAX			IpAddress
		MAX-ACCESS		read-write
		STATUS			current
		DESCRIPTION		"DHCP Server Primary DNS IP Address configuration"
		::=  {  gemtekDevCpeDhcpServer  4  }

	gemtekDevCpeDhcpServerPrimaryDnsFromIsp	OBJECT-TYPE	
		SYNTAX			INTEGER  { disabled ( 0 ) , enabled ( 1 ) } 
		MAX-ACCESS		read-write
		STATUS			current
		DESCRIPTION		"DHCP Server Primary DNS From ISP Enable/Disable"
		::=  {  gemtekDevCpeDhcpServer  5  }

	gemtekDevCpeDhcpServerSecondDnsIp	OBJECT-TYPE	
		SYNTAX			IpAddress
		MAX-ACCESS		read-write
		STATUS			current
		DESCRIPTION		"DHCP Server Second DNS IP Address configuration"
		::=  {  gemtekDevCpeDhcpServer  6  }

	gemtekDevCpeDhcpServerSecondDnsFromIsp	OBJECT-TYPE	
		SYNTAX			INTEGER  { disabled ( 0 ) , enabled ( 1 ) } 
		MAX-ACCESS		read-write
		STATUS			current
		DESCRIPTION		"DHCP Server Second DNS From ISP Enable/Disable"
		::=  {  gemtekDevCpeDhcpServer  7  }

	gemtekDevCpeDhcpServerTertiaryDnsIp	OBJECT-TYPE	
		SYNTAX			IpAddress
		MAX-ACCESS		read-write
		STATUS			current
		DESCRIPTION		"DHCP Server Tertiary DNS IP Address configuration"
		::=  {  gemtekDevCpeDhcpServer  8  }

	gemtekDevCpeDhcpServerTertiaryDnsFromIsp	OBJECT-TYPE	
		SYNTAX			INTEGER  { disabled ( 0 ) , enabled ( 1 ) } 
		MAX-ACCESS		read-write
		STATUS			current
		DESCRIPTION		"DHCP Server Tertiary DNS From ISP Enable/Disable"
		::=  {  gemtekDevCpeDhcpServer  9  }

	gemtekDevCpeDhcpServerDomainName	OBJECT-TYPE	
		SYNTAX			OCTET STRING ( SIZE ( 0 .. 64 ) ) 
		MAX-ACCESS		read-write
		STATUS			current
		DESCRIPTION		"DHCP Server Domain Name"
		::=  {  gemtekDevCpeDhcpServer  10  }

	gemtekDevCpeDhcpServerMaxLeaseTime	OBJECT-TYPE	
		SYNTAX			Integer32
		MAX-ACCESS		read-write
		STATUS			current
		DESCRIPTION		"DHCP Server MAX Lease Time"
		::=  {  gemtekDevCpeDhcpServer  11  }

	gemtekDevCpeDhcpServerPermanentHostTable	OBJECT-TYPE
		SYNTAX		SEQUENCE  OF  GemtekDevCpeDhcpServerPermanentHostEntry
		MAX-ACCESS	not-accessible
		STATUS		current
		DESCRIPTION	"DHCP Server Permanent Host Table"
		::=  { gemtekDevCpeDhcpServer  12 }

	gemtekDevCpeDhcpServerPermanentHostEntry	OBJECT-TYPE
		SYNTAX		GemtekDevCpeDhcpServerPermanentHostEntry
		MAX-ACCESS	not-accessible
		STATUS		current
		DESCRIPTION	"DHCP Server Permanent Host Entry"
		INDEX		{  gemtekDevCpeDhcpServerPermanentHostIndex  }
		::=  { gemtekDevCpeDhcpServerPermanentHostTable 1 }

	GemtekDevCpeDhcpServerPermanentHostEntry  ::=  SEQUENCE {
		gemtekDevCpeDhcpServerPermanentHostIndex  Integer32,
		gemtekDevCpeDhcpServerPermanentHostMac  OCTET STRING,
		gemtekDevCpeDhcpServerPermanentHostIp  IpAddress,
		gemtekDevCpeDhcpServerPermanentHostEntryEnable  INTEGER,
		gemtekDevCpeDhcpServerPermanentRowstatus  RowStatus
		}


	gemtekDevCpeDhcpServerPermanentHostIndex	OBJECT-TYPE	
		SYNTAX			Integer32
		MAX-ACCESS		read-only
		STATUS			current
		DESCRIPTION		"DHCP Server Permanent Host Index"
		::=  {  gemtekDevCpeDhcpServerPermanentHostEntry  1  }


	gemtekDevCpeDhcpServerPermanentHostMac	OBJECT-TYPE	
		SYNTAX			OCTET STRING  ( SIZE ( 0 .. 18  ) ) 
		MAX-ACCESS		read-create
		STATUS			current
		DESCRIPTION		"DHCP Server Permanent Host MAC"
		::=  {  gemtekDevCpeDhcpServerPermanentHostEntry  2  }


	gemtekDevCpeDhcpServerPermanentHostIp	OBJECT-TYPE	
		SYNTAX			IpAddress
		MAX-ACCESS		read-create
		STATUS			current
		DESCRIPTION		"DHCP Server Permanent Host IP"
		::=  {  gemtekDevCpeDhcpServerPermanentHostEntry  3  }


	gemtekDevCpeDhcpServerPermanentHostEntryEnable	OBJECT-TYPE	
		SYNTAX			INTEGER  { disabled ( 0 ) , enabled ( 1 ) } 
		MAX-ACCESS		read-create
		STATUS			current
		DESCRIPTION		"DHCP Server Permanent Host Entry Enable/Disable"
		::=  {  gemtekDevCpeDhcpServerPermanentHostEntry  4  }


	gemtekDevCpeDhcpServerPermanentRowstatus	OBJECT-TYPE	
		SYNTAX			RowStatus
		MAX-ACCESS		read-create
		STATUS			current
		DESCRIPTION		"active(1) to active the row and save setting to memory.
						 createAndWait(5) to create a row in the bottom.
						 destroy(6) to delete a row."
		::=  {  gemtekDevCpeDhcpServerPermanentHostEntry  5  }

	gemtekDevCpePortForwardingTable	OBJECT-TYPE
		SYNTAX		SEQUENCE  OF  GemtekDevCpePortForwardingEntry
		MAX-ACCESS	not-accessible
		STATUS		current
		DESCRIPTION	"Port Forwarding Table"
		::=  { gemtekDevCpePortForwarding  1 }

	gemtekDevCpePortForwardingEntry	OBJECT-TYPE
		SYNTAX		GemtekDevCpePortForwardingEntry
		MAX-ACCESS	not-accessible
		STATUS		current
		DESCRIPTION	"Port Forwarding Entry
		WAN End - WAN Begin=LAN End - LAN Begin, WAN End - WAN Begin <=30, 
		WAN Begin=>1 WAN End<=65535, LAN Begin=>1 LAN End<=65535"
		INDEX		{  gemtekDevCpePortForwardingIndex  }
		::=  { gemtekDevCpePortForwardingTable 1 }

	GemtekDevCpePortForwardingEntry  ::=  SEQUENCE {
		gemtekDevCpePortForwardingIndex  Integer32,
		gemtekDevCpePortForwardingWanPortBegin  Integer32,
		gemtekDevCpePortForwardingWanPortEnd  Integer32,
		gemtekDevCpePortForwardingLanIp  IpAddress,
		gemtekDevCpePortForwardingLanPortBegin  Integer32,
		gemtekDevCpePortForwardingLanPortEnd  Integer32,
		gemtekDevCpePortForwardingProtocol  INTEGER,
		gemtekDevCpePortForwardingEntryEnable  INTEGER,
		gemtekDevCpePortForwardingRowstatus  RowStatus
		}


	gemtekDevCpePortForwardingIndex	OBJECT-TYPE	
		SYNTAX			Integer32
		MAX-ACCESS		read-only
		STATUS			current
		DESCRIPTION		"Port Forwarding Index"
		::=  {  gemtekDevCpePortForwardingEntry  1  }


	gemtekDevCpePortForwardingWanPortBegin	OBJECT-TYPE	
		SYNTAX			Integer32
		MAX-ACCESS		read-create
		STATUS			current
		DESCRIPTION		"Port Forwarding Wan Port Begin"
		::=  {  gemtekDevCpePortForwardingEntry  2  }


	gemtekDevCpePortForwardingWanPortEnd	OBJECT-TYPE	
		SYNTAX			Integer32
		MAX-ACCESS		read-create
		STATUS			current
		DESCRIPTION		"Port Forwarding Wan Port End"
		::=  {  gemtekDevCpePortForwardingEntry  3  }


	gemtekDevCpePortForwardingLanIp	OBJECT-TYPE	
		SYNTAX			IpAddress
		MAX-ACCESS		read-create
		STATUS			current
		DESCRIPTION		"Port Forwarding Lan Ip"
		::=  {  gemtekDevCpePortForwardingEntry  4  }


	gemtekDevCpePortForwardingLanPortBegin	OBJECT-TYPE	
		SYNTAX			Integer32
		MAX-ACCESS		read-create
		STATUS			current
		DESCRIPTION		"Port Forwarding Lan Port Begin"
		::=  {  gemtekDevCpePortForwardingEntry  5  }


	gemtekDevCpePortForwardingLanPortEnd	OBJECT-TYPE	
		SYNTAX			Integer32
		MAX-ACCESS		read-create
		STATUS			current
		DESCRIPTION		"Port Forwarding Lan Port End"
		::=  {  gemtekDevCpePortForwardingEntry  6  }


	gemtekDevCpePortForwardingProtocol	OBJECT-TYPE	
		SYNTAX			INTEGER  { tcp ( 0 ) , udp ( 1 ) , tcpAndUdp ( 2 ) } 
		MAX-ACCESS		read-create
		STATUS			current
		DESCRIPTION		"Port Forwarding Entry Protocol"
		::=  {  gemtekDevCpePortForwardingEntry  7  }


	gemtekDevCpePortForwardingEntryEnable	OBJECT-TYPE	
		SYNTAX			INTEGER  { disabled ( 0 ) , enabled ( 1 ) } 
		MAX-ACCESS		read-create
		STATUS			current
		DESCRIPTION		"Port Forwarding Entry Enable"
		::=  {  gemtekDevCpePortForwardingEntry  8  }


	gemtekDevCpePortForwardingRowstatus	OBJECT-TYPE	
		SYNTAX			RowStatus
		MAX-ACCESS		read-create
		STATUS			current
		DESCRIPTION		"active(1) to active the row and save setting to memory.
						 createAndWait(5) to create a row in the bottom.
						 destroy(6) to delete a row."
		::=  {  gemtekDevCpePortForwardingEntry  9  }

	gemtekDevCpePortTriggerTable	OBJECT-TYPE
		SYNTAX		SEQUENCE  OF  GemtekDevCpePortTriggerEntry
		MAX-ACCESS	not-accessible
		STATUS		current
		DESCRIPTION	"Port Trigger Table"
		::=  { gemtekDevCpePortTrigger  1 }

	gemtekDevCpePortTriggerEntry	OBJECT-TYPE
		SYNTAX		GemtekDevCpePortTriggerEntry
		MAX-ACCESS	not-accessible
		STATUS		current
		DESCRIPTION	"Port Trigger Entry
		1<=TriggerPortBegin<TriggerPortEnd<=65535
		1<=ForwardingPortBegin<ForwardingPortEnd<=65535
		(ForwardingPortEnd-ForwardingPortBegin)<=30"
		INDEX		{  gemtekDevCpePortTriggerIndex  }
		::=  { gemtekDevCpePortTriggerTable 1 }

	GemtekDevCpePortTriggerEntry  ::=  SEQUENCE {
		gemtekDevCpePortTriggerIndex  Integer32,
		gemtekDevCpePortTriggerName  OCTET STRING,
		gemtekDevCpePortTriggerTriggerPortBegin  Integer32,
		gemtekDevCpePortTriggerTriggerPortEnd  Integer32,
		gemtekDevCpePortTriggerForwardingPortBegin  Integer32,
		gemtekDevCpePortTriggerForwardingPortEnd  Integer32,
		gemtekDevCpePortTriggerProtocol  INTEGER,
		gemtekDevCpePortTriggerEntryEnable  INTEGER,
		gemtekDevCpePortTriggerRowstatus  RowStatus
		}


	gemtekDevCpePortTriggerIndex	OBJECT-TYPE	
		SYNTAX			Integer32
		MAX-ACCESS		read-only
		STATUS			current
		DESCRIPTION		"Port Trigger Index"
		::=  {  gemtekDevCpePortTriggerEntry  1  }


	gemtekDevCpePortTriggerName	OBJECT-TYPE	
		SYNTAX			OCTET STRING  ( SIZE ( 0 .. 30  ) ) 
		MAX-ACCESS		read-create
		STATUS			current
		DESCRIPTION		"Port Trigger Name"
		::=  {  gemtekDevCpePortTriggerEntry  2  }


	gemtekDevCpePortTriggerTriggerPortBegin	OBJECT-TYPE	
		SYNTAX			Integer32
		MAX-ACCESS		read-create
		STATUS			current
		DESCRIPTION		"Port Trigger Trigger Port Begin"
		::=  {  gemtekDevCpePortTriggerEntry  3  }


	gemtekDevCpePortTriggerTriggerPortEnd	OBJECT-TYPE	
		SYNTAX			Integer32
		MAX-ACCESS		read-create
		STATUS			current
		DESCRIPTION		"Port Trigger Trigger Port End"
		::=  {  gemtekDevCpePortTriggerEntry  4  }


	gemtekDevCpePortTriggerForwardingPortBegin	OBJECT-TYPE	
		SYNTAX			Integer32
		MAX-ACCESS		read-create
		STATUS			current
		DESCRIPTION		"Port Trigger Forwarding Port Begin"
		::=  {  gemtekDevCpePortTriggerEntry  5  }


	gemtekDevCpePortTriggerForwardingPortEnd	OBJECT-TYPE	
		SYNTAX			Integer32
		MAX-ACCESS		read-create
		STATUS			current
		DESCRIPTION		"Port Trigger Forwarding Port End"
		::=  {  gemtekDevCpePortTriggerEntry  6  }


	gemtekDevCpePortTriggerProtocol	OBJECT-TYPE	
		SYNTAX			INTEGER  { tcp ( 0 ) , udp ( 1 ) } 
		MAX-ACCESS		read-create
		STATUS			current
		DESCRIPTION		"Port Trigger Protocol"
		::=  {  gemtekDevCpePortTriggerEntry  7  }


	gemtekDevCpePortTriggerEntryEnable	OBJECT-TYPE	
		SYNTAX			INTEGER  { disabled ( 0 ) , enabled ( 1 ) } 
		MAX-ACCESS		read-create
		STATUS			current
		DESCRIPTION		"Port Trigger Entry Enable"
		::=  {  gemtekDevCpePortTriggerEntry  8  }


	gemtekDevCpePortTriggerRowstatus	OBJECT-TYPE	
		SYNTAX			RowStatus
		MAX-ACCESS		read-create
		STATUS			current
		DESCRIPTION		"active(1) to active the row and save setting to memory.
						 createAndWait(5) to create a row in the bottom.
						 destroy(6) to delete a row."
		::=  {  gemtekDevCpePortTriggerEntry  9  }

	gemtekDevCpeDhcpClentListTable	OBJECT-TYPE
		SYNTAX		SEQUENCE  OF  GemtekDevCpeDhcpClentListEntry
		MAX-ACCESS	not-accessible
		STATUS		current
		DESCRIPTION	"gemtekDevCpeDhcpClentListTable"
		::=  { gemtekDevCpeDhcpClientList  1 }

	gemtekDevCpeDhcpClentListEntry	OBJECT-TYPE
		SYNTAX		GemtekDevCpeDhcpClentListEntry
		MAX-ACCESS	not-accessible
		STATUS		current
		DESCRIPTION	"gemtekDevCpeDhcpClentListEntry"
		INDEX		{  gemtekDevCpeDhcpClentListIndex  }
		::=  { gemtekDevCpeDhcpClentListTable 1 }

	GemtekDevCpeDhcpClentListEntry  ::=  SEQUENCE {
		gemtekDevCpeDhcpClentListIndex  Integer32,
		gemtekDevCpeDhcpClentListIp  IpAddress,
		gemtekDevCpeDhcpClentListMacAddress  OCTET STRING,
		gemtekDevCpeDhcpClentListExpireTime  OCTET STRING
		}


	gemtekDevCpeDhcpClentListIndex	OBJECT-TYPE	
		SYNTAX			Integer32
		MAX-ACCESS		read-only
		STATUS			current
		DESCRIPTION		"DHCP Clent List Index"
		::=  {  gemtekDevCpeDhcpClentListEntry  1  }


	gemtekDevCpeDhcpClentListIp	OBJECT-TYPE	
		SYNTAX			IpAddress
		MAX-ACCESS		read-only
		STATUS			current
		DESCRIPTION		"DHCP Clent List: IP Address"
		::=  {  gemtekDevCpeDhcpClentListEntry  2  }


	gemtekDevCpeDhcpClentListMacAddress	OBJECT-TYPE	
		SYNTAX			OCTET STRING  ( SIZE ( 0 .. 18  ) )
		MAX-ACCESS		read-only
		STATUS			current
		DESCRIPTION		"DHCP Clent List: MAC Address"
		::=  {  gemtekDevCpeDhcpClentListEntry  3  }


	gemtekDevCpeDhcpClentListExpireTime	OBJECT-TYPE	
		SYNTAX			OCTET STRING
		MAX-ACCESS		read-only
		STATUS			current
		DESCRIPTION		"DHCP Clent List: Expire Time"
		::=  {  gemtekDevCpeDhcpClentListEntry  4  } 

	gemtekDevCpeTftpServerIP	OBJECT-TYPE	
		SYNTAX			IpAddress
		MAX-ACCESS		read-write
		STATUS			current
		DESCRIPTION		"TFTP upgrade server IP"
		::=  {  gemtekDevCpeTftpUpgrade  1  }

	gemtekDevCpeTftpFileName	OBJECT-TYPE	
		SYNTAX			OCTET STRING  ( SIZE ( 0 .. 256  ) ) 
		MAX-ACCESS		read-write
		STATUS			current
		DESCRIPTION		"TFTP File Name"
		::=  {  gemtekDevCpeTftpUpgrade  2  }

	gemtekDevCpeTftpUpgradeCmd	OBJECT-TYPE	
		SYNTAX			INTEGER  { default ( 0 ) , downloadAndUpgrade ( 1 ) } 
		MAX-ACCESS		read-write
		STATUS			current
		DESCRIPTION		"Control TFTP upgrade"
		::=  {  gemtekDevCpeTftpUpgrade  3  }

	gemtekDevCpeTftpUpgradeAdminStatus	OBJECT-TYPE	
		SYNTAX			INTEGER  { ready ( 0 ) , downloading ( 1 ) , installing ( 2 ) , error ( 3 ) , success ( 4 ) } 
		MAX-ACCESS		read-only
		STATUS			current
		DESCRIPTION		"Device status information on the progress of the upgrade."
		::=  {  gemtekDevCpeTftpUpgrade  4  }

	gemtekDevCpeMgmtDscpId 	OBJECT-TYPE	
		SYNTAX			Integer32
		MAX-ACCESS		read-write
		STATUS			current
		DESCRIPTION		"MGMT DSCP ID(range:0~63, default:0)"
		::=  {  gemtekDevCpeDscpConfiguration  1  }
 
 	gemtekDevCpeDropDataPacket	OBJECT-TYPE	
		SYNTAX			INTEGER  { disabled ( 0 ) , enabled ( 1 ) } 
		MAX-ACCESS		read-write
		STATUS			current
		DESCRIPTION		"Drop data packet if its dscp is the same as mgmt Enabled/Disabled(default:Disabled)"
		::=  {  gemtekDevCpeDscpConfiguration  2  }

	gemtekDevCpeSyslogEnable	OBJECT-TYPE	
		SYNTAX			INTEGER  { disabled ( 0 ) , enabled ( 1 ) } 
		MAX-ACCESS		read-write
		STATUS			current
		DESCRIPTION		"Send syslog to syslog server enable/disable"
		::=  {  gemtekDevCpeSyslog  1  }

	gemtekDevCpeSyslogServerIp	OBJECT-TYPE	
		SYNTAX			IpAddress
		MAX-ACCESS		read-write
		STATUS			current
		DESCRIPTION		"config syslog server IP"
		::=  {  gemtekDevCpeSyslog  2  }

 	gemtekDevCpeSyslogServerPort	OBJECT-TYPE
		SYNTAX			Integer32
		MAX-ACCESS		read-create
		STATUS			current
		DESCRIPTION		"config syslog server port(1~65535,default:514)"
		::=  {  gemtekDevCpeSyslog  3  }
	
	gemtekDevCpeMaxTxPowerModeSelection	OBJECT-TYPE
		SYNTAX			INTEGER  { rf ( 0 ) , eirp ( 1 ) }
		MAX-ACCESS		read-write
		STATUS			obsolete
		DESCRIPTION		"The variable is deprecated.
						Max Tx Power Mode Selection (RF Mode/EIRP Mode)"
		::=  {  gemtekDevCpeMaxTxPower  1  }
	
	gemtekDevCpeMaxTxPowerRfMode	OBJECT IDENTIFIER
		::=  {  gemtekDevCpeMaxTxPower  2  }
	
	gemtekDevCpeMaxTxPowerEirpMode	OBJECT IDENTIFIER
		::=  {  gemtekDevCpeMaxTxPower  3  }
	
	gemtekDevCpeRfModeBPSK	OBJECT-TYPE
		SYNTAX			Unsigned32 
		MAX-ACCESS		read-write
		STATUS			obsolete
		DESCRIPTION		"The variable is deprecated.
						RF Mode BPSK Setting(0~2750)"
		::=  {  gemtekDevCpeMaxTxPowerRfMode  1  }
	
	gemtekDevCpeRfModeQPSK	OBJECT-TYPE
		SYNTAX			Unsigned32 
		MAX-ACCESS		read-write
		STATUS			obsolete
		DESCRIPTION		"The variable is deprecated.
						RF Mode QPSK Setting(0~2750)"
		::=  {  gemtekDevCpeMaxTxPowerRfMode  2  }
	
	gemtekDevCpeRfModeQAM16	OBJECT-TYPE
		SYNTAX			Unsigned32 
		MAX-ACCESS		read-write
		STATUS			obsolete
		DESCRIPTION		"The variable is deprecated.
						RF Mode QAM16 Setting(0~2750)"
		::=  {  gemtekDevCpeMaxTxPowerRfMode  3  }
	
	gemtekDevCpeRfModeQAM64	OBJECT-TYPE
		SYNTAX			Unsigned32 
		MAX-ACCESS		read-write
		STATUS			obsolete
		DESCRIPTION		"The variable is deprecated.
						RF Mode QAM64 Setting(0~2450)"
		::=  {  gemtekDevCpeMaxTxPowerRfMode  4  }
	
	gemtekDevCpeEirpModeAntennaGain	OBJECT-TYPE
		SYNTAX			Unsigned32 
		MAX-ACCESS		read-write
		STATUS			obsolete
		DESCRIPTION		"The variable is deprecated.
						EIRP Mode Antenna Gain(0~2450)"
		::=  {  gemtekDevCpeMaxTxPowerEirpMode  1  }
	
	gemtekDevCpeEirpModeBPSK	OBJECT-TYPE
		SYNTAX			Unsigned32 
		MAX-ACCESS		read-write
		STATUS			obsolete
		DESCRIPTION		"The variable is deprecated.
						EIRP Mode BPSK Setting(0~2750)"
		::=  {  gemtekDevCpeMaxTxPowerEirpMode  2  }
	
	gemtekDevCpeEirpModeQPSK	OBJECT-TYPE
		SYNTAX			Unsigned32 
		MAX-ACCESS		read-write
		STATUS			obsolete
		DESCRIPTION		"The variable is deprecated.
						EIRP Mode QPSK Setting(0~2750)"
		::=  {  gemtekDevCpeMaxTxPowerEirpMode  3  }
	
	gemtekDevCpeEirpModeQAM16	OBJECT-TYPE
		SYNTAX			Unsigned32 
		MAX-ACCESS		read-write
		STATUS			obsolete
		DESCRIPTION		"The variable is deprecated.
						EIRP Mode QAM16 Setting(0~2750)"
		::=  {  gemtekDevCpeMaxTxPowerEirpMode  4  }
	
	gemtekDevCpeEirpModeQAM64	OBJECT-TYPE
		SYNTAX			Unsigned32 
		MAX-ACCESS		read-write
		STATUS			obsolete
		DESCRIPTION		"The variable is deprecated.
						EIRP Mode QAM64 Setting(0~2450)"
		::=  {  gemtekDevCpeMaxTxPowerEirpMode  5  }
END
