--
-- she-ptp-mib.mib
-- MIB generated by MG-SOFT Visual MIB Builder Version 6.0  Build 88
-- Thursday, June 25, 2009 at 16:45:51
--

-- Start of ClearCase branch-information of current release:
-- she-ptp-mib.mib   /main/she_r3.5_grf/7
-- End of ClearCase branch-information.

	SHE-PTP-MIB DEFINITIONS ::= BEGIN
 
		IMPORTS
			she			
				FROM AN-MIB			
			sheAlarmTimeAndDate, sheAlarmReportingSource, sheAlarmReportingSourceType, sheAlarmSeverity, SheAlarmSevProfileIndex			
				FROM SHE-ALARMING-MIB			
			SheControlStatusType			
				FROM SHE-TC-MIB			
			SnmpAdminString			
				FROM SNMP-FRAMEWORK-MIB			
			OBJECT-GROUP, MODULE-COMPLIANCE, NOTIFICATION-GROUP			
				FROM SNMPv2-CONF			
			Integer32, Unsigned32, Gauge32, OBJECT-TYPE, MODULE-IDENTITY, 
			NOTIFICATION-TYPE			
				FROM SNMPv2-SMI			
			TruthValue, TEXTUAL-CONVENTION			
				FROM SNMPv2-TC;
	
	
		shePtpMIB MODULE-IDENTITY 
			LAST-UPDATED "200906251300Z"		-- June 25, 2009 at 13:00 GMT
			ORGANIZATION 
				"Nokia Siemens Networks"
			CONTACT-INFO 
				"Gerd Barchmann
				COO BCS BBA RD SDE HW1
				
				gerd.barchmann@nsn.com
				+49 3834 555654
				
				sylwester.nawrocki@tieto.com"
			DESCRIPTION 
				"This MIB based on ptp-Mib proposal from IEEE1588 workin group.
				
				Management Information Base module for PTP configuration,
				default dataset, current dataset, parent dataset, global time proporties
				dataset, foreign dataset and port configuration dataset components.
				
				New supported with R3.7M.
				
				"
			REVISION "200812101554Z"		-- December 10, 2008 at 15:54 GMT
			DESCRIPTION 
				"Initial version for SHE R3.7M."
			REVISION "200901291126Z"		-- January 29, 2009 at 11:26 GMT
			DESCRIPTION 
				"Modifications after review."
			REVISION "200903251313Z"		-- March 25, 2009 at 13:13 GMT
			DESCRIPTION 
				"Update descriptions and remove not needed parameters from port-table.
				Add new alarm trap if IpHostInterface config is missing or invalid."
			REVISION "200905081005Z"		-- May 08, 2009 at 10:05 GMT
			DESCRIPTION 
				"Update parameter syntax and descriptions after review.
				Add alarmSeverity configuration to portDs."
			REVISION "200906040848Z"		-- June 04, 2009 at 08:48 GMT
			DESCRIPTION 
				"Correct descriptions for shePtpForeignMasterDSNumberForeignRecords
				and shePtpForeignMasterDSAnnounceMessages."
			REVISION "200906251644Z"		-- June 25, 2009 at 16:44 GMT
			DESCRIPTION 
				"Correct syntax for parameter shePtpClockType."
			::= { she 22 }

		
	
--
-- Type definitions
--
	
		ShePtpControlRequestType ::= INTEGER
			{
			noRequest(1),
			setPtpDefaultDataSet(10),
			setPtpPortConfigDataSet(11),
			createPtpAcceptableMasterTableEntry(12),
			modifyPtpAcceptableMasterTableEntry(13),
			deletePtpAcceptableMasterTableEntry(14),
			createPtpUnicastDiscoveryMasterTableEntry(15),
			modifyPtpUnicastDiscoveryMasterTableEntry(16),
			deletePtpUnicastDiscoveryMasterTableEntry(17)
			}

--  info - IMPL: detailed Results R2.8 ->
		ShePtpControlRequestResultType ::= INTEGER
			{
			noRequest(1),
			comExecStarted(30),
			paramFaulty(31),
			requestBusy(32),
			setDataFailed(34),
			aswTimeout(35),
			commandFailed(36),
			commandSucceeded(37)
			}

	
--
-- Textual conventions
--
	
		ShePtpEnableType ::= TEXTUAL-CONVENTION
			STATUS current
			DESCRIPTION 
				"Used for show adminState of PTP subsystem in NE."
			SYNTAX INTEGER
				{
				enabled(1),
				disabled(2)
				}

		ShePtpPortDSDelayMechanismType ::= TEXTUAL-CONVENTION
			STATUS current
			DESCRIPTION 
				"Description."
			SYNTAX INTEGER { end2End(1) }

		ShePtpAcceptableMasterNetworkProtocolType ::= TEXTUAL-CONVENTION
			STATUS current
			DESCRIPTION 
				"Description."
			SYNTAX INTEGER { ipUdp(1) }

		ShePtpUnicastDiscoveryMasterIndexType ::= TEXTUAL-CONVENTION
			STATUS current
			DESCRIPTION 
				"Description."
			SYNTAX Unsigned32 (1..10)

		ShePtpUnicastDiscoveryMasterRateType ::= TEXTUAL-CONVENTION
			STATUS current
			DESCRIPTION 
				"Description."
			SYNTAX INTEGER
				{
				use128msgs(-7),
				use64msgs(-6),
				use32msgs(-5),
				use16msgs(-4),
				use8msgs(-3),
				use4msgs(-2),
				use2msgs(-1),
				use1msgs(0)
				}

		ShePtpAcceptableMasterSyncStateType ::= TEXTUAL-CONVENTION
			STATUS current
			DESCRIPTION 
				"used to show the status of configured acceptable master clocks."
			SYNTAX INTEGER
				{
				freerun(1),
				holdover(2),
				acquiring(3),
				acquired(4)
				}

		ShePtpPortDSIntervalType ::= TEXTUAL-CONVENTION
			STATUS current
			DESCRIPTION 
				"Used to configure SyncInterval and ReqInterval in portDS."
			SYNTAX Integer32 (-7..1)

	
--
-- Node definitions
--
	
		shePtpObjects OBJECT IDENTIFIER ::= { shePtpMIB 1 }

		
-- ***********************************************************
-- 
--                  P T P    C O N F I G 
-- 
-- *********************************************************** 
		shePtpBase OBJECT IDENTIFIER ::= { shePtpObjects 1 }

		
		shePtpAdminState OBJECT-TYPE
			SYNTAX ShePtpEnableType
			MAX-ACCESS read-only
			STATUS current
			DESCRIPTION
				"Enable or disable the Precision Time Protocol on this node.
				The default value is disabled.
				
				Note: SHE system will enable/disable the PTP subsystem via a configuration command
				in sheSyncMib. This will force an switchover between the system default sync module, which
				could use T3 or BITS or syncEthernet as sync sources configured and controled via sheSyncMib,
				and the PTP sync module configured and controled via this shePtpMib module.
				
				A modification will only be supported if CXU_B3 is used! All other CXU versions are not able to 
				support timing over packet feature!"
			REFERENCE
				"tbd."
			DEFVAL { disabled }
			::= { shePtpBase 1 }

		
		shePtpManufacturerIdentity OBJECT-TYPE
			SYNTAX SnmpAdminString
			MAX-ACCESS read-only
			STATUS current
			DESCRIPTION
				"The value of manufacturerIdentity shall be an OUI owned by the manufacturer of the node. "
			::= { shePtpBase 2 }

		
		shePtpRevisionData OBJECT-TYPE
			SYNTAX SnmpAdminString
			MAX-ACCESS read-only
			STATUS current
			DESCRIPTION
				"Indication of the revisions for node hardware (HW), firmware (FW), and software (SW).
				This information shall be semicolon (;) separated (HW;FW;SW). "
			::= { shePtpBase 3 }

		
		shePtpClockType OBJECT-TYPE
			SYNTAX OCTET STRING (SIZE (2))
			MAX-ACCESS read-only
			STATUS current
			DESCRIPTION
				"ClockType as defined in the CLOCK_DESCRIPTION management message.
				
				Indication of the PTP node type. A TRUE value of a bit in the clockType field indicates 
				that the description applies to the node. 
				
				0 - ordinary clock 
				1 - boundary clock 
				2 - peer-to-peer transparent clock 
				3 - end-to-end transparent clock 
				4 - management node 
				5..0xF - Reserved "
			::= { shePtpBase 4 }

		
		shePtpVersion OBJECT-TYPE
			SYNTAX Unsigned32
			MAX-ACCESS read-only
			STATUS current
			DESCRIPTION
				"Version number of supported IEEE1588 release."
			DEFVAL { 2 }
			::= { shePtpBase 5 }

		
-- ***********************************************************
-- 
--           P T P    D E F A U L T    D A T A    S E T
-- 
-- *********************************************************** 
		shePtpDefaultDataSet OBJECT IDENTIFIER ::= { shePtpObjects 2 }

		
		shePtpDefaultDSInitializable OBJECT-TYPE
			SYNTAX TruthValue
			MAX-ACCESS read-only
			STATUS current
			DESCRIPTION
				"The clock can be reinitialized by a management message."
			DEFVAL { true }
			::= { shePtpDefaultDataSet 1 }

		
		shePtpDefaultDSTwoStepFlag OBJECT-TYPE
			SYNTAX TruthValue
			MAX-ACCESS read-only
			STATUS current
			DESCRIPTION
				"Use Follow Up messages or not.
				Using Follow Up will increase PTP packet rate (2x Sync rate) and CPU load!"
			::= { shePtpDefaultDataSet 2 }

		
		shePtpDefaultDSIdentity OBJECT-TYPE
			SYNTAX OCTET STRING (SIZE (0..8))
			MAX-ACCESS read-only
			STATUS current
			DESCRIPTION
				"The clockIdentity is an 8 octet (byte) array. The value range of  each octet  is 0..0xFF.
				"
			REFERENCE
				"(see page 52 IEEE1588 PTPv2 standard)"
			::= { shePtpDefaultDataSet 3 }

		
		shePtpDefaultDSNumberPorts OBJECT-TYPE
			SYNTAX Unsigned32 (1)
			MAX-ACCESS read-only
			STATUS current
			DESCRIPTION
				"Number of available PTP port's in the system."
			::= { shePtpDefaultDataSet 4 }

		
		shePtpDefaultDSClass OBJECT-TYPE
			SYNTAX Integer32 (0..255)
			MAX-ACCESS read-only
			STATUS current
			DESCRIPTION
				"clockClass attribute of this ordinary slave-only clock. 
				Default value is 255."
			::= { shePtpDefaultDataSet 5 }

		
		shePtpDefaultDSAccuracy OBJECT-TYPE
			SYNTAX Integer32 (0..255)
			MAX-ACCESS read-only
			STATUS current
			DESCRIPTION
				"Part of default dataset clockQuality struct. Characterizes a clock for the purpose
				of the best master clock (BMC) algorithm. This is an enum value as defined in clause
				7.6.2.5, table 6 of IEEE1588-2008 standard. clockAccuracy is related to the time source
				and holdover specifications of this clock"
			::= { shePtpDefaultDataSet 6 }

		
		shePtpDefaultDSVariance OBJECT-TYPE
			SYNTAX Integer32 (0..65535)
			MAX-ACCESS read-only
			STATUS current
			DESCRIPTION
				"offsetScaledLogVariance defaultDS member, it is an attribute defining the stability 
				of a clock. This is the precision of the timestamps included in messages issued by the clock
				when it is not synchronized to another clock using the protocol. The representation is 
				described in clause 7.6.3.3 of IEEE1588-2008 standard."
			::= { shePtpDefaultDataSet 7 }

		
		shePtpDefaultDSPriority1 OBJECT-TYPE
			SYNTAX INTEGER (0..255)
			MAX-ACCESS read-only
			STATUS current
			DESCRIPTION
				"priority1 attribute of this PTP clock.
				This attribute is used in the execution of the best master clock algorithm, if BMC is used.
				However in this PTP slave clock implementation SLAVE_ONLY mode is used and priority1 is 
				meaningless in respect of BMC."
			::= { shePtpDefaultDataSet 8 }

		
		shePtpDefaultDSPriority2 OBJECT-TYPE
			SYNTAX Integer32 (0..255)
			MAX-ACCESS read-only
			STATUS current
			DESCRIPTION
				"priority2 attribute of this PTP clock.
				This attribute is used in the execution of the best master clock algorithm, if BMC is used.
				However in this PTP slave clock implementation SLAVE_ONLY mode is used and priority2 is 
				meaningless in respect of BMC."
			::= { shePtpDefaultDataSet 9 }

		
		shePtpDefaultDSDomainNumber OBJECT-TYPE
			SYNTAX Integer32 (0..255)
			MAX-ACCESS read-only
			STATUS current
			DESCRIPTION
				"A domain number specifying the scope of PTP message communication, state, operations, data sets and timescale.
				0 - default 
				1 - alternate domain 1 
				2 - alternate domain 2 
				3 - alternate domain 3 
				4..127 - user-defined 
				128..255 - reserved"
			::= { shePtpDefaultDataSet 10 }

		
		shePtpDefaultDSSlaveOnly OBJECT-TYPE
			SYNTAX TruthValue
			MAX-ACCESS read-only
			STATUS current
			DESCRIPTION
				"Set to TRUE during initialization and not allowed to be changed as this is a slave-only clock."
			DEFVAL { true }
			::= { shePtpDefaultDataSet 11 }

		
		shePtpDefaultDataSetControl OBJECT IDENTIFIER ::= { shePtpObjects 3 }

		
		shePtpDefaultDSControlRequest OBJECT-TYPE
			SYNTAX ShePtpControlRequestType
			MAX-ACCESS read-write
			STATUS current
			DESCRIPTION
				"setPtpDefaultDataSet (10):
				shePtpDefaultDSControlInitializable
				shePtpDefaultDSControlTwoStepFlag
				shePtpDefaultDSControlIdentity
				shePtpDefaultDSControlPriority1
				shePtpDefaultDSControlPriority2
				shePtpDefaultDSControlDomainNumber"
			::= { shePtpDefaultDataSetControl 1 }

		
		shePtpDefaultDSControlStatus OBJECT-TYPE
			SYNTAX SheControlStatusType
			MAX-ACCESS read-only
			STATUS current
			DESCRIPTION
				"The status of a user command. 
				"
			::= { shePtpDefaultDataSetControl 2 }

		
		shePtpDefaultDSControlTimer OBJECT-TYPE
			SYNTAX Gauge32
			MAX-ACCESS read-only
			STATUS current
			DESCRIPTION
				"The maximum wait time for the manager for a long running user command. 
				"
			::= { shePtpDefaultDataSetControl 3 }

		
		shePtpDefaultDSControlReqResult OBJECT-TYPE
			SYNTAX ShePtpControlRequestResultType
			MAX-ACCESS read-only
			STATUS current
			DESCRIPTION
				"The result of the last user command."
			::= { shePtpDefaultDataSetControl 4 }

		
		shePtpDefaultDSControlTimeStamp OBJECT-TYPE
			SYNTAX Unsigned32
			UNITS "sec"
			MAX-ACCESS read-only
			STATUS current
			DESCRIPTION
				"The time stamp of the last command (end of command)."
			::= { shePtpDefaultDataSetControl 5 }

		
		shePtpDefaultDSControlInitializable OBJECT-TYPE
			SYNTAX TruthValue
			MAX-ACCESS read-write
			STATUS current
			DESCRIPTION
				"look at group."
			::= { shePtpDefaultDataSetControl 6 }

		
		shePtpDefaultDSControlTwoStepFlag OBJECT-TYPE
			SYNTAX TruthValue
			MAX-ACCESS read-write
			STATUS current
			DESCRIPTION
				"look at group."
			::= { shePtpDefaultDataSetControl 7 }

		
		shePtpDefaultDSControlIdentity OBJECT-TYPE
			SYNTAX OCTET STRING (SIZE (0..8))
			MAX-ACCESS read-write
			STATUS current
			DESCRIPTION
				"look at group."
			::= { shePtpDefaultDataSetControl 8 }

		
		shePtpDefaultDSControlPriority1 OBJECT-TYPE
			SYNTAX Integer32 (0..255)
			MAX-ACCESS read-write
			STATUS current
			DESCRIPTION
				"look at group."
			::= { shePtpDefaultDataSetControl 9 }

		
		shePtpDefaultDSControlPriority2 OBJECT-TYPE
			SYNTAX Integer32 (0..255)
			MAX-ACCESS read-write
			STATUS current
			DESCRIPTION
				"look at group."
			::= { shePtpDefaultDataSetControl 10 }

		
		shePtpDefaultDSControlDomainNumber OBJECT-TYPE
			SYNTAX Integer32 (0..127)
			MAX-ACCESS read-write
			STATUS current
			DESCRIPTION
				"look at group.
				
				Range 128...255 is reserved."
			::= { shePtpDefaultDataSetControl 11 }

		
-- ***********************************************************
-- 
--           P T P   Current    D A T A    S E T
-- 
-- ***********************************************************
		shePtpCurrentDataSet OBJECT IDENTIFIER ::= { shePtpObjects 4 }

		
		shePtpCurrentDataSetStepsRemoved OBJECT-TYPE
			SYNTAX Integer32
			MAX-ACCESS read-only
			STATUS current
			DESCRIPTION
				"The number of communication paths traversed between the local clock and
				the grandmaster clock."
			::= { shePtpCurrentDataSet 1 }

		
		shePtpCurrentDataSetOffsettFromMasterSeconds OBJECT-TYPE
			SYNTAX Integer32
			MAX-ACCESS read-only
			STATUS current
			DESCRIPTION
				"Implementation-specific current value of the time difference between a master and a slave 
				as computed by the slave in seconds."
			::= { shePtpCurrentDataSet 2 }

		
		shePtpCurrentDataSetOffsettFromMasterNanoSeconds OBJECT-TYPE
			SYNTAX Integer32 (0..999999999)
			MAX-ACCESS read-only
			STATUS current
			DESCRIPTION
				"Implementation-specific current value of the time difference between a master and a slave 
				as computed by the slave in nano-seconds."
			::= { shePtpCurrentDataSet 3 }

		
		shePtpCurrentDataSetMeanPathDelaySeconds OBJECT-TYPE
			SYNTAX Integer32
			MAX-ACCESS read-only
			STATUS current
			DESCRIPTION
				"Implementation-specific current value of the mean propagation time between a master and 
				slave clock as computed by the slave in seconds. "
			::= { shePtpCurrentDataSet 4 }

		
		shePtpCurrentDataSetMeanPathDelayNanoSeconds OBJECT-TYPE
			SYNTAX Integer32 (0..999999999)
			MAX-ACCESS read-only
			STATUS current
			DESCRIPTION
				"Implementation-specific current value of the mean propagation time between a master and 
				slave clock as computed by the slave in nano-seconds. "
			::= { shePtpCurrentDataSet 5 }

		
-- ***********************************************************
-- 
--           P T P   P A R E N T    D A T A    S E T
-- 
-- ***********************************************************
		shePtpParentDataSet OBJECT IDENTIFIER ::= { shePtpObjects 5 }

		
		shePtpParentClockIdentity OBJECT-TYPE
			SYNTAX OCTET STRING (SIZE (0..8))
			MAX-ACCESS read-only
			STATUS current
			DESCRIPTION
				"Identifies parent clock this slave clock is synchronized to.
				The clockIdentity is an 8 octet (byte) array. The value range of  each octet  is 0..0xFF."
			REFERENCE
				"(page 52 in IEEE1588 PTPv2 standard)"
			::= { shePtpParentDataSet 1 }

		
		shePtpParentClockPortNumber OBJECT-TYPE
			SYNTAX Integer32
			MAX-ACCESS read-only
			STATUS current
			DESCRIPTION
				"Port number of master clock to which this clock synchronizes."
			::= { shePtpParentDataSet 2 }

		
		shePtpParentGrandmasterIdentity OBJECT-TYPE
			SYNTAX OCTET STRING (SIZE (0..8))
			MAX-ACCESS read-only
			STATUS current
			DESCRIPTION
				"ClockIdentity attribute of the grandmaster clock."
			::= { shePtpParentDataSet 3 }

		
		shePtpParentGrandmasterClockClass OBJECT-TYPE
			SYNTAX Integer32 (0..255)
			MAX-ACCESS read-only
			STATUS current
			DESCRIPTION
				"Part of grandmaster clock quality struct."
			::= { shePtpParentDataSet 4 }

		
		shePtpParentGrandmasterClockAccuracy OBJECT-TYPE
			SYNTAX Integer32 (0..255)
			MAX-ACCESS read-only
			STATUS current
			DESCRIPTION
				"Part of grandmaster clock quality struct."
			::= { shePtpParentDataSet 5 }

		
		shePtpParentGrandmasterClockVariance OBJECT-TYPE
			SYNTAX Integer32 (0..65535)
			MAX-ACCESS read-only
			STATUS current
			DESCRIPTION
				"Part of grandmaster clock quality struct."
			::= { shePtpParentDataSet 6 }

		
		shePtpParentGrandmasterPriority1 OBJECT-TYPE
			SYNTAX Integer32 (0..255)
			MAX-ACCESS read-only
			STATUS current
			DESCRIPTION
				"Priority1 attribute of the grandmaster clock. "
			::= { shePtpParentDataSet 7 }

		
		shePtpParentGrandmasterPriority2 OBJECT-TYPE
			SYNTAX Integer32 (0..255)
			MAX-ACCESS read-only
			STATUS current
			DESCRIPTION
				"Priority2 attribute of the grandmaster clock. "
			::= { shePtpParentDataSet 8 }

		
-- shePtpPortConfigDataSetTable: PTP configuration/info on a per port basis
-- 
		shePtpPortDataSetTable OBJECT-TYPE
			SYNTAX SEQUENCE OF ShePtpPortDataSetEntry
			MAX-ACCESS not-accessible
			STATUS current
			DESCRIPTION
				"The table containing Port Data Set entries for each port of this clock.
				For the single port of this clock, ShePtpPortDataSetEntry is maintained as the
				basis for protocol decisions and providing values for message fields.
				The number of the table entries is the value of shePtpDefaultDSNumberPorts."
			::= { shePtpObjects 6 }

		
		shePtpPortDataSetEntry OBJECT-TYPE
			SYNTAX ShePtpPortDataSetEntry
			MAX-ACCESS not-accessible
			STATUS current
			DESCRIPTION
				"PTP configuration information for a particular port.
				"
			INDEX { shePtpPortDSPortNumber }
			::= { shePtpPortDataSetTable 1 }

		
		ShePtpPortDataSetEntry ::=
			SEQUENCE { 
				shePtpPortDSPortNumber
					Integer32,
				shePtpPortDSClockIdentity
					OCTET STRING,
				shePtpPortDSDelayMechanism
					ShePtpPortDSDelayMechanismType,
				shePtpPortDSAcceptableMasterEnabled
					TruthValue,
				shePtpPortDSUnicastNegotiationEnabled
					TruthValue,
				shePtpPortDSUnicastNegotiationDuration
					Integer32,
				shePtpPortDSUnicastLogQueryInterval
					Integer32,
				shePtpPortDSVlanId
					Integer32,
				shePtpPortDSLogMeanSyncInterval
					ShePtpPortDSIntervalType,
				shePtpPortDSLogMinMeanDelayReqInterval
					ShePtpPortDSIntervalType,
				shePtpPortDSLogMeanAnnounceInterval
					Integer32,
				shePtpPortDSAnnounceReceiptTimeout
					Integer32,
				shePtpPortDSLogMinPdelayReqInterval
					Integer32,
				shePtpPortDSAlarmSeverityIndex
					SheAlarmSevProfileIndex
			 }

		shePtpPortDSPortNumber OBJECT-TYPE
			SYNTAX Integer32 (1)
			MAX-ACCESS read-only
			STATUS current
			DESCRIPTION
				"The value of the portNumber for a port on a PTP node supporting a single PTP port shall be 1.
				The values of the port numbers for the N ports on a PTP node supporting N PTP ports shall be 1, 2, ..N, respectively"
			::= { shePtpPortDataSetEntry 1 }

		
		shePtpPortDSClockIdentity OBJECT-TYPE
			SYNTAX OCTET STRING (SIZE (0..8))
			MAX-ACCESS read-only
			STATUS current
			DESCRIPTION
				"PortIdentity attribute of the local port."
			::= { shePtpPortDataSetEntry 2 }

		
		shePtpPortDSDelayMechanism OBJECT-TYPE
			SYNTAX ShePtpPortDSDelayMechanismType
			MAX-ACCESS read-only
			STATUS current
			DESCRIPTION
				"Indication of the propagation delay measuring option used by the port in computing shePtpCurrentDataSetMeanPathDelay*.
				Possible values:
				 E2E (0x01) - The port is configured to use the delay request-response mechanism;
				 P2P (0x02) - The port is configured to use the peer delay mechanism;
				 DISABLED (0xFE) - The port does not implement the delay mechanism."
			DEFVAL { end2End }
			::= { shePtpPortDataSetEntry 3 }

		
		shePtpPortDSAcceptableMasterEnabled OBJECT-TYPE
			SYNTAX TruthValue
			MAX-ACCESS read-only
			STATUS current
			DESCRIPTION
				"Enable/Disable the usage of acceptableMasterTable. The Acceptable Master Table is always used 
				and this attribute value is always TRUE."
			DEFVAL { true }
			::= { shePtpPortDataSetEntry 4 }

		
		shePtpPortDSUnicastNegotiationEnabled OBJECT-TYPE
			SYNTAX TruthValue
			MAX-ACCESS read-only
			STATUS current
			DESCRIPTION
				"This atrribute determines if the message negotiation is used (TRUE) or not (FALSE)
				in case unicast communications is used, for any master clock entered in the acceptableMasterTable.
				This is a global flag to enable/disable unicast negotiation. This flag must be set to true
				and an entry added to the acceptableMasterTable and the discoveryMasterTable for autonegotiation
				to be started with given master clock."
			::= { shePtpPortDataSetEntry 5 }

		
		shePtpPortDSUnicastNegotiationDuration OBJECT-TYPE
			SYNTAX Integer32 (10..1000)
			UNITS "sec"
			MAX-ACCESS read-only
			STATUS current
			DESCRIPTION
				"The duration in seconds for which to request unicast contracts. Only relevant 
				for negotiated unicast streams, i.e. to the master clocks which port addresses are
				present in the shePtpUnicastDiscoveryMasterTable."
			DEFVAL { 300 }
			::= { shePtpPortDataSetEntry 6 }

		
		shePtpPortDSUnicastLogQueryInterval OBJECT-TYPE
			SYNTAX Integer32 (2..4)
			MAX-ACCESS read-only
			STATUS current
			DESCRIPTION
				"The log to the base 2 value of the request rate (per second) when trying to establish
				a unicast contract with a remote master device (when it does not respond immediately)."
			::= { shePtpPortDataSetEntry 7 }

		
		shePtpPortDSVlanId OBJECT-TYPE
			SYNTAX Integer32 (1..4093)
			MAX-ACCESS read-only
			STATUS current
			DESCRIPTION
				"ID of VLAN used for PTP traffic. 
				
				This configuration is only a reference to used VLAN - no explicite Vlan create configuration in the NE 
				will be forced by this setting.
				The interface configuration including IpAddress, SubnetMask and Vlan has to be made via general
				sheSystemIpHostTable configuration.  "
			::= { shePtpPortDataSetEntry 8 }

		
		shePtpPortDSLogMeanSyncInterval OBJECT-TYPE
			SYNTAX ShePtpPortDSIntervalType
			MAX-ACCESS read-only
			STATUS current
			DESCRIPTION
				"The interval to use for multicast sync messages on this port. 
				This is log2(1/Sync packet rate) PTP version 2."
			DEFVAL { 0 }
			::= { shePtpPortDataSetEntry 9 }

		
		shePtpPortDSLogMinMeanDelayReqInterval OBJECT-TYPE
			SYNTAX ShePtpPortDSIntervalType
			MAX-ACCESS read-only
			STATUS current
			DESCRIPTION
				"In PTP v2 for a slave device this is the preferred interval to be used for transmitting
				delay request messages but is subject to any minimum specified by the master.
				
				Logarithm to the base 2 of the minDelayReqInterval. "
			DEFVAL { 0 }
			::= { shePtpPortDataSetEntry 10 }

		
		shePtpPortDSLogMeanAnnounceInterval OBJECT-TYPE
			SYNTAX Integer32 (0..4)
			MAX-ACCESS read-only
			STATUS current
			DESCRIPTION
				"The interval to use for multicast announce messages on this port. 
				This is log to the base 2 of the Announce message rate (per second)."
			DEFVAL { 1 }
			::= { shePtpPortDataSetEntry 11 }

		
		shePtpPortDSAnnounceReceiptTimeout OBJECT-TYPE
			SYNTAX Integer32 (2..10)
			MAX-ACCESS read-only
			STATUS current
			DESCRIPTION
				"The timeout period, in announce message intervals, within which at least one 
				announce message must be received."
			DEFVAL { 3 }
			::= { shePtpPortDataSetEntry 12 }

		
		shePtpPortDSLogMinPdelayReqInterval OBJECT-TYPE
			SYNTAX Integer32 (0..5)
			MAX-ACCESS read-only
			STATUS current
			DESCRIPTION
				"The minimum permitted mean time interval between successive Pdelay_Req messages. 
				By default this attribute is initialized to the value of shePtpPortDSLogMeanSyncInterval.				
				This is log to the base 2 of the Pdelay_req message rate (per second)."
			::= { shePtpPortDataSetEntry 13 }

		
		shePtpPortDSAlarmSeverityIndex OBJECT-TYPE
			SYNTAX SheAlarmSevProfileIndex
			MAX-ACCESS read-only
			STATUS current
			DESCRIPTION
				"This index selects an item in the sheAlarmSeverityProfileTable. It is
				used to assign the reported alarm to a severity."
			DEFVAL { 1 }
			::= { shePtpPortDataSetEntry 14 }

		
		shePtpPortDataSetControl OBJECT IDENTIFIER ::= { shePtpObjects 7 }

		
		shePtpPortDataSetControlRequest OBJECT-TYPE
			SYNTAX ShePtpControlRequestType
			MAX-ACCESS read-write
			STATUS current
			DESCRIPTION
				"setPtpPortConfigDataSet (11):
				shePtpPortDataSetControlIndex
				shePtpPortDataSetControlUnicastNegotiationEnabled
				shePtpPortDataSetControlUnicastNegotiationDuration
				shePtpPortDataSetControlUnicastLogQueryInterval
				shePtpPortDataSetControlVlanId
				shePtpPortDataSetControlLogMeanSyncInterval
				shePtpPortDataSetControlLogMinMeanDelayReqInterval
				shePtpPortDataSetControlLogMeanAnnounceInterval
				shePtpPortDataSetControlAnnounceReceiptTimeout
				shePtpPortDataSetControlLogMinPdelayReqInterval
				shePtpPortDataSetControlAlarmSeverityIndex"
			::= { shePtpPortDataSetControl 1 }

		
		shePtpPortDataSetControlStatus OBJECT-TYPE
			SYNTAX SheControlStatusType
			MAX-ACCESS read-only
			STATUS current
			DESCRIPTION
				"The status of a user command. 
				"
			::= { shePtpPortDataSetControl 2 }

		
		shePtpPortDataSetControlTimer OBJECT-TYPE
			SYNTAX Gauge32
			MAX-ACCESS read-only
			STATUS current
			DESCRIPTION
				"The maximum wait time for the manager for a long running user command. 
				"
			::= { shePtpPortDataSetControl 3 }

		
		shePtpPortDataSetControlControlReqResult OBJECT-TYPE
			SYNTAX ShePtpControlRequestResultType
			MAX-ACCESS read-only
			STATUS current
			DESCRIPTION
				"The result of the last user command."
			::= { shePtpPortDataSetControl 4 }

		
		shePtpPortDataSetControlTimeStamp OBJECT-TYPE
			SYNTAX Unsigned32
			UNITS "sec"
			MAX-ACCESS read-only
			STATUS current
			DESCRIPTION
				"The time stamp of the last command (end of command)."
			::= { shePtpPortDataSetControl 5 }

		
		shePtpPortDataSetControlIndex OBJECT-TYPE
			SYNTAX Integer32 (1)
			MAX-ACCESS read-write
			STATUS current
			DESCRIPTION
				"The index of port DS for configuration."
			::= { shePtpPortDataSetControl 6 }

		
		shePtpPortDataSetControlUnicastNegotiationEnabled OBJECT-TYPE
			SYNTAX TruthValue
			MAX-ACCESS read-write
			STATUS current
			DESCRIPTION
				"look at table."
			::= { shePtpPortDataSetControl 7 }

		
		shePtpPortDataSetControlUnicastNegotiationDuration OBJECT-TYPE
			SYNTAX Integer32 (10..1000)
			UNITS "sec"
			MAX-ACCESS read-write
			STATUS current
			DESCRIPTION
				"look at table."
			::= { shePtpPortDataSetControl 8 }

		
		shePtpPortDataSetControlUnicastLogQueryInterval OBJECT-TYPE
			SYNTAX Integer32 (2..4)
			MAX-ACCESS read-write
			STATUS current
			DESCRIPTION
				"look at table."
			::= { shePtpPortDataSetControl 9 }

		
		shePtpPortDataSetControlVlanId OBJECT-TYPE
			SYNTAX Integer32 (1..4093)
			MAX-ACCESS read-write
			STATUS current
			DESCRIPTION
				"look at table."
			::= { shePtpPortDataSetControl 10 }

		
		shePtpPortDataSetControlLogMeanSyncInterval OBJECT-TYPE
			SYNTAX ShePtpPortDSIntervalType
			MAX-ACCESS read-write
			STATUS current
			DESCRIPTION
				"look at table."
			::= { shePtpPortDataSetControl 11 }

		
		shePtpPortDataSetControlLogMinMeanDelayReqInterval OBJECT-TYPE
			SYNTAX ShePtpPortDSIntervalType
			MAX-ACCESS read-write
			STATUS current
			DESCRIPTION
				"look at table."
			::= { shePtpPortDataSetControl 12 }

		
		shePtpPortDataSetControlLogMeanAnnounceInterval OBJECT-TYPE
			SYNTAX Integer32 (0..4)
			MAX-ACCESS read-write
			STATUS current
			DESCRIPTION
				"look at table."
			::= { shePtpPortDataSetControl 13 }

		
		shePtpPortDataSetControlAnnounceReceiptTimeout OBJECT-TYPE
			SYNTAX Integer32 (2..10)
			MAX-ACCESS read-write
			STATUS current
			DESCRIPTION
				"look at table."
			::= { shePtpPortDataSetControl 14 }

		
		shePtpPortDataSetControlLogMinPdelayReqInterval OBJECT-TYPE
			SYNTAX Integer32 (0..5)
			MAX-ACCESS read-write
			STATUS current
			DESCRIPTION
				"look at table."
			::= { shePtpPortDataSetControl 15 }

		
		shePtpPortDataSetControlAlarmSeverityIndex OBJECT-TYPE
			SYNTAX SheAlarmSevProfileIndex
			MAX-ACCESS read-write
			STATUS current
			DESCRIPTION
				"look at table"
			::= { shePtpPortDataSetControl 16 }

		
		shePtpForeignMasterDataSetTable OBJECT-TYPE
			SYNTAX SEQUENCE OF ShePtpForeignMasterDataSetEntry
			MAX-ACCESS not-accessible
			STATUS current
			DESCRIPTION
				"This table is maintained for the purpose of qualifying Announce messages,
				it is used by best master clock algorithm. 
				There will be an entry dynamically created in the table for each master clock from
				which Announce messages are received on corresponding (shePtpPortDSPortNumber)
				clock port."
			::= { shePtpObjects 8 }

		
		shePtpForeignMasterDataSetEntry OBJECT-TYPE
			SYNTAX ShePtpForeignMasterDataSetEntry
			MAX-ACCESS not-accessible
			STATUS current
			DESCRIPTION
				"PTP configuration information for a particular port.
				"
			INDEX { shePtpPortDSPortNumber, shePtpForeignMasterDSIndex }
			::= { shePtpForeignMasterDataSetTable 1 }

		
		ShePtpForeignMasterDataSetEntry ::=
			SEQUENCE { 
				shePtpForeignMasterDSIndex
					Unsigned32,
				shePtpForeignMasterDSNumberForeignRecords
					Integer32,
				shePtpForeignMasterDSClockIdentity
					OCTET STRING,
				shePtpForeignMasterDSPortNumber
					Integer32,
				shePtpForeignMasterDSAnnounceMessages
					Unsigned32,
				shePtpForeignMasterDSNetworkProtocol
					ShePtpAcceptableMasterNetworkProtocolType,
				shePtpForeignMasterDSProtocolAddressLength
					Integer32,
				shePtpForeignMasterDSProtocolAddress
					OCTET STRING
			 }

		shePtpForeignMasterDSIndex OBJECT-TYPE
			SYNTAX Unsigned32 (1..10)
			MAX-ACCESS read-only
			STATUS current
			DESCRIPTION
				"Second Index for table, Count of foreign master entries on a port.
				Foreign Master Data set shall have a minimum capacity of 5 foreign master records"
			::= { shePtpForeignMasterDataSetEntry 1 }

		
		shePtpForeignMasterDSNumberForeignRecords OBJECT-TYPE
			SYNTAX Integer32 (0..5)
			MAX-ACCESS read-only
			STATUS current
			DESCRIPTION
				"Count of foreign clock records on a port. This equals to the actual number of 
				foreign clocks from which Announce messages are received. 
				Table shall have a minimum capacity of 5 foreign master records."
			::= { shePtpForeignMasterDataSetEntry 2 }

		
		shePtpForeignMasterDSClockIdentity OBJECT-TYPE
			SYNTAX OCTET STRING (SIZE (0..8))
			MAX-ACCESS read-only
			STATUS current
			DESCRIPTION
				"Part of the sourcePortIdentity field value of an Announce message received from the 
				foreign master."
			::= { shePtpForeignMasterDataSetEntry 3 }

		
		shePtpForeignMasterDSPortNumber OBJECT-TYPE
			SYNTAX Integer32
			MAX-ACCESS read-only
			STATUS current
			DESCRIPTION
				"Part of the sourcePortIdentity field value of an Announce message received from the 
				foreign master."
			::= { shePtpForeignMasterDataSetEntry 4 }

		
		shePtpForeignMasterDSAnnounceMessages OBJECT-TYPE
			SYNTAX Unsigned32
			MAX-ACCESS read-only
			STATUS current
			DESCRIPTION
				"The number of Announce messages from the foreign master indicated by the 
				shePtpForeignMasterDSClockIdentity and shePtpForeignMasterDSPortNumber 
				(foreignMasterPortIdentity) that have been received within a time window of 
				duration 4 * shePtpPortDSLogMeanAnnounceInterval."
			::= { shePtpForeignMasterDataSetEntry 5 }

		
		shePtpForeignMasterDSNetworkProtocol OBJECT-TYPE
			SYNTAX ShePtpAcceptableMasterNetworkProtocolType
			MAX-ACCESS read-only
			STATUS current
			DESCRIPTION
				"Supported PTP transport protocol is only IP/UDP."
			DEFVAL { ipUdp }
			::= { shePtpForeignMasterDataSetEntry 6 }

		
		shePtpForeignMasterDSProtocolAddressLength OBJECT-TYPE
			SYNTAX Integer32 (4)
			MAX-ACCESS read-only
			STATUS current
			DESCRIPTION
				"Supported PTP transport protocol is only IP/UDP so address length is always 4."
			::= { shePtpForeignMasterDataSetEntry 7 }

		
		shePtpForeignMasterDSProtocolAddress OBJECT-TYPE
			SYNTAX OCTET STRING (SIZE (0..16))
			MAX-ACCESS read-only
			STATUS current
			DESCRIPTION
				"The IP address of the detected foreign master."
			::= { shePtpForeignMasterDataSetEntry 8 }

		
		shePtpAcceptableMasterTable OBJECT-TYPE
			SYNTAX SEQUENCE OF ShePtpAcceptableMasterEntry
			MAX-ACCESS not-accessible
			STATUS current
			DESCRIPTION
				"Configure acceptable master clocks entries."
			::= { shePtpObjects 9 }

		
		shePtpAcceptableMasterEntry OBJECT-TYPE
			SYNTAX ShePtpAcceptableMasterEntry
			MAX-ACCESS not-accessible
			STATUS current
			DESCRIPTION
				"An entry per each PTP server to which this slave clock is allowed to synchronize.
				All Announce and other PTP messages sent by master clock which is not in the 
				shePtpAcceptableMasterTable will be ignored, e.g. not considered 
				by Best Master Clock algorithm."
			INDEX { shePtpAcceptableMasterIndex }
			::= { shePtpAcceptableMasterTable 1 }

		
		ShePtpAcceptableMasterEntry ::=
			SEQUENCE { 
				shePtpAcceptableMasterIndex
					Unsigned32,
				shePtpAcceptableMasterNetworkProtocol
					ShePtpAcceptableMasterNetworkProtocolType,
				shePtpAcceptableMasterProtocolAddressLength
					Integer32,
				shePtpAcceptableMasterProtocolAddress
					OCTET STRING,
				shePtpAcceptableMasterPriority
					Integer32,
				shePtpAcceptableMasterUnicast
					TruthValue,
				shePtpAcceptableMasterMinTimingPktSize
					Integer32,
				shePtpAcceptableMasterSyncStatus
					ShePtpAcceptableMasterSyncStateType
			 }

		shePtpAcceptableMasterIndex OBJECT-TYPE
			SYNTAX Unsigned32 (1..10)
			MAX-ACCESS read-only
			STATUS current
			DESCRIPTION
				"Index for table, Count of configured acceptable master entries."
			::= { shePtpAcceptableMasterEntry 1 }

		
		shePtpAcceptableMasterNetworkProtocol OBJECT-TYPE
			SYNTAX ShePtpAcceptableMasterNetworkProtocolType
			MAX-ACCESS read-only
			STATUS current
			DESCRIPTION
				"Supported PTP transport protocol is only IP/UDP."
			DEFVAL { ipUdp }
			::= { shePtpAcceptableMasterEntry 2 }

		
		shePtpAcceptableMasterProtocolAddressLength OBJECT-TYPE
			SYNTAX Integer32 (4)
			MAX-ACCESS read-only
			STATUS current
			DESCRIPTION
				"Supported PTP transport protocol is only IP/UDP so address length is always 4."
			::= { shePtpAcceptableMasterEntry 3 }

		
		shePtpAcceptableMasterProtocolAddress OBJECT-TYPE
			SYNTAX OCTET STRING (SIZE (0..16))
			MAX-ACCESS read-only
			STATUS current
			DESCRIPTION
				"The IP address of the configured acceptable master."
			::= { shePtpAcceptableMasterEntry 4 }

		
		shePtpAcceptableMasterPriority OBJECT-TYPE
			SYNTAX Integer32 (0..255)
			MAX-ACCESS read-only
			STATUS current
			DESCRIPTION
				"This attribute is an alternate priority to be used to determine best master clock.
				If shePtpAcceptableMasterPriority is 0 it shall have no effect on computation determination
				of best master clock. If the value of shePtpAcceptableMasterPriority is greater than 0, 
				the value of priority1 in the Announce message from the remote port shall be replaced 
				by the value of the shePtpAcceptableMasterPriority for purposes of determining best master clock."
			::= { shePtpAcceptableMasterEntry 5 }

		
		shePtpAcceptableMasterUnicast OBJECT-TYPE
			SYNTAX TruthValue
			MAX-ACCESS read-only
			STATUS current
			DESCRIPTION
				"This attribute determines the communications type used for PTP messages (unicast/multicast).
				It depends on destination IP address type of the packets (master clock port address or IP 
				multicast domain). It is set to TRUE if unicast communication is used  or set to
				FALSE if multicast addresses are used (standard PTP assigned IP multicast addresses)."
			::= { shePtpAcceptableMasterEntry 6 }

		
		shePtpAcceptableMasterMinTimingPktSize OBJECT-TYPE
			SYNTAX Integer32 (0..255)
			MAX-ACCESS read-only
			STATUS current
			DESCRIPTION
				"The minimum packet size to use for packets carrying timing information. This is the total
				packet size after all protocol headers have been added, but excluding the Ethernet FCS. 
				The required packet size is achieved by adding padding bytes to the minimum timing packet
				size required by the PTP protocol.
				If the specified value is less than the minimum quired by the protocol it will be ignored.
				Hence specifying zero will always use the standard packet size - no padding will be added
				to the PTP messages.
				"
			::= { shePtpAcceptableMasterEntry 7 }

		
		shePtpAcceptableMasterSyncStatus OBJECT-TYPE
			SYNTAX ShePtpAcceptableMasterSyncStateType
			MAX-ACCESS read-only
			STATUS current
			DESCRIPTION
				"This parameter show the clock recovery algorithm status which is an enum of
				values { FREERUN, HOLDOVER, ACQUIRING, ACQUIRED }. For normal operation, i.e. when this
				slave clock is synchronized to any master clock that attribute will have 'ACQUIRED' value."
			::= { shePtpAcceptableMasterEntry 8 }

		
		shePtpAcceptableMasterControl OBJECT IDENTIFIER ::= { shePtpObjects 10 }

		
		shePtpAcceptableMasterControlRequest OBJECT-TYPE
			SYNTAX ShePtpControlRequestType
			MAX-ACCESS read-write
			STATUS current
			DESCRIPTION
				"createPtpAcceptableMasterTableEntry (12):
				shePtpAcceptableMasterControlProtocolAddress
				shePtpAcceptableMasterControlPriority
				shePtpAcceptableMasterControlUnicast
				shePtpAcceptableMasterControlMinTimingPktSize
				
				modifyPtpAcceptableMasterTableEntry (13):
				shePtpAcceptableMasterControlIndex
				shePtpAcceptableMasterControlProtocolAddress
				shePtpAcceptableMasterControlPriority
				shePtpAcceptableMasterControlUnicast
				shePtpAcceptableMasterControlMinTimingPktSize
				
				deletePtpAcceptableMasterTableEntry (14):
				shePtpAcceptableMasterControlIndex"
			::= { shePtpAcceptableMasterControl 1 }

		
		shePtpAcceptableMasterControlStatus OBJECT-TYPE
			SYNTAX SheControlStatusType
			MAX-ACCESS read-only
			STATUS current
			DESCRIPTION
				"The status of a user command. 
				"
			::= { shePtpAcceptableMasterControl 2 }

		
		shePtpAcceptableMasterControlTimer OBJECT-TYPE
			SYNTAX Gauge32
			MAX-ACCESS read-only
			STATUS current
			DESCRIPTION
				"The maximum wait time for the manager for a long running user command. 
				"
			::= { shePtpAcceptableMasterControl 3 }

		
		shePtpAcceptableMasterControlReqResult OBJECT-TYPE
			SYNTAX ShePtpControlRequestResultType
			MAX-ACCESS read-only
			STATUS current
			DESCRIPTION
				"The result of the last user command."
			::= { shePtpAcceptableMasterControl 4 }

		
		shePtpAcceptableMasterControlTimeStamp OBJECT-TYPE
			SYNTAX Unsigned32
			UNITS "sec"
			MAX-ACCESS read-only
			STATUS current
			DESCRIPTION
				"The time stamp of the last command (end of command)."
			::= { shePtpAcceptableMasterControl 5 }

		
		shePtpAcceptableMasterControlIndex OBJECT-TYPE
			SYNTAX Integer32 (1..10)
			MAX-ACCESS read-write
			STATUS current
			DESCRIPTION
				"The index of acceptable master table entry for configuration."
			::= { shePtpAcceptableMasterControl 6 }

		
		shePtpAcceptableMasterControlProtocolAddress OBJECT-TYPE
			SYNTAX OCTET STRING (SIZE (0..16))
			MAX-ACCESS read-write
			STATUS current
			DESCRIPTION
				"look at table."
			::= { shePtpAcceptableMasterControl 7 }

		
		shePtpAcceptableMasterControlPriority OBJECT-TYPE
			SYNTAX Integer32 (0..255)
			MAX-ACCESS read-write
			STATUS current
			DESCRIPTION
				"look at table."
			::= { shePtpAcceptableMasterControl 8 }

		
		shePtpAcceptableMasterControlUnicast OBJECT-TYPE
			SYNTAX TruthValue
			MAX-ACCESS read-write
			STATUS current
			DESCRIPTION
				"look at table."
			::= { shePtpAcceptableMasterControl 9 }

		
		shePtpAcceptableMasterControlMinTimingPktSize OBJECT-TYPE
			SYNTAX Integer32 (0..255)
			MAX-ACCESS read-write
			STATUS current
			DESCRIPTION
				"look at table."
			::= { shePtpAcceptableMasterControl 10 }

		
		shePtpUnicastDiscoveryMasterTable OBJECT-TYPE
			SYNTAX SEQUENCE OF ShePtpUnicastDiscoveryMasterEntry
			MAX-ACCESS not-accessible
			STATUS current
			DESCRIPTION
				"The table is used by this slave clock to start negotiation of message rates
				with required master clocks. It is only meaningful when unicast communications
				is used and  shePtpPortDSUnicastNegotiationEnabled attribute of corresponding
				clock port is set to TRUE."
			::= { shePtpObjects 11 }

		
		shePtpUnicastDiscoveryMasterEntry OBJECT-TYPE
			SYNTAX ShePtpUnicastDiscoveryMasterEntry
			MAX-ACCESS not-accessible
			STATUS current
			DESCRIPTION
				"Request, that the master identified by this antry, transmits unicast Announce, Sync
				and Delay_Resp messages to that slave clock will be sent.
				PTP message rates autonegotiation will be performed with a master identified by this entry.
				"
			INDEX { shePtpPortDSPortNumber, shePtpUnicastDiscoveryMasterIndex }
			::= { shePtpUnicastDiscoveryMasterTable 1 }

		
		ShePtpUnicastDiscoveryMasterEntry ::=
			SEQUENCE { 
				shePtpUnicastDiscoveryMasterIndex
					ShePtpUnicastDiscoveryMasterIndexType,
				shePtpUnicastDiscoveryMasterNetworkProtocol
					ShePtpAcceptableMasterNetworkProtocolType,
				shePtpUnicastDiscoveryMasterProtocolAddressLength
					Integer32,
				shePtpUnicastDiscoveryMasterProtocolAddress
					OCTET STRING
			 }

		shePtpUnicastDiscoveryMasterIndex OBJECT-TYPE
			SYNTAX ShePtpUnicastDiscoveryMasterIndexType
			MAX-ACCESS read-only
			STATUS current
			DESCRIPTION
				"second table Index"
			::= { shePtpUnicastDiscoveryMasterEntry 1 }

		
		shePtpUnicastDiscoveryMasterNetworkProtocol OBJECT-TYPE
			SYNTAX ShePtpAcceptableMasterNetworkProtocolType
			MAX-ACCESS read-only
			STATUS current
			DESCRIPTION
				"Supported PTP transport protocol is only IP/UDP."
			DEFVAL { ipUdp }
			::= { shePtpUnicastDiscoveryMasterEntry 2 }

		
		shePtpUnicastDiscoveryMasterProtocolAddressLength OBJECT-TYPE
			SYNTAX Integer32 (4)
			MAX-ACCESS read-only
			STATUS current
			DESCRIPTION
				"Supported PTP transport protocol is only IP/UDP so address length is always 4."
			::= { shePtpUnicastDiscoveryMasterEntry 3 }

		
		shePtpUnicastDiscoveryMasterProtocolAddress OBJECT-TYPE
			SYNTAX OCTET STRING (SIZE (0..16))
			MAX-ACCESS read-only
			STATUS current
			DESCRIPTION
				"Protocol address of master clock port to which this slave clock is to be sending
				unicast message GRANT REQUESTS, i.e. unicast discovery of the master which port address
				is added to the shePtpUnicastDiscoveryMasterTable shall be in effect right after an 
				entry is added (if this address is not yet in the shePtpUnicastDiscoveryMasterTable
				and PTP message rates are not already negotiated). 
				Please NOTE that the master's port address must be added in advance to the shePtpAcceptableMasterTable too."
			::= { shePtpUnicastDiscoveryMasterEntry 4 }

		
		shePtpUnicastDiscoveryMasterControl OBJECT IDENTIFIER ::= { shePtpObjects 12 }

		
		shePtpUnicastDiscoveryMasterControlRequest OBJECT-TYPE
			SYNTAX ShePtpControlRequestType
			MAX-ACCESS read-write
			STATUS current
			DESCRIPTION
				"createPtpUnicastDiscoveryMasterTableEntry (15):
				shePtpUnicastDiscoveryMasterControlPortDsNumber
				shePtpUnicastDiscoveryMasterControlProtocolAddress
				
				modifyPtpUnicastDiscoveryMasterTableEntry (16):
				shePtpUnicastDiscoveryMasterControlPortDsNumber
				shePtpUnicastDiscoveryMasterControlIndex
				shePtpUnicastDiscoveryMasterControlProtocolAddress
				
				deletePtpUnicastDiscoveryMasterTableEntry (17):
				shePtpUnicastDiscoveryMasterControlPortDsNumber
				shePtpUnicastDiscoveryMasterControlIndex
				"
			::= { shePtpUnicastDiscoveryMasterControl 1 }

		
		shePtpUnicastDiscoveryMasterControlControlStatus OBJECT-TYPE
			SYNTAX SheControlStatusType
			MAX-ACCESS read-only
			STATUS current
			DESCRIPTION
				"The status of a user command. 
				"
			::= { shePtpUnicastDiscoveryMasterControl 2 }

		
		shePtpUnicastDiscoveryMasterControlTimer OBJECT-TYPE
			SYNTAX Gauge32
			MAX-ACCESS read-only
			STATUS current
			DESCRIPTION
				"The maximum wait time for the manager for a long running user command. 
				"
			::= { shePtpUnicastDiscoveryMasterControl 3 }

		
		shePtpUnicastDiscoveryMasterControlReqResult OBJECT-TYPE
			SYNTAX ShePtpControlRequestResultType
			MAX-ACCESS read-only
			STATUS current
			DESCRIPTION
				"The result of the last user command."
			::= { shePtpUnicastDiscoveryMasterControl 4 }

		
		shePtpUnicastDiscoveryMasterControlTimeStamp OBJECT-TYPE
			SYNTAX Unsigned32
			UNITS "sec"
			MAX-ACCESS read-only
			STATUS current
			DESCRIPTION
				"The time stamp of the last command (end of command)."
			::= { shePtpUnicastDiscoveryMasterControl 5 }

		
		shePtpUnicastDiscoveryMasterControlPortDsNumber OBJECT-TYPE
			SYNTAX Unsigned32 (1..5)
			MAX-ACCESS read-write
			STATUS current
			DESCRIPTION
				"The index 1 of unicast discovery master table entry for configuration - portDs index."
			::= { shePtpUnicastDiscoveryMasterControl 6 }

		
		shePtpUnicastDiscoveryMasterControlIndex OBJECT-TYPE
			SYNTAX ShePtpUnicastDiscoveryMasterIndexType
			MAX-ACCESS read-write
			STATUS current
			DESCRIPTION
				"The index 2 of unicast discovery master table."
			::= { shePtpUnicastDiscoveryMasterControl 7 }

		
		shePtpUnicastDiscoveryMasterControlProtocolAddress OBJECT-TYPE
			SYNTAX OCTET STRING (SIZE (0..16))
			MAX-ACCESS read-write
			STATUS current
			DESCRIPTION
				"look at table."
			::= { shePtpUnicastDiscoveryMasterControl 8 }

		
		shePtpNotifications OBJECT IDENTIFIER ::= { shePtpMIB 2 }

		
		shePtpEvents OBJECT IDENTIFIER ::= { shePtpNotifications 1 }

		
		shePtpAdminStateChanged NOTIFICATION-TYPE
			OBJECTS { shePtpAdminState }
			STATUS current
			DESCRIPTION 
				"The administrative state of the PTP subsystem has changed."
			::= { shePtpEvents 1 }

		
		shePtpDefaultDataSetModified NOTIFICATION-TYPE
			OBJECTS { shePtpDefaultDSControlTimeStamp, shePtpDefaultDSControlInitializable, shePtpDefaultDSControlTwoStepFlag, shePtpDefaultDSControlIdentity, shePtpDefaultDSControlPriority1, 
				shePtpDefaultDSControlPriority2, shePtpDefaultDSControlDomainNumber }
			STATUS current
			DESCRIPTION 
				"Notification for successful PTP default data set configuration."
			::= { shePtpEvents 2 }

		
		shePtpPortConfigDataModified NOTIFICATION-TYPE
			OBJECTS { shePtpPortDataSetControlTimeStamp, shePtpPortDataSetControlIndex, shePtpPortDataSetControlUnicastNegotiationEnabled, shePtpPortDataSetControlUnicastNegotiationDuration, shePtpPortDataSetControlUnicastLogQueryInterval, 
				shePtpPortDataSetControlVlanId, shePtpPortDataSetControlLogMeanSyncInterval, shePtpPortDataSetControlLogMinMeanDelayReqInterval, shePtpPortDataSetControlLogMeanAnnounceInterval, shePtpPortDataSetControlAnnounceReceiptTimeout, 
				shePtpPortDataSetControlLogMinPdelayReqInterval, shePtpPortDataSetControlAlarmSeverityIndex }
			STATUS current
			DESCRIPTION 
				"Notification for successfull PTP port config data configuration."
			::= { shePtpEvents 3 }

		
		shePtpAcceptableMasterTableEntryCreated NOTIFICATION-TYPE
			OBJECTS { shePtpAcceptableMasterControlTimeStamp, shePtpAcceptableMasterControlIndex, shePtpAcceptableMasterControlProtocolAddress, shePtpAcceptableMasterControlPriority, shePtpAcceptableMasterControlUnicast, 
				shePtpAcceptableMasterControlMinTimingPktSize }
			STATUS current
			DESCRIPTION 
				"Notification for successfull create of PTP acceptable master table entry."
			::= { shePtpEvents 4 }

		
		shePtpAcceptableMasterTableEntryModified NOTIFICATION-TYPE
			OBJECTS { shePtpAcceptableMasterControlTimeStamp, shePtpAcceptableMasterControlIndex, shePtpAcceptableMasterControlProtocolAddress, shePtpAcceptableMasterControlPriority, shePtpAcceptableMasterControlUnicast, 
				shePtpAcceptableMasterControlMinTimingPktSize }
			STATUS current
			DESCRIPTION 
				"Notification for successfull modify of PTP acceptable master table entry."
			::= { shePtpEvents 5 }

		
		shePtpAcceptableMasterTableEntryDeleted NOTIFICATION-TYPE
			OBJECTS { shePtpAcceptableMasterControlTimeStamp, shePtpAcceptableMasterControlIndex }
			STATUS current
			DESCRIPTION 
				"Notification for successfull delete of PTP acceptable master table entry."
			::= { shePtpEvents 6 }

		
		shePtpUnicastDiscoveryMasterTableEntryCreated NOTIFICATION-TYPE
			OBJECTS { shePtpUnicastDiscoveryMasterControlTimeStamp, shePtpUnicastDiscoveryMasterControlPortDsNumber, shePtpUnicastDiscoveryMasterControlIndex, shePtpUnicastDiscoveryMasterControlProtocolAddress }
			STATUS current
			DESCRIPTION 
				"Notification for successfull create of PTP unicast discovery master table entry."
			::= { shePtpEvents 7 }

		
		shePtpUnicastDiscoveryMasterTableEntryModified NOTIFICATION-TYPE
			OBJECTS { shePtpUnicastDiscoveryMasterControlTimeStamp, shePtpUnicastDiscoveryMasterControlPortDsNumber, shePtpUnicastDiscoveryMasterControlIndex, shePtpUnicastDiscoveryMasterControlProtocolAddress }
			STATUS current
			DESCRIPTION 
				"Notification for successfull modify of PTP unicast discovery master table entry."
			::= { shePtpEvents 8 }

		
		shePtpUnicastDiscoveryMasterTableEntryDeleted NOTIFICATION-TYPE
			OBJECTS { shePtpUnicastDiscoveryMasterControlTimeStamp, shePtpUnicastDiscoveryMasterControlPortDsNumber, shePtpUnicastDiscoveryMasterControlIndex }
			STATUS current
			DESCRIPTION 
				"Notification for successfull delete of PTP unicast discovery master table entry."
			::= { shePtpEvents 9 }

		
		shePtpForeignMasterTableChanged NOTIFICATION-TYPE
			OBJECTS { shePtpPortDataSetControlTimeStamp, shePtpForeignMasterDSNumberForeignRecords, shePtpForeignMasterDSClockIdentity, shePtpForeignMasterDSPortNumber, shePtpForeignMasterDSAnnounceMessages, 
				shePtpForeignMasterDSNetworkProtocol, shePtpForeignMasterDSProtocolAddressLength, shePtpForeignMasterDSProtocolAddress }
			STATUS current
			DESCRIPTION 
				"This trap will be send if the foreign master table changes because of new detected masters or a
				alraedy detected entry is lost."
			::= { shePtpEvents 10 }

		
		shePtpAlarms OBJECT IDENTIFIER ::= { shePtpNotifications 2 }

		
		shePtpSynchronizationAlarm NOTIFICATION-TYPE
			OBJECTS { sheAlarmTimeAndDate, sheAlarmReportingSource, sheAlarmReportingSourceType, sheAlarmSeverity }
			STATUS current
			DESCRIPTION 
				"This alarm will be activated if the ptp sync module is enabled and no external sync master
				was found or connection could not be established or was lost."
			::= { shePtpAlarms 1 }

		
		shePtpIpHostInterfaceAlarm NOTIFICATION-TYPE
			OBJECTS { sheAlarmTimeAndDate, sheAlarmReportingSource, sheAlarmReportingSourceType, sheAlarmSeverity }
			STATUS current
			DESCRIPTION 
				"This alarm will be activated:
				1. If the ptp sync module is enabled and no valid IpHostInterface configuration could be detected.
				   -> Configure a valid host interface via sheSystemIpHostTable.
				2. The used interface was reconfigured during ongoing PTP session.
				   -> The PTP module must be restarted.
				"
			::= { shePtpAlarms 2 }

		
		shePtpConformance OBJECT IDENTIFIER ::= { shePtpMIB 100 }

		
--  ***********************************************************
-- 
-- P T P  M I B   N O T I F I C A T I O N S
-- 
-- *********************************************************** 
-- 
-- tbd.
-- 
-- ***********************************************************
-- 
--    P T P   M I B   C O N F O R M A N C E 
-- 
-- *********************************************************** 
-- 
-- tbd.
		shePtpCompliances OBJECT IDENTIFIER ::= { shePtpConformance 1 }

		
--  compliance statements
-- this module
		shePtpCompliance MODULE-COMPLIANCE
			STATUS current
			DESCRIPTION 
				"The compliance statement for SNMP entities which implement
				the PTP MIB."
			MODULE -- this module
				MANDATORY-GROUPS { shePtpGroup, shePtpNotificationGroup, shePtpControlGroup }
			::= { shePtpCompliances 1 }

		
		shePtpGroups OBJECT IDENTIFIER ::= { shePtpConformance 2 }

		
		shePtpGroup OBJECT-GROUP
			OBJECTS { shePtpAdminState, shePtpManufacturerIdentity, shePtpRevisionData, shePtpClockType, shePtpVersion, 
				shePtpDefaultDSInitializable, shePtpDefaultDSTwoStepFlag, shePtpDefaultDSIdentity, shePtpDefaultDSNumberPorts, shePtpDefaultDSClass, 
				shePtpDefaultDSAccuracy, shePtpDefaultDSVariance, shePtpDefaultDSPriority1, shePtpDefaultDSPriority2, shePtpDefaultDSDomainNumber, 
				shePtpDefaultDSSlaveOnly, shePtpParentClockIdentity, shePtpParentClockPortNumber, shePtpParentGrandmasterIdentity, shePtpParentGrandmasterClockClass, 
				shePtpParentGrandmasterClockAccuracy, shePtpParentGrandmasterClockVariance, shePtpParentGrandmasterPriority1, shePtpParentGrandmasterPriority2, shePtpForeignMasterDSNumberForeignRecords, 
				shePtpForeignMasterDSClockIdentity, shePtpForeignMasterDSPortNumber, shePtpForeignMasterDSAnnounceMessages, shePtpPortDSDelayMechanism, shePtpPortDSClockIdentity, 
				shePtpPortDSPortNumber, shePtpPortDSAcceptableMasterEnabled, shePtpPortDSUnicastNegotiationEnabled, shePtpPortDSUnicastLogQueryInterval, shePtpPortDSVlanId, 
				shePtpPortDSUnicastNegotiationDuration, shePtpAcceptableMasterIndex, shePtpAcceptableMasterNetworkProtocol, shePtpAcceptableMasterProtocolAddressLength, shePtpAcceptableMasterProtocolAddress, 
				shePtpAcceptableMasterPriority, shePtpAcceptableMasterMinTimingPktSize, shePtpAcceptableMasterSyncStatus, shePtpAcceptableMasterControlRequest, shePtpAcceptableMasterControlStatus, 
				shePtpAcceptableMasterControlTimer, shePtpAcceptableMasterControlReqResult, shePtpAcceptableMasterControlTimeStamp, shePtpAcceptableMasterControlIndex, shePtpAcceptableMasterControlProtocolAddress, 
				shePtpAcceptableMasterControlPriority, shePtpUnicastDiscoveryMasterIndex, shePtpPortDSLogMeanSyncInterval, shePtpPortDSLogMinMeanDelayReqInterval, shePtpPortDSLogMeanAnnounceInterval, 
				shePtpPortDSAnnounceReceiptTimeout, shePtpPortDSLogMinPdelayReqInterval, shePtpPortDSAlarmSeverityIndex, shePtpUnicastDiscoveryMasterNetworkProtocol, shePtpUnicastDiscoveryMasterProtocolAddressLength, 
				shePtpUnicastDiscoveryMasterProtocolAddress, shePtpForeignMasterDSNetworkProtocol, shePtpForeignMasterDSProtocolAddressLength, shePtpAcceptableMasterUnicast, shePtpCurrentDataSetStepsRemoved, 
				shePtpCurrentDataSetOffsettFromMasterSeconds, shePtpCurrentDataSetOffsettFromMasterNanoSeconds, shePtpCurrentDataSetMeanPathDelaySeconds, shePtpCurrentDataSetMeanPathDelayNanoSeconds, shePtpForeignMasterDSIndex, 
				shePtpForeignMasterDSProtocolAddress }
			STATUS current
			DESCRIPTION 
				"Description."
			::= { shePtpGroups 1 }

		
		shePtpControlGroup OBJECT-GROUP
			OBJECTS { shePtpDefaultDSControlRequest, shePtpDefaultDSControlStatus, shePtpDefaultDSControlTimer, shePtpDefaultDSControlReqResult, shePtpDefaultDSControlTimeStamp, 
				shePtpDefaultDSControlInitializable, shePtpDefaultDSControlTwoStepFlag, shePtpDefaultDSControlIdentity, shePtpDefaultDSControlPriority1, shePtpDefaultDSControlPriority2, 
				shePtpDefaultDSControlDomainNumber, shePtpPortDataSetControlRequest, shePtpPortDataSetControlStatus, shePtpPortDataSetControlTimer, shePtpPortDataSetControlControlReqResult, 
				shePtpPortDataSetControlTimeStamp, shePtpPortDataSetControlIndex, shePtpPortDataSetControlUnicastNegotiationEnabled, shePtpPortDataSetControlUnicastNegotiationDuration, shePtpPortDataSetControlUnicastLogQueryInterval, 
				shePtpPortDataSetControlVlanId, shePtpPortDataSetControlAlarmSeverityIndex, shePtpAcceptableMasterControlRequest, shePtpAcceptableMasterControlStatus, shePtpAcceptableMasterControlTimer, 
				shePtpAcceptableMasterControlReqResult, shePtpAcceptableMasterControlTimeStamp, shePtpAcceptableMasterControlIndex, shePtpAcceptableMasterControlProtocolAddress, shePtpAcceptableMasterControlPriority, 
				shePtpAcceptableMasterControlUnicast, shePtpAcceptableMasterControlMinTimingPktSize, shePtpUnicastDiscoveryMasterControlRequest, shePtpUnicastDiscoveryMasterControlControlStatus, shePtpUnicastDiscoveryMasterControlTimer, 
				shePtpUnicastDiscoveryMasterControlReqResult, shePtpUnicastDiscoveryMasterControlTimeStamp, shePtpPortDataSetControlLogMeanSyncInterval, shePtpPortDataSetControlLogMinMeanDelayReqInterval, shePtpPortDataSetControlLogMeanAnnounceInterval, 
				shePtpPortDataSetControlAnnounceReceiptTimeout, shePtpPortDataSetControlLogMinPdelayReqInterval, shePtpUnicastDiscoveryMasterControlProtocolAddress, shePtpUnicastDiscoveryMasterControlIndex, shePtpUnicastDiscoveryMasterControlPortDsNumber
				 }
			STATUS current
			DESCRIPTION 
				"Description."
			::= { shePtpGroups 2 }

		
		shePtpNotificationGroup NOTIFICATION-GROUP
			NOTIFICATIONS { shePtpAdminStateChanged, shePtpDefaultDataSetModified, shePtpAcceptableMasterTableEntryCreated, shePtpForeignMasterTableChanged, shePtpAcceptableMasterTableEntryModified, 
				shePtpAcceptableMasterTableEntryDeleted, shePtpUnicastDiscoveryMasterTableEntryModified, shePtpSynchronizationAlarm, shePtpPortConfigDataModified, shePtpIpHostInterfaceAlarm, 
				shePtpUnicastDiscoveryMasterTableEntryDeleted, shePtpUnicastDiscoveryMasterTableEntryCreated }
			STATUS current
			DESCRIPTION 
				"Description."
			::= { shePtpGroups 3 }

		
	
	END

--
-- she-ptp-mib.mib
--
