ELTEX-MES-AAA-STATISTICS-MIB DEFINITIONS ::= BEGIN


IMPORTS
    eltMesAAAStatMIB                    FROM ELTEX-MES-MNG-MIB
    MODULE-IDENTITY, OBJECT-TYPE,
    Counter32,Unsigned32,IpAddress      FROM SNMPv2-SMI
    InetAddress, InetAddressType        FROM INET-ADDRESS-MIB -- RFC2851
    TruthValue,DisplayString,
    TEXTUAL-CONVENTION                  FROM SNMPv2-TC;

eltRadiusAuthServTotalAccessRequests OBJECT-TYPE
    SYNTAX      Counter32
    MAX-ACCESS  read-only
    STATUS      current
    DESCRIPTION
        "The number of packets received on the authentication port."
    ::= { eltMesAAAStatMIB 1 }

eltRadiusAuthServTotalAccessAccepts OBJECT-TYPE
    SYNTAX      Counter32
    MAX-ACCESS  read-only
    STATUS      current
    DESCRIPTION
        "The number of RADIUS Access-Accept packets sent."
    ::= { eltMesAAAStatMIB 2 }

eltRadiusAuthServAccessRejects OBJECT-TYPE
    SYNTAX      Counter32
    MAX-ACCESS  read-only
    STATUS      current
    DESCRIPTION
        "The number of RADIUS Access-Reject packets sent."
    ::= { eltMesAAAStatMIB 3 }

eltRadiusAuthServAccessChallenges OBJECT-TYPE
    SYNTAX      Counter32
    MAX-ACCESS  read-only
    STATUS      current
    DESCRIPTION
        "The number of RADIUS Access-Challenge packets sent."
    ::= { eltMesAAAStatMIB 4 }

eltRadiusAuthServAverageResponseDelay OBJECT-TYPE
    SYNTAX      Counter32
    MAX-ACCESS  read-only
    STATUS      current
    DESCRIPTION
        "Average response delay(ms)
        Average time from when the packet was first transmitted to when it
        received a response. If the response timed out and the packet was sent
        again, this value includes the timeout. If the packet never received a
        response, this is not included in the average.
        "
    ::= { eltMesAAAStatMIB 5 }

eltRadiusAuthServMaximumResponseDelay OBJECT-TYPE
    SYNTAX      Counter32
    MAX-ACCESS  read-only
    STATUS      current
    DESCRIPTION
        "Maximum response delay(ms)
         Maximum delay observed while gathering average response delay
         information."
    ::= { eltMesAAAStatMIB 6 }

eltRadiusAuthServTotalTimeouts OBJECT-TYPE
    SYNTAX      Unsigned32
    MAX-ACCESS  read-only
    STATUS      current
    DESCRIPTION
        "Number of times a server did not respond, and the RADIUS server
         re-sent the packet."
    ::= { eltMesAAAStatMIB 7 }

eltRadiusAuthServTotalMalformedAccessRequests OBJECT-TYPE
    SYNTAX      Counter32
    MAX-ACCESS  read-only
    STATUS      current
    DESCRIPTION
        "The number of malformed RADIUS Access-Request
        packets received.  Bad authenticators
        and unknown types are not included as
        malformed Access-Requests."
    ::= { eltMesAAAStatMIB 8 }

eltRadiusAuthServMaximumBufferSize OBJECT-TYPE
    SYNTAX      Counter32
    MAX-ACCESS  read-only
    STATUS      current
    DESCRIPTION
        "The maximum buffer size in bytes."
    ::= { eltMesAAAStatMIB 9 }

eltRadiusAuthServTotalPacketsDropped  OBJECT-TYPE
    SYNTAX      Counter32
    MAX-ACCESS  read-only
    STATUS      current
    DESCRIPTION
        "The number of incoming packets
        silently discarded for some reason other
        than malformed, bad authenticators or
        unknown types."
    ::= { eltMesAAAStatMIB 10 }
--

eltRadiusAccServTotalRequests OBJECT-TYPE
    SYNTAX      Counter32
    MAX-ACCESS  read-only
    STATUS      current
    DESCRIPTION
        "The number of packets received on the accounting port."
    ::= { eltMesAAAStatMIB 11 }

eltRadiusAccServTotalDupRequests OBJECT-TYPE
    SYNTAX      Counter32
    MAX-ACCESS  read-only
    STATUS      current
    DESCRIPTION
        "The number of duplicate RADIUS Accounting-Request packets received."
    ::= { eltMesAAAStatMIB 12 }


eltRadiusAccServTotalResponses OBJECT-TYPE
    SYNTAX      Counter32
    MAX-ACCESS  read-only
    STATUS      current
    DESCRIPTION
        "The number of RADIUS Accounting-Response packets sent."
    ::= { eltMesAAAStatMIB 13 }

eltRadiusAccServAverageResponseDelay OBJECT-TYPE
    SYNTAX      Counter32
    MAX-ACCESS  read-only
    STATUS      current
    DESCRIPTION
        "Average response delay(ms)
        Average time from when the packet was first transmitted to when it
        received a response. If the response timed out and the packet was sent
        again, this value includes the timeout. If the packet never received a
        response, this is not included in the average.
        "
    ::= { eltMesAAAStatMIB 14 }

eltRadiusAccServMaximumResponseDelay OBJECT-TYPE
    SYNTAX      Counter32
    MAX-ACCESS  read-only
    STATUS      current
    DESCRIPTION
        "Maximum response delay(ms)
         Maximum delay observed while gathering average response delay
         information."
    ::= { eltMesAAAStatMIB 15 }

eltRadiusAccServTotalTimeouts OBJECT-TYPE
    SYNTAX      Unsigned32
    MAX-ACCESS  read-only
    STATUS      current
    DESCRIPTION
        "Number of times a server did not respond, and the RADIUS server
         re-sent the packet."
    ::= { eltMesAAAStatMIB 16 }

eltRadiusAccServTotalMalformedAccessRequests OBJECT-TYPE
    SYNTAX      Counter32
    MAX-ACCESS  read-only
    STATUS      current
    DESCRIPTION
        "The number of malformed RADIUS Accounting-Request
        packets received.  Bad authenticators or unknown
        types are not included as malformed Access-Requests."
    ::= { eltMesAAAStatMIB 17 }

eltRadiusAccServMaximumBufferSize OBJECT-TYPE
    SYNTAX      Counter32
    MAX-ACCESS  read-only
    STATUS      current
    DESCRIPTION
        "The maximum buffer size in bytes."
    ::= { eltMesAAAStatMIB 18 }

eltRadiusAccServTotalPacketsDropped  OBJECT-TYPE
    SYNTAX      Counter32
    MAX-ACCESS  read-only
    STATUS      current
    DESCRIPTION
        "The number of incoming packets silently discarded
        for a reason other than malformed, bad authenticators,
        or unknown types."
    ::= { eltMesAAAStatMIB 19 }

eltTacacsStatsTable OBJECT-TYPE
        SYNTAX      SEQUENCE OF EltTacacsStatsEntry
        MAX-ACCESS  not-accessible
        STATUS      current
        DESCRIPTION
                "This table contains the statistics for the
                TACACS+ servers."
        ::= { eltMesAAAStatMIB 20 }

eltTacacsStatsEntry OBJECT-TYPE
        SYNTAX     EltTacacsStatsEntry
        MAX-ACCESS not-accessible
        STATUS     current
        DESCRIPTION
                "AEntry is TACACS + server, containing its statistics."
        INDEX       { eltTacacsServerAddress }
        ::= { eltTacacsStatsTable 1 }

   EltTacacsStatsEntry ::=
     SEQUENCE {
       eltTacacsServerAddress              IpAddress,
       eltTacacsSocketOpens                Unsigned32,
       eltTacacsSocketCloses                      Unsigned32,
       eltTacacsSocketAborts               Unsigned32,
       eltTacacsSocketErrors               Unsigned32,
       eltTacacsSocketTimeouts             Unsigned32,
       eltTacacsFailesConnAttemps          Unsigned32,
       eltTacacsTotalPackageSent           Unsigned32,
       eltTacacsTotalPackageRecv           Unsigned32
     }

eltTacacsServerAddress OBJECT-TYPE
    SYNTAX     IpAddress
    MAX-ACCESS     read-write
    STATUS current
    DESCRIPTION
        "The IP address of the TACACS+ server
        referred to in this table entry."
    ::= { eltTacacsStatsEntry 1 }

eltTacacsSocketOpens OBJECT-TYPE
    SYNTAX         Unsigned32
    MAX-ACCESS     read-write
    STATUS current
    DESCRIPTION
        "Number of successful TCP socket
        connections to the TACACS+ server."
    ::= { eltTacacsStatsEntry 2 }

eltTacacsSocketCloses OBJECT-TYPE
    SYNTAX         Unsigned32
    MAX-ACCESS     read-write
    STATUS current
    DESCRIPTION
        "Number of successfully closed
        TCP socket attempts."
    ::= { eltTacacsStatsEntry 3 }

eltTacacsSocketAborts OBJECT-TYPE
    SYNTAX         Unsigned32
    MAX-ACCESS     read-write
    STATUS current
    DESCRIPTION
        "Number of premature TCP socket closures to
        the TACACS+ server; that is, the peer did
        not wait for a reply from the server after
        a the peer sent its request."
    ::= { eltTacacsStatsEntry 4 }

eltTacacsSocketErrors OBJECT-TYPE
    SYNTAX         Unsigned32
    MAX-ACCESS     read-write
    STATUS current
    DESCRIPTION
        "Any other socket read or write errors,
        such as incorrect packet format and length."
    ::= { eltTacacsStatsEntry 5 }

eltTacacsSocketTimeouts OBJECT-TYPE
    SYNTAX         Unsigned32
    MAX-ACCESS     read-write
    STATUS current
    DESCRIPTION
        "Number of times a server did not respond."
    ::= { eltTacacsStatsEntry 6 }

eltTacacsFailesConnAttemps OBJECT-TYPE
    SYNTAX         Unsigned32
    MAX-ACCESS     read-write
    STATUS current
    DESCRIPTION
        "Number of failed TCP socket connections
        to the TACACS+ server."
    ::= { eltTacacsStatsEntry 7 }

eltTacacsTotalPackageSent OBJECT-TYPE
    SYNTAX         Unsigned32
    MAX-ACCESS     read-write
    STATUS current
    DESCRIPTION
        "Number of packets sent to the TACACS+ server."
    ::= { eltTacacsStatsEntry 8 }

eltTacacsTotalPackageRecv OBJECT-TYPE
    SYNTAX         Unsigned32
    MAX-ACCESS     read-write
    STATUS current
    DESCRIPTION
        "Number of packets received from the TACACS+ server."
    ::= { eltTacacsStatsEntry 9 }

eltRadiusServerStatusTable OBJECT-TYPE
    SYNTAX     SEQUENCE OF ELTRadiusServerStatusEntry
    MAX-ACCESS     not-accessible
    STATUS current
    DESCRIPTION
        "The (conceptual) table listing the RADIUS
        servers with which the cliient shares a secret."
    ::= { eltMesAAAStatMIB 21 }

eltRadiusServerStatusEntry OBJECT-TYPE
    SYNTAX     ELTRadiusServerStatusEntry
    MAX-ACCESS     not-accessible
    STATUS current
    DESCRIPTION
        "An entry (conceptual row) representing a RADIUS
        server with which the client shares
        a secret."
    INDEX      { eltRadiusServerAddressType,
                 eltRadiusServerAddress,
                 eltRadiusServerAuthPortNumber,
                 eltRadiusServerAcctPortNumber}
    ::= { eltRadiusServerStatusTable 1 }

ELTRadiusServerStatusEntry ::= SEQUENCE {
    eltRadiusServerAddressType                   InetAddressType,
    eltRadiusServerAddress                       InetAddress,
    eltRadiusServerAuthPortNumber                INTEGER,
    eltRadiusServerAcctPortNumber                INTEGER,
    eltRadiusServerAuthClientTimeouts            Unsigned32,
    eltRadiusServerDeadStatus                    TruthValue,
    eltRadiusServerRemainDeadTime                Unsigned32
}

eltRadiusServerAddressType OBJECT-TYPE
    SYNTAX  InetAddressType
    MAX-ACCESS read-write
    STATUS current
    DESCRIPTION
        "The Inet address type of RADIUS server reffered to
         in this table entry .IPv6Z type is not supported."
    ::= { eltRadiusServerStatusEntry 1}

eltRadiusServerAddress OBJECT-TYPE
    SYNTAX         InetAddress
    MAX-ACCESS     read-write
    STATUS current
    DESCRIPTION
        "The IP address of the RADIUS server
        referred to in this table entry."
    ::= { eltRadiusServerStatusEntry 2 }

eltRadiusServerAuthPortNumber  OBJECT-TYPE
    SYNTAX INTEGER (0..65535)
    MAX-ACCESS read-write
    STATUS current
    DESCRIPTION
        "The UDP port the client is using to send authentication
        requests to this server."
    ::= { eltRadiusServerStatusEntry 3 }

eltRadiusServerAcctPortNumber  OBJECT-TYPE
    SYNTAX INTEGER (0..65535)
    MAX-ACCESS read-write
    STATUS current
    DESCRIPTION
        "The UDP port the client is using to send accounting
        requests to this server."
    ::= { eltRadiusServerStatusEntry 4 }

eltRadiusServerAuthClientTimeouts  OBJECT-TYPE
    SYNTAX Unsigned32
    MAX-ACCESS read-only
    STATUS current
    DESCRIPTION
        "The timeouts this RADIUS server to reply."
    ::= { eltRadiusServerStatusEntry 5 }



eltRadiusServerDeadStatus  OBJECT-TYPE
    SYNTAX TruthValue
    MAX-ACCESS read-only
    STATUS current
    DESCRIPTION
        "The dead status for this RADIUS server."
    ::= { eltRadiusServerStatusEntry 6 }

eltRadiusServerRemainDeadTime OBJECT-TYPE
    SYNTAX Unsigned32
    MAX-ACCESS read-only
    STATUS current
    DESCRIPTION
        "The remain dead time for this RADIUS server."
    ::= { eltRadiusServerStatusEntry 7 }


eltRadiusServerStatusReset OBJECT-TYPE
    SYNTAX      INTEGER  (0..1)
    MAX-ACCESS  read-write
    STATUS      current
    DESCRIPTION
        "Reset dead status for all RADIUS servers."
    ::= { eltMesAAAStatMIB 22 }


END
