--
-- HUAWEI-L2VPN-PW-APS-MIB.mib
--

--  ==================================================================
-- Copyright (C) 2013 by  HUAWEI TECHNOLOGIES. All rights reserved.
-- 
-- Description: HUAWEI L2VPN PW APS TRAP Management MIB
-- Reference:
-- Version:     V1.0
-- History:
--              V1.0 houchengjie, 2011-04-21, publish
-- ==================================================================

    HUAWEI-L2VPN-PW-APS-MIB DEFINITIONS ::= BEGIN

        IMPORTS
            hwDatacomm
                FROM HUAWEI-MIB
            HWL2VpnVcEncapsType
                FROM HUAWEI-VPLS-EXT-MIB
            Unsigned32,OBJECT-TYPE, MODULE-IDENTITY, NOTIFICATION-TYPE
                FROM SNMPv2-SMI
            OBJECT-GROUP, MODULE-COMPLIANCE, NOTIFICATION-GROUP
                FROM SNMPv2-CONF
            RowStatus
                FROM SNMPv2-TC
            hwPWInterfaceIndex
                FROM HUAWEI-PWE3-MIB;

        -- 1.3.6.1.4.1.2011.5.25.119.10
    hwL2vpnPwAps MODULE-IDENTITY 
        LAST-UPDATED "201305131250Z"        -- May 13, 2013 at 12:50 GMT
        ORGANIZATION
            "Huawei Technologies Co.,Ltd."
        CONTACT-INFO 
            "Huawei Industrial Base
              Bantian, Longgang
               Shenzhen 518129
               People's Republic of China
               Website: http://www.huawei.com
               Email: support@huawei.com
             "
        DESCRIPTION 
            "The HUAWEI-L2VPN-PW-APS-MIB contains objects to
            manage PW APS."
        -- Revision history
        REVISION "201305131250Z"
             DESCRIPTION "V2.11, add hwPwApsDegraded for PTN5900"
        ::= { hwL2Vpn 10 }


--
-- Node definitions
--

--  Node definitions
-- 
        -- 1.3.6.1.4.1.2011.5.25.119
        hwL2Vpn OBJECT IDENTIFIER ::= { hwDatacomm 119 }


--           
-- The APS ALARM Attribute Group
-- 
        -- 1.3.6.1.4.1.2011.5.25.119.10.1
        hwPwApsObjects OBJECT IDENTIFIER ::= { hwL2vpnPwAps 1 }


--
-- The L2VPN's PwAps Table
-- 
        hwPwApsTable OBJECT-TYPE
            SYNTAX SEQUENCE OF HWPwApsEntry
            MAX-ACCESS not-accessible
            STATUS current
            DESCRIPTION
                "This table provides the information of PW APS."
            ::= { hwPwApsObjects 1 }

        hwPwApsEntry OBJECT-TYPE
            SYNTAX HWPwApsEntry
            MAX-ACCESS not-accessible
            STATUS current
            DESCRIPTION
                "Provides the information of a PW APS entry."
            INDEX { hwPwApsId }
            ::= { hwPwApsTable 1 }

        HWPwApsEntry ::=
            SEQUENCE { 
                hwPwApsId
                    Unsigned32,
                hwPwApsRole
                    INTEGER,
                hwPwApsRequestResult
                    INTEGER,
                hwPwApsState
                    INTEGER,
                hwPwApsWorkState
                    INTEGER,
                hwPwApsProtectState
                    INTEGER 
             }

        hwPwApsId OBJECT-TYPE
            SYNTAX Unsigned32
            MAX-ACCESS accessible-for-notify
            STATUS current
            DESCRIPTION
                "This object indicates the ID of the PW APS."
            ::= { hwPwApsEntry 1 }

        hwPwApsRole OBJECT-TYPE
            SYNTAX INTEGER
                {
                master(1),
                slave(2),
                unknown(255)
                }
            MAX-ACCESS read-only
            STATUS current
            DESCRIPTION
                "This object indicates the role of the PW APS."
            ::= { hwPwApsEntry 2 }

        hwPwApsRequestResult OBJECT-TYPE
            SYNTAX INTEGER
                {
                work(1),
                protect(2)
                }
            MAX-ACCESS read-only
            STATUS current
            DESCRIPTION
                "This object indicates the request result of the PW APS."
            ::= { hwPwApsEntry 3 }

       hwPwApsState OBJECT-TYPE
            SYNTAX INTEGER
                {
                lo(1),
                sfp(2),
                fs(3),
                sf(4),
                sdp(5),
                sd(6),
                ms(7),
                wtr(8),
                exer(9),
                rr(10),
                dnr(11),
                nr(12),
                unknown(255)
                }
            MAX-ACCESS read-only
            STATUS current
            DESCRIPTION
                "This object indicates the state of the PW APS."
            ::= { hwPwApsEntry 4 }

       hwPwApsWorkState OBJECT-TYPE
            SYNTAX INTEGER
                {
                nondefect(1),
                defect(2),
                defectsd(3),
                unknown(255)
                }
            MAX-ACCESS read-only
            STATUS current
            DESCRIPTION
                "This object indicates the work state of the PW APS."
            ::= { hwPwApsEntry 5 }

       hwPwApsProtectState OBJECT-TYPE
            SYNTAX INTEGER
                {
                nondefect(1),
                defect(2),
                defectsd(3),
                unknown(255)
                }
            MAX-ACCESS read-only
            STATUS current
            DESCRIPTION
                "This object indicates the protect state of the PW APS."
            ::= { hwPwApsEntry 6 }

--
-- L2VPN PW APS Trap Definitions
-- 
        -- 1.3.6.1.4.1.2011.5.25.119.10.2
        hwL2vpnPwApsTraps OBJECT IDENTIFIER ::= { hwL2vpnPwAps 2 }

        -- 1.3.6.1.4.1.2011.5.25.119.10.2.1
        hwPwApsTypeMismatch NOTIFICATION-TYPE
            OBJECTS { hwPwApsId, hwPWInterfaceIndex }
            STATUS current
            DESCRIPTION 
                "APS reported an alarm about the mismatch of the protection type."
            ::= { hwL2vpnPwApsTraps 1 }

        -- 1.3.6.1.4.1.2011.5.25.119.10.2.2
        hwPwApsTypeMismatchClear NOTIFICATION-TYPE
            OBJECTS { hwPwApsId, hwPWInterfaceIndex }
            STATUS current
            DESCRIPTION 
                "APS reported an alarm about the rectification of the mismatch of the protection type."
            ::= { hwL2vpnPwApsTraps 2 }

        -- 1.3.6.1.4.1.2011.5.25.119.10.2.3
        hwPwApsPathMismatch  NOTIFICATION-TYPE
            OBJECTS { hwPwApsId, hwPWInterfaceIndex }
            STATUS current
            DESCRIPTION 
                "APS reported an alarm about the mismatch of the working and protection paths."
            ::= { hwL2vpnPwApsTraps 3 }

        -- 1.3.6.1.4.1.2011.5.25.119.10.2.4
        hwPwApsPathMismatchClear NOTIFICATION-TYPE
            OBJECTS { hwPwApsId, hwPWInterfaceIndex }
            STATUS current
            DESCRIPTION 
                "APS reported an alarm about the rectification of the mismatch of the working and protection paths."
            ::= { hwL2vpnPwApsTraps 4 }

        -- 1.3.6.1.4.1.2011.5.25.119.10.2.5
        hwPwApsSwitchFail  NOTIFICATION-TYPE
            OBJECTS { hwPwApsId, hwPWInterfaceIndex }
            STATUS current
            DESCRIPTION 
                "APS reported an alarm about the inconsistent switching results on the local and remote ends."
            ::= { hwL2vpnPwApsTraps 5 }

        -- 1.3.6.1.4.1.2011.5.25.119.10.2.6
        hwPwApsSwitchFailClear NOTIFICATION-TYPE
            OBJECTS { hwPwApsId, hwPWInterfaceIndex }
            STATUS current
            DESCRIPTION 
                "APS reported an alarm about the rectification of the inconsistency in switching results on the local and remote ends."
            ::= { hwL2vpnPwApsTraps 6 }

        -- 1.3.6.1.4.1.2011.5.25.119.10.2.7
        hwPwApsLost  NOTIFICATION-TYPE
            OBJECTS { hwPwApsId, hwPWInterfaceIndex }
            STATUS current
            DESCRIPTION 
                "APS reported a packet lost alarm."
            ::= { hwL2vpnPwApsTraps 7 }

        -- 1.3.6.1.4.1.2011.5.25.119.10.2.8
        hwPwApsLostClear NOTIFICATION-TYPE
            OBJECTS { hwPwApsId, hwPWInterfaceIndex }
            STATUS current
            DESCRIPTION 
                "APS reported the clearing of the packet loss alarm."
            ::= { hwL2vpnPwApsTraps 8 }

        -- 1.3.6.1.4.1.2011.5.25.119.10.2.9
        hwPwApsIdMismatch  NOTIFICATION-TYPE
            OBJECTS { hwPwApsId, hwPWInterfaceIndex }
            STATUS current
            DESCRIPTION 
                "APS reported an ID mismatch alarm."
            ::= { hwL2vpnPwApsTraps 9 }

        -- 1.3.6.1.4.1.2011.5.25.119.10.2.10
        hwPwApsIdMismatchClear NOTIFICATION-TYPE
            OBJECTS { hwPwApsId, hwPWInterfaceIndex }
            STATUS current
            DESCRIPTION 
                "APS reported the clearing of the ID mismatch alarm."
            ::= { hwL2vpnPwApsTraps 10 }

        -- 1.3.6.1.4.1.2011.5.25.119.10.2.11
        hwPwApsBypassPwMismatch  NOTIFICATION-TYPE
            OBJECTS { hwPwApsId, hwPWInterfaceIndex }
            STATUS current
            DESCRIPTION 
                "APS reported a bypass mismatch alarm."
            ::= { hwL2vpnPwApsTraps 11 }

        -- 1.3.6.1.4.1.2011.5.25.119.10.2.12
        hwPwApsBypssPwMismatchClear NOTIFICATION-TYPE
            OBJECTS { hwPwApsId, hwPWInterfaceIndex }
            STATUS current
            DESCRIPTION 
                "APS reported the clearing of the bypass mismatch alarm."
            ::= { hwL2vpnPwApsTraps 12 }

        -- 1.3.6.1.4.1.2011.5.25.119.10.2.13
        hwPwApsSwitchEvent NOTIFICATION-TYPE
            OBJECTS { hwPwApsRole, hwPwApsRequestResult, hwPwApsState, hwPwApsWorkState, 
                      hwPwApsProtectState }
            STATUS current
            DESCRIPTION 
                "APS reported the event of switch."
            ::= { hwL2vpnPwApsTraps 13 }

        -- 1.3.6.1.4.1.2011.5.25.119.10.2.14
        hwPwApsOutAge  NOTIFICATION-TYPE
            OBJECTS { hwPwApsId, hwPWInterfaceIndex }
            STATUS current
            DESCRIPTION 
                "APS reported a PW out age alarm."
            ::= { hwL2vpnPwApsTraps 14 }
        -- 1.3.6.1.4.1.2011.5.25.119.10.2.15
        hwPwApsOutAgeClear NOTIFICATION-TYPE
            OBJECTS { hwPwApsId, hwPWInterfaceIndex }
            STATUS current
            DESCRIPTION 
                "APS reported the clearing of the PW out age alarm."
            ::= { hwL2vpnPwApsTraps 15 }

        -- 1.3.6.1.4.1.2011.5.25.119.10.2.16
        hwPwApsDegraded  NOTIFICATION-TYPE
            OBJECTS { hwPwApsId, hwPWInterfaceIndex }
            STATUS current
            DESCRIPTION 
                "APS reported a PW degraded alarm."
            ::= { hwL2vpnPwApsTraps 16 }
        -- 1.3.6.1.4.1.2011.5.25.119.10.2.17
        hwPwApsDegradedClear NOTIFICATION-TYPE
            OBJECTS { hwPwApsId, hwPWInterfaceIndex }
            STATUS current
            DESCRIPTION 
                "APS reported the clearing of the PW degraded alarm."
            ::= { hwL2vpnPwApsTraps 17 }

-- the mib object of hwL2vpnPwApsScalarsObject is reserved
-- L2VPN PW APS Scalars Object Definitions
--
           hwL2vpnPwApsScalarsObject OBJECT IDENTIFIER ::= { hwL2vpnPwAps 3 }

--    Conformance information
--

                -- 1.3.6.1.4.1.2011.5.25.119.10.3
                hwPwApsMIBConformance OBJECT IDENTIFIER ::= { hwL2vpnPwAps 4 }


                -- 1.3.6.1.4.1.2011.5.25.119.10.3.1
                hwPwApsMIBCompliances OBJECT IDENTIFIER ::= { hwPwApsMIBConformance 1 }


                -- 1.3.6.1.4.1.2011.5.25.119.10.3.1.1
                hwPwApsMIBCompliance MODULE-COMPLIANCE
                        STATUS current
                        DESCRIPTION 
                                "The compliance statement for systems supporting the HUAWEI-L2VPN-PW-APS-MIB."
                        MODULE -- this module
                                MANDATORY-GROUPS { hwPwApsGroup, hwPwApsNotificationGroup }
                        ::= { hwPwApsMIBCompliances 1 }


                -- 1.3.6.1.4.1.2011.5.25.119.10.3.2
                hwPwApsMIBGroups OBJECT IDENTIFIER ::= { hwPwApsMIBConformance 2 }


                -- 1.3.6.1.4.1.2011.5.25.119.10.3.2.1
                hwPwApsGroup OBJECT-GROUP
                        OBJECTS { hwPwApsId, hwPwApsRole, hwPwApsRequestResult, hwPwApsState, 
                                  hwPwApsWorkState, hwPwApsProtectState }
                        STATUS current
                        DESCRIPTION 
                                "The PW APS group."
                        ::= { hwPwApsMIBGroups 1 }


                -- 1.3.6.1.4.1.2011.5.25.119.10.3.2.2
                hwPwApsNotificationGroup NOTIFICATION-GROUP
                        NOTIFICATIONS { hwPwApsTypeMismatch, hwPwApsTypeMismatchClear, hwPwApsPathMismatch, hwPwApsPathMismatchClear, 
                                        hwPwApsSwitchFail, hwPwApsSwitchFailClear, hwPwApsLost, hwPwApsLostClear ,
                                        hwPwApsIdMismatch, hwPwApsIdMismatchClear, hwPwApsBypassPwMismatch, hwPwApsBypssPwMismatchClear,
                                        hwPwApsSwitchEvent, hwPwApsOutAge, hwPwApsOutAgeClear, hwPwApsDegraded, hwPwApsDegradedClear }
                        STATUS current
                        DESCRIPTION 
                                "The PW APS Notification group."
                        ::= { hwPwApsMIBGroups 2 }

    END

--
-- HUAWEI-L2VPN-PW-APS-MIB.mib
--
