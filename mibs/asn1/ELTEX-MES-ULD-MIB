-- -----------------------------------------------------------------------------
-- MIB NAME : Eltex MES ULD
-- FILE NAME: EULD.mib
-- DATE     : 2013/01/28
-- VERSION  : 1.00
-- PURPOSE  : MIB structure of Unidirectional Link Detection
-- -----------------------------------------------------------------------------


ELTEX-MES-ULD-MIB DEFINITIONS ::= BEGIN

        IMPORTS
            MODULE-IDENTITY,OBJECT-TYPE     FROM SNMPv2-SMI
            ifIndex                         FROM IF-MIB
            eltMesMng                       FROM ELTEX-MES
 			TruthValue                      FROM SNMPv2-TC;

        eltMesULDMIB MODULE-IDENTITY
            LAST-UPDATED "201511190000Z"	-- November 19, 2015
            ORGANIZATION "Eltex Ltd."
            CONTACT-INFO
                "http://www.eltex.nsk.ru"
            DESCRIPTION
                "The unidirectioanl link detection module MIB."

            REVISION	 "201511190000Z"	-- November 19, 2015
            DESCRIPTION
                "Deprecate all objects in this module."
           ::= { eltMesMng 87}

eltMesULDNotifications OBJECT IDENTIFIER ::= { eltMesULDMIB 0 }
eltMesULDMgmt OBJECT IDENTIFIER ::= {eltMesULDMIB 1}

-- -----------------------------------------------------------------------------
-- eltMesULDMgmt
-- -----------------------------------------------------------------------------

                eltULDTable OBJECT-TYPE
                    SYNTAX  SEQUENCE OF EltULDEntry
                    MAX-ACCESS not-accessible
                    STATUS deprecated
                    DESCRIPTION
                        "The management information of the unidirectional link detection."
                    ::= { eltMesULDMgmt 1 }

                eltULDEntry OBJECT-TYPE
                        SYNTAX EltULDEntry
                        MAX-ACCESS not-accessible
                        STATUS deprecated
                        DESCRIPTION
                            "A list of information contained in eltULDTable."
                        INDEX { ifIndex }
                        ::= { eltULDTable 1 }

                EltULDEntry ::=
                        SEQUENCE {
                                eltULDAdminState
                                        INTEGER,
                                eltULDOperStatus
                                        INTEGER,
                                   eltULDMode
                                        INTEGER,
                                   eltULDDiscoveryTime
                                        INTEGER,
                                   eltULDIsAggressive
                                        TruthValue,
                                   eltULDLinkStatus
                                        INTEGER
                        }


                eltULDAdminState OBJECT-TYPE
                        SYNTAX INTEGER
                        {
                                 enabled(1),
                                disabled(2)
                        }
                        MAX-ACCESS  read-write
                        STATUS      deprecated
                        DESCRIPTION
                                "This object indicates the unidirectional link detection configuration status."
                        DEFVAL   {disabled}
                        ::= { eltULDEntry 1 }

                eltULDOperStatus OBJECT-TYPE
                        SYNTAX INTEGER
                        {
                                 enabled(1),
                                disabled(2)
                        }
                        MAX-ACCESS  read-only
                        STATUS      deprecated
                        DESCRIPTION
                                "This object is determined by local and remote port supporting OAM and unidirectional detection.
                                If both local and remote port support OAM and unidirectional detection, it is enabled(1),else it
                                is disabled(2)."
                        ::= { eltULDEntry 2 }

                eltULDMode OBJECT-TYPE
                        SYNTAX  INTEGER
                        {
                                log(1),
                                err-disable(2)
                        }
                        MAX-ACCESS   read-write
                        STATUS      deprecated
                        DESCRIPTION
                                 "This object indicates the mode for unidirectional link detection.
                                  shutdown: if any unidirectional link is detected, disable the port and log an event.
                                  normal: only log an event when a unidirectional link is detected."
                        DEFVAL   {log}
                        ::= { eltULDEntry 3 }

                eltULDDiscoveryTime OBJECT-TYPE
                        SYNTAX INTEGER(5..300)
                        MAX-ACCESS   read-write
                        STATUS      deprecated
                        DESCRIPTION
                                 "This object indicates the neighbor discovery time for unidirectional link detection.
                                 If the discovery time ends, the unidirectional link detection starts."
                        DEFVAL   { 5 }
                        ::= { eltULDEntry 4 }

                eltULDIsAggressive OBJECT-TYPE
                         SYNTAX  TruthValue
                         MAX-ACCESS   read-write
                         STATUS      deprecated
                         DESCRIPTION
                                  "This object indicates the mode for
						 		   unidirectional link detection protocol.
                                   If true then port is considered to be
                                   UNIDIRECTIONAL if there is no answer
                                   from remote side during discovery
                                   timeout. If false then port is considered to be
                                   UNKNOWN."
                         DEFVAL   { false }
                         ::= { eltULDEntry 5 }

                eltULDLinkStatus OBJECT-TYPE
                        SYNTAX      INTEGER
                        {
                                unknown(1),
                                unidirectional(2),
                                bidirectional(3),
                                tx-rx-loop(4),
                                neighbor-mismatch(5)
                        }
                        MAX-ACCESS  read-only
                        STATUS      deprecated
                        DESCRIPTION
                                "This object indicates the link status, which is a result of unidirectional link detection."
                        ::= {eltULDEntry 6 }

-- -----------------------------------------------------------------------------
-- eltMesULDNotifications
-- -----------------------------------------------------------------------------

   eltULDLinkStatusChanged NOTIFICATION-TYPE
     OBJECTS { ifIndex,
               eltULDLinkStatus
             }
     STATUS  deprecated
     DESCRIPTION
       "A eltULDLinkStatusChanged notification is sent when a local
       link status has been changed. This event should not be sent
       more then one per second."
    ::= { eltMesULDNotifications 1 }
END
