ZYXEL-MAC-BASED-VLAN-MIB DEFINITIONS ::= BEGIN

    IMPORTS
	enterprises		FROM RFC1155-SMI                                
	
	OBJECT-TYPE
		FROM SNMPv2-SMI			-- RFC2578	
	RowStatus, MacAddress
		FROM SNMPv2-TC			-- RFC2579
	DisplayString                                          
	  	FROM RFC1213-MIB
	esMgmt			
		FROM ZYXEL-ES-SMI;
        
    zyxelMacBasedVlan MODULE-IDENTITY
        LAST-UPDATED	"201402250000Z" 
        ORGANIZATION "Enterprise Solution ZyXEL"     
        CONTACT-INFO
            ""	   
        DESCRIPTION
            "study"
        ::= { esMgmt 99 }

    -- zyxelMacBasedVlan OIDs
    zyxelMacBasedVlanSetup	OBJECT IDENTIFIER ::= { zyxelMacBasedVlan 1 }

    zyxelMacBasedVlanStatus	OBJECT IDENTIFIER ::= { zyxelMacBasedVlan 2 }

    zyMacBasedVlanMaxNumberOfVlans OBJECT-TYPE
        SYNTAX		INTEGER
        MAX-ACCESS	read-only
        STATUS		current
        DESCRIPTION
            "Maximum binding number of MAC-based VLAN"
        ::= { zyxelMacBasedVlanSetup 1 }


    zyxelMacBasedVlanBindingTable OBJECT-TYPE
        SYNTAX		SEQUENCE OF ZyxelMacBasedVlanBindingEntry
        MAX-ACCESS	not-accessible
        STATUS		current
        DESCRIPTION
            "The table of MAC-based VLAN configuration."
        ::= { zyxelMacBasedVlanSetup 2 }

    zyxelMacBasedVlanBindingEntry OBJECT-TYPE
        SYNTAX		ZyxelMacBasedVlanBindingEntry
        MAX-ACCESS	not-accessible
        STATUS		current
        DESCRIPTION
            "An entry contains MAC-based VLAN configuration. "
        INDEX          	{ zyMacBasedVlanBindingSourceMac}            
        ::= { zyxelMacBasedVlanBindingTable 1 }

    ZyxelMacBasedVlanBindingEntry ::=
           SEQUENCE {
        	zyMacBasedVlanBindingSourceMac		MacAddress,
        	zyMacBasedVlanBindingName			DisplayString,           
         	zyMacBasedVlanBindingVlan	        INTEGER,
        	zyMacBasedVlanBindingPriority		INTEGER,
            zyMacBasedVlanBindingRowStatus      RowStatus
           }        
        
    zyMacBasedVlanBindingSourceMac OBJECT-TYPE
        SYNTAX		MacAddress
        MAX-ACCESS	not-accessible
        STATUS		current
        DESCRIPTION
            "source MAC address of binding"
        ::= { zyxelMacBasedVlanBindingEntry 1 }

    zyMacBasedVlanBindingName OBJECT-TYPE
        SYNTAX		OCTET STRING
        MAX-ACCESS	read-write
        STATUS		current
        DESCRIPTION
            "Set a name of the MAC-based VLAN binding"
        ::= { zyxelMacBasedVlanBindingEntry 2 }

    zyMacBasedVlanBindingVlan OBJECT-TYPE
        SYNTAX		INTEGER (1..4094)
        MAX-ACCESS	read-write
        STATUS		current
        DESCRIPTION
            "Set a vid for untagged frame forwarding"
        ::= { zyxelMacBasedVlanBindingEntry 3 }

    zyMacBasedVlanBindingPriority OBJECT-TYPE
        SYNTAX		INTEGER (0..7)
        MAX-ACCESS	read-write
        STATUS		current
        DESCRIPTION
            "Set a priority to apply to the vlan"
        ::= { zyxelMacBasedVlanBindingEntry 4 }

    zyMacBasedVlanBindingRowStatus OBJECT-TYPE
        SYNTAX		RowStatus
        MAX-ACCESS	read-create
        STATUS		current
        DESCRIPTION
            "This object allows entries to be created and deleted from the MAC."
        ::= { zyxelMacBasedVlanBindingEntry 5 }
END
