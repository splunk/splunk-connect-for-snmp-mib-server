-- File Name : PACKETPOWER-EG4-MIB
-- Date      : Thu Feb 04 03:34:15 GMT 2016
-- Author    : WebNMS Agent Toolkit C Edition - MibEditor 6



PACKETPOWER-EG4-MIB     DEFINITIONS ::= BEGIN
        IMPORTS
                DateAndTime, DisplayString, RowStatus, TruthValue, DisplayString
                        FROM SNMPv2-TC
                MODULE-IDENTITY, OBJECT-TYPE, NOTIFICATION-TYPE, enterprises, Integer32, Counter32, IpAddress
                        FROM SNMPv2-SMI;

        org     OBJECT IDENTIFIER
                ::=  {  iso  3  }

        dod     OBJECT IDENTIFIER
                ::=  {  org  6  }

        internet        OBJECT IDENTIFIER
                ::=  {  dod  1  }

        private OBJECT IDENTIFIER
                ::=  {  internet  4  }

        enterprises     OBJECT IDENTIFIER
                ::=  {  private  1  }

        packetPower     OBJECT IDENTIFIER
                ::=  {  enterprises  33688  }

        eg4     OBJECT IDENTIFIER
                ::=  {  packetPower  4  }

        readingsTable   OBJECT-TYPE
                SYNTAX          SEQUENCE  OF  ReadingsEntry
                MAX-ACCESS      not-accessible
                STATUS          current
                DESCRIPTION     "Table of most recent, time-stamped readings on all channels monitored by each node."
                ::=  { eg4  1 }

        readingsEntry   OBJECT-TYPE
                SYNTAX          ReadingsEntry
                MAX-ACCESS      not-accessible
                STATUS          current
                DESCRIPTION     "Time-stamped reading corresponding to a physical value most recently reported on a given measurement channel."
                INDEX           {  reNodeId1, reNodeId2, reNodeId3, reNodeId4, channelId  }
                ::=  { readingsTable 1 }

        ReadingsEntry  ::=  SEQUENCE {
                reNodeId1  Integer32,
                reNodeId2  Integer32,
                reNodeId3  Integer32,
                reNodeId4  Integer32,
                channelId  INTEGER,
                reNodeIdHex  DisplayString,
                reNodeIdString  DisplayString,
                reChannelName  DisplayString,
                reTime  DateAndTime,
                reUnixTime  Integer32,
                reIso8601Time  DisplayString,
                reValue  Integer32,
                reUnits  DisplayString
                }


        reNodeId1       OBJECT-TYPE
                SYNTAX                  Integer32  ( 0 .. 65536  )
                MAX-ACCESS              not-accessible
                STATUS                  current
                DESCRIPTION             "Node identifier, part 1 of 4 (16 bits, bits 63-48 of the id - part AAAA of AAAA-BBBB-CCCC-DDDD)."
                ::=  {  readingsEntry  1  }


        reNodeId2       OBJECT-TYPE
                SYNTAX                  Integer32  ( 0 .. 65536  )
                MAX-ACCESS              not-accessible
                STATUS                  current
                DESCRIPTION             "Node identifier, part 2 of 4 (16 bits, bits 47-32 of the id - part BBBB of AAAA-BBBB-CCCC-DDDD)."
                ::=  {  readingsEntry  2  }


        reNodeId3       OBJECT-TYPE
                SYNTAX                  Integer32  ( 0 .. 65536  )
                MAX-ACCESS              not-accessible
                STATUS                  current
                DESCRIPTION             "Node identifier, part 3 of 4 (16 bits, bits 31-16 of the id - part CCCC of AAAA-BBBB-CCCC-DDDD)."
                ::=  {  readingsEntry  3  }


        reNodeId4       OBJECT-TYPE
                SYNTAX                  Integer32  ( 0 .. 65536  )
                MAX-ACCESS              not-accessible
                STATUS                  current
                DESCRIPTION             "Node identifier, part 4 of 4 (16 bits, bits 15-0 of the id - part DDDD of AAAA-BBBB-CCCC-DDDD)."
                ::=  {  readingsEntry  4  }


        channelId       OBJECT-TYPE
                SYNTAX                  INTEGER  { current ( 2 ) , voltage ( 1 ) , power ( 3 ) , energy ( 4 ) , frequency ( 5 ) , temperature ( 6 ) , humidity ( 7 ) , va ( 8 ) , vdd ( 9 ) , battery ( 10 ) , pressure ( 11 ) , contact ( 12 ) , contactcount ( 13 ) }
                MAX-ACCESS              not-accessible
                STATUS                  current
                DESCRIPTION             "Channel ID, indicating the type of measurement reported."
                ::=  {  readingsEntry  5  }


        reNodeIdHex     OBJECT-TYPE
                SYNTAX                  DisplayString  ( SIZE ( 0 .. 16  ) )
                MAX-ACCESS              read-only
                STATUS                  current
                DESCRIPTION             "Node ID number as as 16-character uppercase hexadecimal string."
                ::=  {  readingsEntry  6  }


        reNodeIdString  OBJECT-TYPE
                SYNTAX                  DisplayString  ( SIZE ( 0 .. 19  ) )
                MAX-ACCESS              read-only
                STATUS                  current
                DESCRIPTION             "Node identifier (hex), formatted XXXX-XXXX-XXXX-XXXX (matches all Packet Power product labels)."
                ::=  {  readingsEntry  7  }


        reChannelName   OBJECT-TYPE
                SYNTAX                  DisplayString  ( SIZE ( 0 .. 255  ) )
                MAX-ACCESS              read-only
                STATUS                  current
                DESCRIPTION             "Channel name, indicating channel type and instance (e.g.VoltageA)."
                ::=  {  readingsEntry  8  }


        reTime  OBJECT-TYPE
                SYNTAX                  DateAndTime
                MAX-ACCESS              read-only
                STATUS                  current
                DESCRIPTION             "Timestamp of the reading."
                ::=  {  readingsEntry  9  }


        reUnixTime      OBJECT-TYPE
                SYNTAX                  Integer32  ( -2147483648 .. 2147483647  )
                MAX-ACCESS              read-only
                STATUS                  current
                DESCRIPTION             "Reading timestamp, UNIX epoch format."
                ::=  {  readingsEntry  10  }


        reIso8601Time   OBJECT-TYPE
                SYNTAX                  DisplayString  ( SIZE ( 0 .. 255  ) )
                MAX-ACCESS              read-only
                STATUS                  current
                DESCRIPTION             "Reading timestamp, ISO8601 format."
                ::=  {  readingsEntry  11  }


        reValue OBJECT-TYPE
                SYNTAX                  Integer32  ( -2147483648 .. 2147483647  )
                MAX-ACCESS              read-only
                STATUS                  current
                DESCRIPTION             "Reading value at timestamp."
                ::=  {  readingsEntry  12  }


        reUnits OBJECT-TYPE
                SYNTAX                  DisplayString  ( SIZE ( 0 .. 255  ) )
                MAX-ACCESS              read-only
                STATUS                  current
                DESCRIPTION             "Units of measure."
                ::=  {  readingsEntry  13  }

        nodesTable      OBJECT-TYPE
                SYNTAX          SEQUENCE  OF  NodesEntry
                MAX-ACCESS      not-accessible
                STATUS          current
                DESCRIPTION     "Table of all active nodes."
                ::=  { eg4  2 }

        nodesEntry      OBJECT-TYPE
                SYNTAX          NodesEntry
                MAX-ACCESS      not-accessible
                STATUS          current
                DESCRIPTION     "Node status, including most recent activity time and radio link quality."
                INDEX           {  ntNodeId1, ntNodeId2, ntNodeId3, ntNodeId4  }
                ::=  { nodesTable 1 }

        NodesEntry  ::=  SEQUENCE {
                ntNodeId1  Integer32,
                ntNodeId2  Integer32,
                ntNodeId3  Integer32,
                ntNodeId4  Integer32,
                ntNodeIdHex  DisplayString,
                ntNodeIdString  DisplayString,
                ntTime  DateAndTime,
                ntUnixTime  Integer32,
                ntIso8601Time  DisplayString,
                ntLinkQuality  Integer32
                }


        ntNodeId1       OBJECT-TYPE
                SYNTAX                  Integer32  ( 0 .. 65532  )
                MAX-ACCESS              not-accessible
                STATUS                  current
                DESCRIPTION             "Node identifier, part 1 of 4 (16 bits, bits 63-48 of the id - part AAAA of AAAA-BBBB-CCCC-DDDD)."
                ::=  {  nodesEntry  1  }


        ntNodeId2       OBJECT-TYPE
                SYNTAX                  Integer32  ( 0 .. 65532  )
                MAX-ACCESS              not-accessible
                STATUS                  current
                DESCRIPTION             "Node identifier, part 2 of 4 (16 bits, bits 47-32 of the id - part BBBB of AAAA-BBBB-CCCC-DDDD)."
                ::=  {  nodesEntry  2  }


        ntNodeId3       OBJECT-TYPE
                SYNTAX                  Integer32  ( 0 .. 65532  )
                MAX-ACCESS              not-accessible
                STATUS                  current
                DESCRIPTION             "Node identifier, part 3 of 4 (16 bits, bits 31-16 of the id - part CCCC of AAAA-BBBB-CCCC-DDDD)."
                ::=  {  nodesEntry  3  }


        ntNodeId4       OBJECT-TYPE
                SYNTAX                  Integer32  ( 0 .. 65532  )
                MAX-ACCESS              not-accessible
                STATUS                  current
                DESCRIPTION             "Node identifier, part 4 of 4 (16 bits, bits 15-0 of the id - part DDDD of AAAA-BBBB-CCCC-DDDD)."
                ::=  {  nodesEntry  4  }


        ntNodeIdHex     OBJECT-TYPE
                SYNTAX                  DisplayString  ( SIZE ( 0 .. 16  ) )
                MAX-ACCESS              read-only
                STATUS                  current
                DESCRIPTION             "Node ID number as as 16-character uppercase hexadecimal string."
                ::=  {  nodesEntry  5  }


        ntNodeIdString  OBJECT-TYPE
                SYNTAX                  DisplayString  ( SIZE ( 0 .. 19  ) )
                MAX-ACCESS              read-only
                STATUS                  current
                DESCRIPTION             "Node identifier (hex), formatted XXXX-XXXX-XXXX-XXXX (matches all Packet Power product labels)."
                ::=  {  nodesEntry  6  }


        ntTime  OBJECT-TYPE
                SYNTAX                  DateAndTime
                MAX-ACCESS              read-only
                STATUS                  current
                DESCRIPTION             "Timestamp of the most recent reading from the node."
                ::=  {  nodesEntry  7  }


        ntUnixTime      OBJECT-TYPE
                SYNTAX                  Integer32  ( -2147483648 .. 2147483647  )
                MAX-ACCESS              read-only
                STATUS                  current
                DESCRIPTION             "Timestamp of the most recent reading from the node, UNIX epoch format."
                ::=  {  nodesEntry  8  }


        ntIso8601Time   OBJECT-TYPE
                SYNTAX                  DisplayString  ( SIZE ( 0 .. 255  ) )
                MAX-ACCESS              read-only
                STATUS                  current
                DESCRIPTION             "Timestamp of the most recent reading from the node, ISO8601 format."
                ::=  {  nodesEntry  9  }


        ntLinkQuality   OBJECT-TYPE
                SYNTAX                  Integer32  ( 0 .. 100  )
                MAX-ACCESS              read-only
                STATUS                  current
                DESCRIPTION             "Radio link quality 0..100"
                ::=  {  nodesEntry  10  }

END
