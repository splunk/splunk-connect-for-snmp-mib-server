--
-- FD-TRAP-MIB.my
-- MIB generated by MG-SOFT Visual MIB Builder Version 3.0 Build 253
-- Wednesday, June 15, 2011 at 18:07:48
--

--  FD-TRAP-MIB.mib
-- MIB generated by MG-SOFT Visual MIB Builder Version 3.0 Build 253
-- Thursday, May 27, 2010 at 18:38:56
-- 

	FD-TRAP-MIB DEFINITIONS ::= BEGIN
 
		IMPORTS
			epon			
				FROM EPON-EOC-MIB			
			linkIdExhaust, onuIdExhaust, linkOnLineStatus			
				FROM FD-OLT-MIB			
			onuOnLineStatus, uniPortLink, uniPortRstpState			
				FROM FD-ONU-MIB			
			swSniPortTrafficChangeVal, oltTrafficChangeVal, onuTrafficChangeVal			
				FROM FD-PERFORMANCE-MIB			
			sfpPlugStauts, swPortLinkState			
				FROM FD-SWITCH-MIB			
			powerStatusBit, fanStatusBit, ponCardRunningStatus, nonAuthOnuMac			
				FROM FD-SYSTEM-MIB			
			MODULE-COMPLIANCE, NOTIFICATION-GROUP			
				FROM SNMPv2-CONF			
			MODULE-IDENTITY, NOTIFICATION-TYPE			
				FROM SNMPv2-SMI;
	
	
		eponTraps MODULE-IDENTITY 
			LAST-UPDATED "201005271056Z"		-- May 27, 2010 at 10:56 GMT
			ORGANIZATION 
				"epon eoc factory."
			CONTACT-INFO 
				""
			DESCRIPTION 
				"Trap mib module"
			::= { epon 6 }
		
	
	
--
-- Node definitions
--
	
		-- 1.3.6.1.4.1.34592.1.3.6.0
		eponTrapsPrefix OBJECT IDENTIFIER ::= { eponTraps 0 }
		
		-- 1.3.6.1.4.1.34592.1.3.6.0.1
		sniSFPStatusChange NOTIFICATION-TYPE
			OBJECTS { sfpPlugStauts }
			STATUS current
			DESCRIPTION 
				"Description."
			::= { eponTrapsPrefix 1 }
		
		-- 1.3.6.1.4.1.34592.1.3.6.0.2
		sniPortLinkChange NOTIFICATION-TYPE
			OBJECTS { swPortLinkState }
			STATUS current
			DESCRIPTION 
				"Description."
			::= { eponTrapsPrefix 2 }
		
		-- 1.3.6.1.4.1.34592.1.3.6.0.3
		powerStatusChange NOTIFICATION-TYPE
			OBJECTS { powerStatusBit }
			STATUS current
			DESCRIPTION 
				"Description."
			::= { eponTrapsPrefix 3 }
		
		-- 1.3.6.1.4.1.34592.1.3.6.0.4
		fanStatusChange NOTIFICATION-TYPE
			OBJECTS { fanStatusBit }
			STATUS current
			DESCRIPTION 
				"Description."
			::= { eponTrapsPrefix 4 }
		
		-- 1.3.6.1.4.1.34592.1.3.6.0.5
		ponRunningStatusChange NOTIFICATION-TYPE
			OBJECTS { ponCardRunningStatus }
			STATUS current
			DESCRIPTION 
				"Description."
			::= { eponTrapsPrefix 5 }
		
		-- 1.3.6.1.4.1.34592.1.3.6.0.6
		onuLinkStatusChange NOTIFICATION-TYPE
			OBJECTS { linkOnLineStatus }
			STATUS current
			DESCRIPTION 
				"Description."
			::= { eponTrapsPrefix 6 }
		
		-- 1.3.6.1.4.1.34592.1.3.6.0.7
		onuOnlineStatusChange NOTIFICATION-TYPE
			OBJECTS { onuOnLineStatus }
			STATUS current
			DESCRIPTION 
				"Description."
			::= { eponTrapsPrefix 7 }
		
		-- 1.3.6.1.4.1.34592.1.3.6.0.8
		onuPortStatusChange NOTIFICATION-TYPE
			OBJECTS { uniPortLink }
			STATUS current
			DESCRIPTION 
				"Description."
			::= { eponTrapsPrefix 8 }
		
		-- 1.3.6.1.4.1.34592.1.3.6.0.9
		swSniPortTrafficChange NOTIFICATION-TYPE
			OBJECTS { swSniPortTrafficChangeVal }
			STATUS current
			DESCRIPTION 
				"Description."
			::= { eponTrapsPrefix 9 }
		
		-- 1.3.6.1.4.1.34592.1.3.6.0.10
		oltTrafficChange NOTIFICATION-TYPE
			OBJECTS { oltTrafficChangeVal }
			STATUS current
			DESCRIPTION 
				"Description."
			::= { eponTrapsPrefix 10 }
		
		-- 1.3.6.1.4.1.34592.1.3.6.0.11
		onuTrafficChange NOTIFICATION-TYPE
			OBJECTS { onuTrafficChangeVal }
			STATUS current
			DESCRIPTION 
				"Description."
			::= { eponTrapsPrefix 11 }
		
		-- 1.3.6.1.4.1.34592.1.3.6.0.12
		linkIdResourceExhaust NOTIFICATION-TYPE
			OBJECTS { linkIdExhaust }
			STATUS current
			DESCRIPTION 
				"Description."
			::= { eponTrapsPrefix 12 }
		
		-- 1.3.6.1.4.1.34592.1.3.6.0.13
		onuIdResourceExhaust NOTIFICATION-TYPE
			OBJECTS { onuIdExhaust }
			STATUS current
			DESCRIPTION 
				"Description."
			::= { eponTrapsPrefix 13 }
		
		-- 1.3.6.1.4.1.34592.1.3.6.0.14
		illegalRegisterAlarm NOTIFICATION-TYPE
			OBJECTS { nonAuthOnuMac }
			STATUS current
			DESCRIPTION 
				"Description."
			::= { eponTrapsPrefix 14 }
		
		-- 1.3.6.1.4.1.34592.1.3.6.0.15
		onuPortRstpStateChange NOTIFICATION-TYPE
			OBJECTS { uniPortRstpState }
			STATUS current
			DESCRIPTION 
				"Description."
			::= { eponTrapsPrefix 15 }
		
		-- 1.3.6.1.4.1.34592.1.3.6.1
		fdTrapConformance OBJECT IDENTIFIER ::= { eponTraps 1 }
		
		-- 1.3.6.1.4.1.34592.1.3.6.1.1
		fdTrapGroups OBJECT IDENTIFIER ::= { fdTrapConformance 1 }
		
		-- 1.3.6.1.4.1.34592.1.3.6.1.1.1
		fdTrapGroup NOTIFICATION-GROUP
			NOTIFICATIONS { sniSFPStatusChange, sniPortLinkChange, powerStatusChange, fanStatusChange, ponRunningStatusChange, 
				onuLinkStatusChange, onuOnlineStatusChange, onuPortStatusChange, swSniPortTrafficChange, oltTrafficChange, 
				onuTrafficChange, onuPortRstpStateChange, illegalRegisterAlarm, linkIdResourceExhaust, onuIdResourceExhaust
				 }
			STATUS current
			DESCRIPTION 
				"A collection of objects providing notification management"
			::= { fdTrapGroups 1 }
		
		-- 1.3.6.1.4.1.34592.1.3.6.1.2
		fdTrapCompliances OBJECT IDENTIFIER ::= { fdTrapConformance 2 }
		
		-- 1.3.6.1.4.1.34592.1.3.6.1.2.1
		fdTrapCompliance MODULE-COMPLIANCE
			STATUS current
			DESCRIPTION 
				"The compliance statement"
			MODULE -- this module
				MANDATORY-GROUPS { fdTrapGroup }
			::= { fdTrapCompliances 1 }
		
	
	END

--
-- FD-TRAP-MIB.my
--
