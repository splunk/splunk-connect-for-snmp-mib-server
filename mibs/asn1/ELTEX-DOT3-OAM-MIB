ELTEX-DOT3-OAM-MIB DEFINITIONS ::= BEGIN

IMPORTS
	MODULE-IDENTITY, OBJECT-TYPE, Counter32, Unsigned32,
	 Integer32, Counter64, NOTIFICATION-TYPE
	 FROM SNMPv2-SMI
	 -- from [RFC2578]
	TEXTUAL-CONVENTION, MacAddress, TimeStamp, TruthValue

	 FROM SNMPv2-TC
	 -- from [RFC2579]
	ifIndex
	 FROM IF-MIB
	 -- from [RFC2863]
	MODULE-COMPLIANCE, OBJECT-GROUP
	 FROM SNMPv2-CONF

	PortList   FROM Q-BRIDGE-MIB

	eltexLtd  FROM ELTEX-SMI-ACTUAL;

eltexDot3OamMIB MODULE-IDENTITY
			LAST-UPDATED "201302220000Z"  -- Februrary 22,2013
			ORGANIZATION "Eltex Ent"
			CONTACT-INFO
					"www.eltex.nsk.ru"
   			DESCRIPTION "Initial version."
   			REVISION    "201302220000Z"  -- Februrary 22,2013
            DESCRIPTION
					"Initial revision."
	::= { eltexLtd 30 }

eltexDot3OamObjects    OBJECT IDENTIFIER ::= { eltexDot3OamMIB 1 }

eltexDot3OamClearStatistic OBJECT-TYPE
    SYNTAX      PortList
    MAX-ACCESS  read-write
    STATUS      current
    DESCRIPTION
        "Each bit that is set in this portList represent a port that
         its OAM statistic should be reset."
    ::= { eltexDot3OamObjects 7 }

END
