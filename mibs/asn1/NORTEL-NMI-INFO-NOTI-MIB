NORTEL-NMI-INFO-NOTI-MIB 

DEFINITIONS ::= BEGIN

   IMPORTS
       nortelNMInotificationsMIB,
       nortelNMIcurrentTxNotificationSequenceNum,
       nortelNMInotifyNeType,
       nortelNMInotifyNeName,
       nortelNMInotifyNeAdminState,
       nortelNMInotifyNeOperState,
       nortelNMInotifyNeUnknownStatus
           FROM  NORTEL-NMI-NOTIFICATIONS-MIB 
       nortelNMInotificationGroups
           FROM NORTEL-NMI-GROUPS-MIB
       NortelNMItimeStampDef 
           FROM NORTEL-NMI-TC-MIB

       NOTIFICATION-GROUP
           FROM SNMPv2-CONF
       DisplayString
           FROM SNMPv2-TC
       MODULE-IDENTITY, OBJECT-IDENTITY, 
       OBJECT-TYPE, NOTIFICATION-TYPE,
       Unsigned32
           FROM SNMPv2-SMI;


   nortelNMIinfoNotiMIB  MODULE-IDENTITY
       LAST-UPDATED "9907190000Z"
       ORGANIZATION "Nortel Networks"
       CONTACT-INFO
              "   Jingdong Liu

                Postal: Nortel Networks
                        P. O. Box 3511, Station C
                        Ottawa, Ontario
                        CANADA
                        K1Y 4H7

                Email:  jingdong@nortelnetworks.com"


       DESCRIPTION
               "This module contains the informational related
                notifications for the Nortel NMI."

       ::= { nortelNMInotificationsMIB 5 }

  -- all notification OIDs would be prefixed with a zero OID to 
  -- facilate snmp v1<->v2 conversion

  nortelNMIinfoNotiPrefix  OBJECT-IDENTITY
           STATUS         current
           DESCRIPTION
                  "This OID represents the prefix branch for all Nortel NMI 
                   informational Notifications.
                   The last but one sub identifier in the OID of 
                   any Notification must have the value zero to facilitate 
                   v2<-->v1 conversion." 
           ::=  {nortelNMIinfoNotiMIB  0 }
 

   nortelNMIinfoNotiVarbinds  OBJECT-IDENTITY
           STATUS         current
           DESCRIPTION
                  "This OID represents the branch which contains varbinds to 
                   informational management related notifications."
           ::=  {nortelNMIinfoNotiMIB  1 }



  -- The following variables belong to the accessible-for-notify clause and
  -- are defined here mainly to be included as varbinds to notifications.
  -- No other protocol operations will be supported for these

 
          nortelNMInotifyLogComponentId  OBJECT-TYPE
              SYNTAX  DisplayString 
              MAX-ACCESS  accessible-for-notify
              STATUS  current
              DESCRIPTION
                 "This variable represents the Distinguished Name (DN) 
                  (refer X.720) of the component object against which the 
                  particular log is generated. The entire component hierarchy 
                  should be presented in the category-value information
                  model to unambiguosly identify the specific component 
                  object instance."

              ::= { nortelNMIinfoNotiVarbinds  1 }


          nortelNMInotifyLogText  OBJECT-TYPE
              SYNTAX   DisplayString (SIZE(1..255)) 
              MAX-ACCESS  accessible-for-notify
              STATUS  current
              DESCRIPTION
                  "This variable provides the text for the log message."

              ::= { nortelNMIinfoNotiVarbinds  2 }


          nortelNMInotifyLogTimeStamp  OBJECT-TYPE
              SYNTAX   NortelNMItimeStampDef 
              MAX-ACCESS  accessible-for-notify
              STATUS  current
              DESCRIPTION
                 "This variable presents the relative timestamp of 
                  occurrence of the log.
                  NortelNMItimeStampDef textual convention is defined at the
                  NORTEL-NMI-TC-MIB."

              ::= { nortelNMIinfoNotiVarbinds  3 }

 
-- Informational Log Notification

          nortelNMIinfoNotification NOTIFICATION-TYPE
                          OBJECTS { nortelNMIcurrentTxNotificationSequenceNum,
                                    nortelNMInotifyLogComponentId,
                                    nortelNMInotifyLogText,
                                    nortelNMInotifyLogTimeStamp
                                  }
            STATUS  current
            DESCRIPTION
              "This notification indicates an informational log message.
               The varbinds include log context via the ComponentId field
               and other additional useful information."
     
          ::= { nortelNMIinfoNotiPrefix 301 }

-- Notification group definitions

    nortelNMIneLogNotificationsGroup NOTIFICATION-GROUP
           NOTIFICATIONS  { nortelNMIinfoNotification }
           STATUS   current
           DESCRIPTION
                " Nortel NMI NE informational log notification group."

           ::= { nortelNMInotificationGroups 5}


END
