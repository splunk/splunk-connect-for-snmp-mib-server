--
-- she-tssm-mib.mib
-- MIB generated by MG-SOFT Visual MIB Builder Version 6.0  Build 88
-- Wednesday, September 17, 2008 at 13:53:43
--

-- Start of ClearCase branch-information of current release:
-- she-tssm-mib.mib   /main/she_r2.8_grf/2
-- End of ClearCase branch-information.

	SHE-TSSM-MIB DEFINITIONS ::= BEGIN
 
		IMPORTS
			she			
				FROM AN-MIB			
			ifIndex			
				FROM IF-MIB			
			SheControlStatusType			
				FROM SHE-TC-MIB			
			SnmpAdminString			
				FROM SNMP-FRAMEWORK-MIB			
			OBJECT-GROUP, MODULE-COMPLIANCE, NOTIFICATION-GROUP			
				FROM SNMPv2-CONF			
			TimeTicks, IpAddress, Integer32, Unsigned32, Gauge32, 
			OBJECT-TYPE, MODULE-IDENTITY, NOTIFICATION-TYPE			
				FROM SNMPv2-SMI			
			TruthValue, DateAndTime			
				FROM SNMPv2-TC;
	
	
-- ------------------------------------------------------------------
-- |||||||||||||||||| MIB for TSSM data retrieval |||||||||||||||||||
-- ------------------------------------------------------------------
-- 
		sheTssmMib MODULE-IDENTITY 
			LAST-UPDATED "200809170955Z"		-- September 17, 2008 at 09:55 GMT
			ORGANIZATION 
				"Nokia Siemens Network"
			CONTACT-INFO 
				"COO BBA
				Siemens Building in Beijing
				
				jie.shen@nsn.com
				######################
				gerd.barchmann@nsn.com"
			DESCRIPTION 
				"The MIB module describes managed objects that support
				Training Speed Statistical Monitoring (TSSM) feature."
			REVISION "200510211130Z"		-- October 21, 2005 at 11:30 GMT
			DESCRIPTION 
				"Change sheTssmLastLinkUpLogAtucChanInterleaveMinTxRate to
				sheTssmLastLinkUpLogConfiguredRateDown;
				Change sheTssmLastLinkUpLogAturChanInterleaveMinTxRate to
				sheTssmLastLinkUpLogConfiguredRateUp;
				Remove the sheTssmProfileTable, move all TSSM configurations
				to sheTssmPortTable. sheTssmPortControl group was changed accordingly.
				"
			REVISION "200511010930Z"		-- November 01, 2005 at 09:30 GMT
			DESCRIPTION 
				"According to the newest TSSM standard, a new variable sheTssmMissTargetRateCriteria
				was added into the object list of traps sheTssmMissTargetRateTrap
				and sheTssmReachTargetRateTrap.
				"
			REVISION "200803190956Z"		-- March 19, 2008 at 09:56 GMT
			DESCRIPTION 
				"Bring them to common SHE MIB package with R2.8."
			REVISION "200804081125Z"		-- April 08, 2008 at 11:25 GMT
			DESCRIPTION 
				"Modify description for sheTssmPortControlIndex value."
			REVISION "200809171352Z"		-- September 17, 2008 at 13:52 GMT
			DESCRIPTION 
				"Correct some ranges."
			::= { she 34 }

		
	
--
-- Type definitions
--
	
		SheTssmMissTargetRateCriteriaType ::= INTEGER
			{
			missUpOrDownTargetRate(1),
			missUpTargetRate(2),
			missDownTargetRate(3)
			}

--  -----------------------------------------------------------------
-- Types definitions
-- -----------------------------------------------------------------
		SheTssmControlRequestType ::= INTEGER
			{
			noRequest(1),
			setTssmGlobalParameters(2),
			setTssmPortParameters(3)
			}

--  This type specifies the result of user commands (control requests)
-- from the TMN-OS or LCT.
		SheTssmControlRequestResultType ::= INTEGER
			{
			noRequest(1),
			wrongIpAddress(2),
			wrongUserPassword(3),
			permissionDenied(4),
			comExecStarted(30),
			paramFaulty(31),
			requestBusy(32),
			setDataFailed(34),
			aswTimeout(35),
			commandFailed(36),
			commandSucceeded(37)
			}

--  the upstream OR downstream rate less than the configured rate
-- only upstream rate less than the configured rate
-- only downstream rate less than the configured rate
		SheTssmUploadStatusType ::= INTEGER
			{
			uploadSuccess(1),
			uploadFail(2)
			}

--  user command results are defined between 2 - 29
-- The following are the error codes of enabling upload command.
-- All happened at the phase to check and create the RootDir
-- IP address of FTP servre is incorrect
-- The user name or password is wrong
-- The user name has no permission to create dir/file
-- end of user command results
		SheTssmThresholdUnitType ::= INTEGER
			{
			kbps(1),
			percentage(2)
			}

		SheTssmConfigType ::= INTEGER
			{
			configAlarmOnly(1),
			configThresholdOnly(2),
			configBoth(3)
			}

		SheTssmConfigRange ::= INTEGER
			{
			system(1),
			module(2),
			port(3)
			}

	
	
--
-- Node definitions
--
	
--  -----------------------------------------------------------------
-- sheTssmInfo group, defines the parameters and its control group
-- -----------------------------------------------------------------
		sheTssmInfo OBJECT IDENTIFIER ::= { sheTssmMib 1 }

		
--  -----------------------------------------------------------------
-- Parameters
-- -----------------------------------------------------------------
		sheTssmParameters OBJECT IDENTIFIER ::= { sheTssmInfo 1 }

		
		sheTssmFtpRootDir OBJECT-TYPE
			SYNTAX SnmpAdminString
			MAX-ACCESS read-only
			STATUS current
			DESCRIPTION
				"The root directory name on FTP server that stores the
				TSSM data of this DSLAM. It is the relative path to the
				ftproot, eg. 'hix5635/v1.5/dslam1/tssm'
				The directory structure looks like:
				ftproot            <-- the upmost ftp root
				|- %FtpRootDir%    <-- this value, specifies the DSLAM
				"
			::= { sheTssmParameters 1 }

		
		sheTssmFtpIp OBJECT-TYPE
			SYNTAX IpAddress
			MAX-ACCESS read-only
			STATUS current
			DESCRIPTION
				"FTP server's IP address."
			::= { sheTssmParameters 2 }

		
		sheTssmFtpUser OBJECT-TYPE
			SYNTAX SnmpAdminString
			MAX-ACCESS read-only
			STATUS current
			DESCRIPTION
				"FTP user name. Write permission is required for this user."
			::= { sheTssmParameters 3 }

		
		sheTssmFtpPassword OBJECT-TYPE
			SYNTAX OCTET STRING (SIZE (0..128))
			MAX-ACCESS read-only
			STATUS current
			DESCRIPTION
				"FTP server access password. To protect the password, the string
				of this object in the GetResponse PDU is encrypted."
			::= { sheTssmParameters 4 }

		
		sheTssmUploadInterval OBJECT-TYPE
			SYNTAX INTEGER (1..24)
			UNITS "Hour"
			MAX-ACCESS read-only
			STATUS current
			DESCRIPTION
				"The interval that TSSM data is uploaded to FTP server. It increases
				with step of 1 hour."
			DEFVAL { 24 }
			::= { sheTssmParameters 5 }

		
		sheTssmUploadEnabled OBJECT-TYPE
			SYNTAX TruthValue
			MAX-ACCESS read-only
			STATUS current
			DESCRIPTION
				"Whether the NE should upload the log files to FTP server."
			DEFVAL { false }
			::= { sheTssmParameters 6 }

		
		sheTssmLogEnabled OBJECT-TYPE
			SYNTAX TruthValue
			MAX-ACCESS read-only
			STATUS current
			DESCRIPTION
				"Whether the NE should keep the log of link parameters."
			DEFVAL { false }
			::= { sheTssmParameters 7 }

		
		sheTssmMissTargetRateCriteria OBJECT-TYPE
			SYNTAX SheTssmMissTargetRateCriteriaType
			MAX-ACCESS read-only
			STATUS current
			DESCRIPTION
				"The criteria of when the miss tartget rate trap should
				be sent."
			DEFVAL { missUpOrDownTargetRate }
			::= { sheTssmParameters 8 }

		
--  -----------------------------------------------------------------
-- Control group
-- -----------------------------------------------------------------
		sheTssmControl OBJECT IDENTIFIER ::= { sheTssmInfo 2 }

		
		sheTssmControlRequest OBJECT-TYPE
			SYNTAX SheTssmControlRequestType
			MAX-ACCESS read-write
			STATUS current
			DESCRIPTION
				"Command (setTssmGlobalParameters) to configure the global TSSM
				parameters. It must be the last member in the varBindList of
				the SNMP set request. The parameters of this command are:
				    sheTssmControlFtpRootDir
				    sheTssmControlFtpIp
				    sheTssmControlFtpUser
				    sheTssmControlFtpPassword
				    sheTssmControlUploadInterval
				    sheTssmControlUploadEnabled
				    sheTssmControlLogEnabled
				    sheTssmControlMissTargetRateCriteria
				  They are optional in the varBindList of set PDU, but at least one
				of them should be there.
				Notifications:
				  sheTssmControlResult at the command ending in case of long running command.
				  The long running command refers to the case that sheTssmUploadEnabled
				is changed from disable to enable. NE will verify the FTP connection at the
				enabling moment. Besides, the RootDir is created if it does not exist yet.
				  EM should GET sheTssmControlReqResult when the Response of the SET PDU
				is received, and the error status is noError. If the value of
				sheTssmControlReqResult is comExecStarted(30), which means the SET operation
				is a long running command, EM must issue another GET operation on
				sheTssmControlTimer. A timer should start on EM with the expire time equals
				to the value of sheTssmControlTimer. The sheTssmControlResult trap is expected
				to reach EM within the specified time.
				  When the trap is received by EM, EM can optionally GET
				sheTssmControlReqResult, sheTssmControlStatus, and sheTssmControlTimeStamp.
				"
			::= { sheTssmControl 1 }

		
		sheTssmControlStatus OBJECT-TYPE
			SYNTAX SheControlStatusType
			MAX-ACCESS read-only
			STATUS current
			DESCRIPTION
				"The status of a control request."
			::= { sheTssmControl 2 }

		
		sheTssmControlTimer OBJECT-TYPE
			SYNTAX Unsigned32
			MAX-ACCESS read-only
			STATUS current
			DESCRIPTION
				"The maximum wait time for the manager for command ending.
				For long running commands.
				The manager reads this value from the SHE."
			::= { sheTssmControl 3 }

		
		sheTssmControlReqResult OBJECT-TYPE
			SYNTAX SheTssmControlRequestResultType
			MAX-ACCESS read-only
			STATUS current
			DESCRIPTION
				"The result of the last user command."
			::= { sheTssmControl 4 }

		
		sheTssmControlTimeStamp OBJECT-TYPE
			SYNTAX Unsigned32
			UNITS "sec"
			MAX-ACCESS read-only
			STATUS current
			DESCRIPTION
				"The time stamp of the last command (end of command)."
			::= { sheTssmControl 5 }

		
		sheTssmControlFtpRootDir OBJECT-TYPE
			SYNTAX SnmpAdminString
			MAX-ACCESS read-write
			STATUS current
			DESCRIPTION
				"The root directory name on FTP server that stores the
				TSSM data of this DSLAM. Change the value of sheTssmFtpRootDir."
			::= { sheTssmControl 6 }

		
		sheTssmControlFtpIp OBJECT-TYPE
			SYNTAX IpAddress
			MAX-ACCESS read-write
			STATUS current
			DESCRIPTION
				"FTP server's IP address. Change the value of sheTssmFtpIp."
			::= { sheTssmControl 7 }

		
		sheTssmControlFtpUser OBJECT-TYPE
			SYNTAX SnmpAdminString
			MAX-ACCESS read-write
			STATUS current
			DESCRIPTION
				"FTP user name.  Change the value of sheTssmFtpUser."
			::= { sheTssmControl 8 }

		
		sheTssmControlFtpPassword OBJECT-TYPE
			SYNTAX OCTET STRING (SIZE (0..128))
			MAX-ACCESS read-write
			STATUS current
			DESCRIPTION
				"FTP server access password. To protect the password, the string
				of this object in the GetResponse PDU is encrypted."
			::= { sheTssmControl 9 }

		
		sheTssmControlUploadInterval OBJECT-TYPE
			SYNTAX INTEGER (1..24)
			UNITS "Hour"
			MAX-ACCESS read-write
			STATUS current
			DESCRIPTION
				"The interval that TSSM data is uploaded to FTP server.
				Change the value of sheTssmUploadInterval."
			::= { sheTssmControl 10 }

		
		sheTssmControlUploadEnabled OBJECT-TYPE
			SYNTAX TruthValue
			MAX-ACCESS read-write
			STATUS current
			DESCRIPTION
				"Whether the FTP upload process is enabled.
				Change the value of sheTssmUploadEnabled.
				If the sheTssmUploadEnabled is changed from disable to enable,
				FTP connection will be verified at the enabling moment. Besides,
				the RootDir is created if it does not exist yet. The command in
				this case is a long running command. sheTssmControlResult trap
				will be sent to EM to notify the command result.
				"
			::= { sheTssmControl 11 }

		
		sheTssmControlLogEnabled OBJECT-TYPE
			SYNTAX TruthValue
			MAX-ACCESS read-write
			STATUS current
			DESCRIPTION
				"Whether the NE should keep the log of link parameters.
				Change the value of sheTssmLogEnabled."
			::= { sheTssmControl 12 }

		
		sheTssmControlMissTargetRateCriteria OBJECT-TYPE
			SYNTAX SheTssmMissTargetRateCriteriaType
			MAX-ACCESS read-write
			STATUS current
			DESCRIPTION
				"The criteria of when the miss tartget rate trap should
				be sent."
			::= { sheTssmControl 13 }

		
--  -----------------------------------------------------------------
-- Status
-- -----------------------------------------------------------------
		sheTssmUploadInfo OBJECT IDENTIFIER ::= { sheTssmInfo 3 }

		
		sheTssmLastUploadStatus OBJECT-TYPE
			SYNTAX SheTssmUploadStatusType
			MAX-ACCESS read-only
			STATUS current
			DESCRIPTION
				"The status of last FTP upload operation.
				It could be uploadSuccess(1) or uploadFail(2)."
			::= { sheTssmUploadInfo 1 }

		
		sheTssmLastUploadTimeStamp OBJECT-TYPE
			SYNTAX TimeTicks
			MAX-ACCESS read-only
			STATUS current
			DESCRIPTION
				"The time stamp of the last FTP upload operation
				(end of operation)."
			::= { sheTssmUploadInfo 2 }

		
		sheTssmLastUploadFileName OBJECT-TYPE
			SYNTAX SnmpAdminString
			MAX-ACCESS read-only
			STATUS current
			DESCRIPTION
				"The file name of last FTP upload operation."
			::= { sheTssmUploadInfo 3 }

		
		sheTssmLastUploadErrorString OBJECT-TYPE
			SYNTAX SnmpAdminString
			MAX-ACCESS read-only
			STATUS current
			DESCRIPTION
				"The text that describes the FTP upload failure. If
				upload succeeded, this string is empty."
			::= { sheTssmUploadInfo 4 }

		
--  -----------------------------------------------------------------
-- Table
-- -----------------------------------------------------------------
		sheTssmPortTable OBJECT-TYPE
			SYNTAX SEQUENCE OF SheTssmPortEntry
			MAX-ACCESS not-accessible
			STATUS current
			DESCRIPTION
				"This table contains configuration parameters for TSSM
				on each ADSL port."
			::= { sheTssmInfo 4 }

		
		sheTssmPortEntry OBJECT-TYPE
			SYNTAX SheTssmPortEntry
			MAX-ACCESS not-accessible
			STATUS current
			DESCRIPTION
				"An entry in sheTssmPortTable."
			INDEX { ifIndex }
			::= { sheTssmPortTable 1 }

		
		SheTssmPortEntry ::=
			SEQUENCE { 
				sheTssmPortTrapEnabled
					TruthValue,
				sheTssmPortThresholdUnit
					SheTssmThresholdUnitType,
				sheTssmPortThresholdRateDownKbps
					Gauge32,
				sheTssmPortThresholdRateUpKbps
					Gauge32,
				sheTssmPortThresholdRateDownRatio
					INTEGER,
				sheTssmPortThresholdRateUpRatio
					INTEGER
			 }

		sheTssmPortTrapEnabled OBJECT-TYPE
			SYNTAX TruthValue
			MAX-ACCESS read-only
			STATUS current
			DESCRIPTION
				"Indicates whether this ADSL port is allowed to send trap to EM.
				If the stable trained rate on this line is lower than the configured
				threshold, sheTssmMissTargetRateTrap will be sent to alarm EM.
				If at next linkup, the stable trained rate is higher than the
				configured threshold, another trap (sheTssmReachTargetRateTrap)
				will be sent to clear the last alarm.
				"
			DEFVAL { false }
			::= { sheTssmPortEntry 1 }

		
		sheTssmPortThresholdUnit OBJECT-TYPE
			SYNTAX SheTssmThresholdUnitType
			MAX-ACCESS read-only
			STATUS current
			DESCRIPTION
				"Indicates what type of unit (kbps or percentage)is used
				to configure the TSSM threshold.
				"
			::= { sheTssmPortEntry 2 }

		
		sheTssmPortThresholdRateDownKbps OBJECT-TYPE
			SYNTAX Gauge32 (1..32736)
			UNITS "kbps"
			MAX-ACCESS read-only
			STATUS current
			DESCRIPTION
				"The configured threshold of downstream transmit rate on the channel.
				It is used only if sheTssmPortThresholdUnit is set to kbps(1).
				"
			::= { sheTssmPortEntry 3 }

		
		sheTssmPortThresholdRateUpKbps OBJECT-TYPE
			SYNTAX Gauge32 (1..32736)
			UNITS "kbps"
			MAX-ACCESS read-only
			STATUS current
			DESCRIPTION
				"The configured threshold of upstream transmit rate on the channel.
				It is used only if sheTssmPortThresholdUnit is set to kbps(1).
				"
			::= { sheTssmPortEntry 4 }

		
		sheTssmPortThresholdRateDownRatio OBJECT-TYPE
			SYNTAX INTEGER (0..100)
			UNITS "%"
			MAX-ACCESS read-only
			STATUS current
			DESCRIPTION
				"The configured threshold of downstream transmit rate on the channel.
				It is used only if sheTssmPortThresholdUnit is set to percentage(2).
				"
			::= { sheTssmPortEntry 5 }

		
		sheTssmPortThresholdRateUpRatio OBJECT-TYPE
			SYNTAX INTEGER (0..100)
			UNITS "%"
			MAX-ACCESS read-only
			STATUS current
			DESCRIPTION
				"The configured threshold of upstream transmit rate on the channel.
				It is used only if sheTssmPortThresholdUnit is set to percentage(2).
				"
			::= { sheTssmPortEntry 6 }

		
		sheTssmPortControl OBJECT IDENTIFIER ::= { sheTssmInfo 5 }

		
		sheTssmPortControlRequest OBJECT-TYPE
			SYNTAX SheTssmControlRequestType
			MAX-ACCESS read-write
			STATUS current
			DESCRIPTION
				"Command to configure sheTssmPortTable (setTssmPortParameters).
				It must be the last member in the varBindList of the SNMP set request.
				The parameters of this command are:
				    (must)
				    sheTssmPortControlType
				    sheTssmPortControlRange
				    (the following parameters depend on the value of above two parameters)
				    sheTssmPortControlIndex
				    sheTssmPortControlTrapEnabled
				    sheTssmPortControlThresholdUnit
				    sheTssmPortControlThresholdRateDownKbps
				    sheTssmPortControlThresholdRateUpKbps
				    sheTssmPortControlThresholdRateDownRatio
				    sheTssmPortControlThresholdRateUpRatio
				"
			::= { sheTssmPortControl 1 }

		
		sheTssmPortControlStatus OBJECT-TYPE
			SYNTAX SheControlStatusType
			MAX-ACCESS read-only
			STATUS current
			DESCRIPTION
				"The status of a user command."
			::= { sheTssmPortControl 2 }

		
		sheTssmPortControlTimer OBJECT-TYPE
			SYNTAX Gauge32
			MAX-ACCESS read-only
			STATUS current
			DESCRIPTION
				"The maximum wait time for the manager for a long running user command."
			::= { sheTssmPortControl 3 }

		
		sheTssmPortControlReqResult OBJECT-TYPE
			SYNTAX SheTssmControlRequestResultType
			MAX-ACCESS read-only
			STATUS current
			DESCRIPTION
				"The result of the last user command."
			::= { sheTssmPortControl 4 }

		
		sheTssmPortControlTimeStamp OBJECT-TYPE
			SYNTAX Unsigned32
			UNITS "sec"
			MAX-ACCESS read-only
			STATUS current
			DESCRIPTION
				"The time stamp of the last command (end of command)."
			::= { sheTssmPortControl 5 }

		
		sheTssmPortControlType OBJECT-TYPE
			SYNTAX SheTssmConfigType
			MAX-ACCESS read-write
			STATUS current
			DESCRIPTION
				"Indicates what parameters are configured in this command. It can be:
				configAlarmOnly(1):
				    Only sheTssmPortControlTrapEnabled is configured to
				    the specified ports. The threshold parametes are ignored.
				configThresholdOnly(2):
				    Only configure the threshold parameters to specified
				    ports. sheTssmPortControlTrapEnabled is ignored.
				configBoth(3):
				    Configure both type of parameters.
				"
			::= { sheTssmPortControl 6 }

		
		sheTssmPortControlRange OBJECT-TYPE
			SYNTAX SheTssmConfigRange
			MAX-ACCESS read-write
			STATUS current
			DESCRIPTION
				"Indicates how to configure the TSSM parameters to ports. It can be:
				system(1): apply the parameters to all the ports in the whole DSLAM
				module(2): apply the parameters to all the ports on a module (board)
				port(3): apply the parameters to a specific port.
				"
			::= { sheTssmPortControl 7 }

		
		sheTssmPortControlIndex OBJECT-TYPE
			SYNTAX Integer32
			MAX-ACCESS read-write
			STATUS current
			DESCRIPTION
				"Depends on the value of sheTssmPortControlRange, this object
				has different meaning:
				sheTssmPortControlRange  sheTssmPortControlIndex
				-----------------------  -----------------------
				system(1)                N/A
				module(2)                the entPhysIndex of card
				port(3)                  IfIndex of the configured adsl-interface
				"
			::= { sheTssmPortControl 8 }

		
		sheTssmPortControlTrapEnabled OBJECT-TYPE
			SYNTAX TruthValue
			MAX-ACCESS read-write
			STATUS current
			DESCRIPTION
				"Indicates whether the specified ADSL port is allowed to send trap
				to EM. If the stable trained rate on this line is lower than the
				configured threshold, a trap will be sent to alarm EM. If at next
				linkup, the stable trained rate is higher than the configured
				threshold, another trap will be sent to clear the last alarm.
				"
			::= { sheTssmPortControl 9 }

		
		sheTssmPortControlThresholdUnit OBJECT-TYPE
			SYNTAX SheTssmThresholdUnitType
			MAX-ACCESS read-write
			STATUS current
			DESCRIPTION
				"Indicates what type of unit is used to configure the
				TSSM threshold. It can be kbps(1), or percentage(2)
				"
			::= { sheTssmPortControl 10 }

		
		sheTssmPortControlThresholdRateDownKbps OBJECT-TYPE
			SYNTAX Gauge32 (1..32736)
			UNITS "kbps"
			MAX-ACCESS read-write
			STATUS current
			DESCRIPTION
				"The configured threshold of downstream transmit rate on the channel.
				It is used only if sheTssmPortThresholdUnit is set to kbps(1).
				"
			::= { sheTssmPortControl 11 }

		
		sheTssmPortControlThresholdRateUpKbps OBJECT-TYPE
			SYNTAX Gauge32 (1..32736)
			UNITS "kbps"
			MAX-ACCESS read-write
			STATUS current
			DESCRIPTION
				"The configured threshold of upstream transmit rate on the channel.
				It is used only if sheTssmPortThresholdUnit is set to kbps(1).
				"
			::= { sheTssmPortControl 12 }

		
		sheTssmPortControlThresholdRateDownRatio OBJECT-TYPE
			SYNTAX INTEGER (0..100)
			UNITS "%"
			MAX-ACCESS read-write
			STATUS current
			DESCRIPTION
				"The configured threshold of downstream transmit rate on the channel.
				It is used only if sheTssmPortThresholdUnit is set to percentage(2).
				"
			::= { sheTssmPortControl 13 }

		
		sheTssmPortControlThresholdRateUpRatio OBJECT-TYPE
			SYNTAX INTEGER (0..100)
			UNITS "%"
			MAX-ACCESS read-write
			STATUS current
			DESCRIPTION
				"The configured threshold of upstream transmit rate on the channel.
				It is used only if sheTssmPortThresholdUnit is set to percentage(2).
				"
			::= { sheTssmPortControl 14 }

		
		sheTssmLastLinkUpLogTable OBJECT-TYPE
			SYNTAX SEQUENCE OF SheTssmLastLinkUpLogEntry
			MAX-ACCESS not-accessible
			STATUS current
			DESCRIPTION
				"Each entry in this table contains the ADSL line parameters of a
				port for last link up."
			::= { sheTssmInfo 6 }

		
		sheTssmLastLinkUpLogEntry OBJECT-TYPE
			SYNTAX SheTssmLastLinkUpLogEntry
			MAX-ACCESS not-accessible
			STATUS current
			DESCRIPTION
				"An entry in sheTssmLastLinkUpLogTable."
			INDEX { ifIndex }
			::= { sheTssmLastLinkUpLogTable 1 }

		
		SheTssmLastLinkUpLogEntry ::=
			SEQUENCE { 
				sheTssmLastLinkUpLogLinkTime
					DateAndTime,
				sheTssmLastLinkUpLogAtucTxRate
					Gauge32,
				sheTssmLastLinkUpLogAturTxRate
					Gauge32,
				sheTssmLastLinkUpLogAtucSnrMgn
					INTEGER,
				sheTssmLastLinkUpLogAturSnrMgn
					INTEGER,
				sheTssmLastLinkUpLogAtucAtn
					Gauge32,
				sheTssmLastLinkUpLogAturAtn
					Gauge32,
				sheTssmLastLinkUpLogAtucAttainableRate
					Gauge32,
				sheTssmLastLinkUpLogAturAttainableRate
					Gauge32,
				sheTssmLastLinkUpLogAtucTxRateThreshold
					Gauge32,
				sheTssmLastLinkUpLogAturTxRateThreshold
					Gauge32,
				sheTssmLastLinkUpLogAtucChanInterleaveDelay
					Gauge32,
				sheTssmLastLinkUpLogAturChanInterleaveDelay
					Gauge32,
				sheTssmLastLinkUpLogAtucTargetSnrMgn
					INTEGER,
				sheTssmLastLinkUpLogAturTargetSnrMgn
					INTEGER,
				sheTssmLastLinkUpLogConfiguredRateDown
					Unsigned32,
				sheTssmLastLinkUpLogConfiguredRateUp
					Unsigned32
			 }

		sheTssmLastLinkUpLogLinkTime OBJECT-TYPE
			SYNTAX DateAndTime
			MAX-ACCESS read-only
			STATUS current
			DESCRIPTION
				"The time when the link up happened last time on this port."
			::= { sheTssmLastLinkUpLogEntry 1 }

		
		sheTssmLastLinkUpLogAtucTxRate OBJECT-TYPE
			SYNTAX Gauge32 (1..32736)
			UNITS "kbps"
			MAX-ACCESS read-only
			STATUS current
			DESCRIPTION
				"The stable downstream transmit rate on the channel.
				It is the value of sheAdslAtucChanCurrTxRate when the link up is stable."
			::= { sheTssmLastLinkUpLogEntry 2 }

		
		sheTssmLastLinkUpLogAturTxRate OBJECT-TYPE
			SYNTAX Gauge32 (1..32736)
			UNITS "kbps"
			MAX-ACCESS read-only
			STATUS current
			DESCRIPTION
				"The stable upstream transmit rate on the channel. It is the
				value of sheAdslAturChanCurrTxRate when the link up is stable."
			::= { sheTssmLastLinkUpLogEntry 3 }

		
		sheTssmLastLinkUpLogAtucSnrMgn OBJECT-TYPE
			SYNTAX INTEGER (-640..640)
			UNITS "tenth dB"
			MAX-ACCESS read-only
			STATUS current
			DESCRIPTION
				"Noise Margin as seen by this ATU with respect to its
				received signal in tenth dB. It is the value of
				sheAdslAtucPhysCurrSnrMgn when the link up is stable."
			::= { sheTssmLastLinkUpLogEntry 4 }

		
		sheTssmLastLinkUpLogAturSnrMgn OBJECT-TYPE
			SYNTAX INTEGER (-640..640)
			UNITS "tenth dB"
			MAX-ACCESS read-only
			STATUS current
			DESCRIPTION
				"Noise Margin as seen by this ATU with respect to its
				received signal in tenth dB. It is the value of
				sheAdslAturPhysCurrSnrMgn when the link up is stable."
			::= { sheTssmLastLinkUpLogEntry 5 }

		
		sheTssmLastLinkUpLogAtucAtn OBJECT-TYPE
			SYNTAX Gauge32 (0..630)
			UNITS "tenth dB"
			MAX-ACCESS read-only
			STATUS current
			DESCRIPTION
				"Measured difference in the total power transmitted by
				the peer ATU and the total power received by this ATU.
				It is the value of sheAdslAtucPhysCurrAtn when the link up is stable."
			::= { sheTssmLastLinkUpLogEntry 6 }

		
		sheTssmLastLinkUpLogAturAtn OBJECT-TYPE
			SYNTAX Gauge32 (0..630)
			UNITS "tenth dB"
			MAX-ACCESS read-only
			STATUS current
			DESCRIPTION
				"Measured difference in the total power transmitted by
				the peer ATU and the total power received by this ATU.
				It is the value of sheAdslAturPhysCurrAtn when the link up is stable."
			::= { sheTssmLastLinkUpLogEntry 7 }

		
		sheTssmLastLinkUpLogAtucAttainableRate OBJECT-TYPE
			SYNTAX Gauge32
			UNITS "kbps"
			MAX-ACCESS read-only
			STATUS current
			DESCRIPTION
				"Indicates the maximum attainable data rate by the ATU.
				It is the value of sheAdslAtucPhysCurrAttainableRate
				when the link up is stable."
			::= { sheTssmLastLinkUpLogEntry 8 }

		
		sheTssmLastLinkUpLogAturAttainableRate OBJECT-TYPE
			SYNTAX Gauge32
			UNITS "kbps"
			MAX-ACCESS read-only
			STATUS current
			DESCRIPTION
				"Indicates the maximum attainable data rate by the ATU.
				It is the value of sheAdslAturPhysCurrAttainableRate
				when the link up is stable."
			::= { sheTssmLastLinkUpLogEntry 9 }

		
		sheTssmLastLinkUpLogAtucTxRateThreshold OBJECT-TYPE
			SYNTAX Gauge32 (1..32736)
			UNITS "kbps"
			MAX-ACCESS read-only
			STATUS current
			DESCRIPTION
				"The configured threshold of downstream transmit rate on the channel."
			::= { sheTssmLastLinkUpLogEntry 10 }

		
		sheTssmLastLinkUpLogAturTxRateThreshold OBJECT-TYPE
			SYNTAX Gauge32 (1..32736)
			UNITS "kbps"
			MAX-ACCESS read-only
			STATUS current
			DESCRIPTION
				"The configured threshold of upstream transmit rate on the channel."
			::= { sheTssmLastLinkUpLogEntry 11 }

		
		sheTssmLastLinkUpLogAtucChanInterleaveDelay OBJECT-TYPE
			SYNTAX Gauge32
			UNITS "milli-seconds"
			MAX-ACCESS read-only
			STATUS current
			DESCRIPTION
				"Interleave Delay for this channel. It is the value of
				sheAdslAtucChanInterleaveDelay when the link up is stable."
			::= { sheTssmLastLinkUpLogEntry 12 }

		
		sheTssmLastLinkUpLogAturChanInterleaveDelay OBJECT-TYPE
			SYNTAX Gauge32
			UNITS "milli-seconds"
			MAX-ACCESS read-only
			STATUS current
			DESCRIPTION
				"Interleave Delay for this channel. It is the value of
				sheAdslAturChanInterleaveDelay when the link up is stable."
			::= { sheTssmLastLinkUpLogEntry 13 }

		
		sheTssmLastLinkUpLogAtucTargetSnrMgn OBJECT-TYPE
			SYNTAX INTEGER (0..310)
			UNITS "tenth dB"
			MAX-ACCESS read-only
			STATUS current
			DESCRIPTION
				"Configured Target Signal/Noise Margin on this line.
				It is the value of sheAdslLineConfProfileAtucConfTargetSnrMgn
				when the link up is stable."
			::= { sheTssmLastLinkUpLogEntry 14 }

		
		sheTssmLastLinkUpLogAturTargetSnrMgn OBJECT-TYPE
			SYNTAX INTEGER (0..310)
			UNITS "tenth dB"
			MAX-ACCESS read-only
			STATUS current
			DESCRIPTION
				"Configured Target Signal/Noise Margin on this line.
				It is the value of sheAdslLineConfProfileAturConfTargetSnrMgn
				when the link up is stable."
			::= { sheTssmLastLinkUpLogEntry 15 }

		
		sheTssmLastLinkUpLogConfiguredRateDown OBJECT-TYPE
			SYNTAX Unsigned32 (32..32736)
			UNITS "kbps"
			MAX-ACCESS read-only
			STATUS current
			DESCRIPTION
				"Configured downstream transmit rate for the channel on this line, in kbps.
				It is the value of sheAdslLineConfProfileAtucChanConfFastMaxTxRate or
				sheAdslLineConfProfileAtucChanConfInterleaveMaxTxRate, depending on
				the mode of the channel is fast or interleave.
				"
			::= { sheTssmLastLinkUpLogEntry 16 }

		
		sheTssmLastLinkUpLogConfiguredRateUp OBJECT-TYPE
			SYNTAX Unsigned32 (32..32736)
			UNITS "kbps"
			MAX-ACCESS read-only
			STATUS current
			DESCRIPTION
				"Configured upstream transmit rate for the channel on this line, in kbps.
				It is the value of sheAdslLineConfProfileAturChanConfFastMaxTxRate or
				sheAdslLineConfProfileAturChanConfInterleaveMaxTxRate, depending on
				the mode of the channel is fast or interleave."
			::= { sheTssmLastLinkUpLogEntry 17 }

		
		sheTssmLastLinkDownLogTable OBJECT-TYPE
			SYNTAX SEQUENCE OF SheTssmLastLinkDownLogEntry
			MAX-ACCESS not-accessible
			STATUS current
			DESCRIPTION
				"Each entry in this table contains the ADSL line parameters of a
				port for last link down."
			::= { sheTssmInfo 7 }

		
		sheTssmLastLinkDownLogEntry OBJECT-TYPE
			SYNTAX SheTssmLastLinkDownLogEntry
			MAX-ACCESS not-accessible
			STATUS current
			DESCRIPTION
				"An entry in sheTssmLastLinkDownLogTable."
			INDEX { ifIndex }
			::= { sheTssmLastLinkDownLogTable 1 }

		
		SheTssmLastLinkDownLogEntry ::=
			SEQUENCE { 
				sheTssmLastLinkDownLogLinkTime
					DateAndTime
			 }

		sheTssmLastLinkDownLogLinkTime OBJECT-TYPE
			SYNTAX DateAndTime
			MAX-ACCESS read-only
			STATUS current
			DESCRIPTION
				"The time when the link down happened last time on this port."
			::= { sheTssmLastLinkDownLogEntry 1 }

		
--  -----------------------------------------------------------------
-- Trap definitions
-- -----------------------------------------------------------------
		sheTssmNotifications OBJECT IDENTIFIER ::= { sheTssmMib 2 }

		
		sheTssmEvents OBJECT IDENTIFIER ::= { sheTssmNotifications 1 }

		
		sheTssmControlResult NOTIFICATION-TYPE
			OBJECTS { sheTssmControlTimeStamp, sheTssmControlRequest, sheTssmControlReqResult }
			STATUS current
			DESCRIPTION 
				"Notification sent at the end of long running command.
				The possible values of sheTssmControlReqResult are:
				    wrongIpAddress(2),      -- IP address of FTP servre is incorrect
				    wrongUserPassword(3),   -- The user name or password is wrong
				    permissionDenied(4),    -- The user name has no permission to create dir/file
				    commandSucceeded(37)
				"
			::= { sheTssmEvents 1 }

		
		sheTssmUploadFailedTrap NOTIFICATION-TYPE
			OBJECTS { sheTssmLastUploadStatus, sheTssmLastUploadTimeStamp, sheTssmLastUploadFileName, sheTssmLastUploadErrorString }
			STATUS current
			DESCRIPTION 
				"Indicates that an FTP upload failure occurred."
			::= { sheTssmEvents 2 }

		
--  the criteria
-- link up time
-- stable downstream rate
-- stable upstream rate
-- downstream noise margin
-- upstream noise margin
-- downstream attenuation
-- upstream attenuation
-- downstream maximum attainable rate
-- upstream maximum attainable rate
-- configured rate
-- configured rate
-- interleave delay
-- interleave delay
-- target noise margin
-- target noise margin
-- alarm threshold rate
-- alarm threshold rate
		sheTssmMissTargetRateTrap NOTIFICATION-TYPE
			OBJECTS { ifIndex, sheTssmMissTargetRateCriteria, sheTssmLastLinkUpLogLinkTime, sheTssmLastLinkUpLogAtucTxRate, sheTssmLastLinkUpLogAturTxRate, 
				sheTssmLastLinkUpLogAtucSnrMgn, sheTssmLastLinkUpLogAturSnrMgn, sheTssmLastLinkUpLogAtucAtn, sheTssmLastLinkUpLogAturAtn, sheTssmLastLinkUpLogAtucAttainableRate, 
				sheTssmLastLinkUpLogAturAttainableRate, sheTssmLastLinkUpLogConfiguredRateDown, sheTssmLastLinkUpLogConfiguredRateUp, sheTssmLastLinkUpLogAtucChanInterleaveDelay, sheTssmLastLinkUpLogAturChanInterleaveDelay, 
				sheTssmLastLinkUpLogAtucTargetSnrMgn, sheTssmLastLinkUpLogAturTargetSnrMgn, sheTssmLastLinkUpLogAtucTxRateThreshold, sheTssmLastLinkUpLogAturTxRateThreshold }
			STATUS current
			DESCRIPTION 
				"Indicates that the stable link rate does not meet the target rate on
				the ADSL port specified by ifIndex. The EM will show an alarm on this port.
				The corresponding parameters are included in the trap."
			::= { sheTssmEvents 3 }

		
--  the criteria
-- link up time
-- stable downstream rate
-- stable upstream rate
-- downstream noise margin
-- upstream noise margin
-- downstream attenuation
-- upstream attenuation
-- downstream maximum attainable rate
-- upstream maximum attainable rate
-- configured rate
-- configured rate
-- interleave delay
-- interleave delay
-- target noise margin
-- target noise margin
-- alarm threshold rate
-- alarm threshold rate
		sheTssmReachTargetRateTrap NOTIFICATION-TYPE
			OBJECTS { ifIndex, sheTssmMissTargetRateCriteria, sheTssmLastLinkUpLogLinkTime, sheTssmLastLinkUpLogAtucTxRate, sheTssmLastLinkUpLogAturTxRate, 
				sheTssmLastLinkUpLogAtucSnrMgn, sheTssmLastLinkUpLogAturSnrMgn, sheTssmLastLinkUpLogAtucAtn, sheTssmLastLinkUpLogAturAtn, sheTssmLastLinkUpLogAtucAttainableRate, 
				sheTssmLastLinkUpLogAturAttainableRate, sheTssmLastLinkUpLogConfiguredRateDown, sheTssmLastLinkUpLogConfiguredRateUp, sheTssmLastLinkUpLogAtucChanInterleaveDelay, sheTssmLastLinkUpLogAturChanInterleaveDelay, 
				sheTssmLastLinkUpLogAtucTargetSnrMgn, sheTssmLastLinkUpLogAturTargetSnrMgn, sheTssmLastLinkUpLogAtucTxRateThreshold, sheTssmLastLinkUpLogAturTxRateThreshold }
			STATUS current
			DESCRIPTION 
				"If at last time, the ADSL port that specified by ifIndex missed the target
				rate, and the sheTssmMissTargetRateTrap was sent, but it met the target rate
				at this link up, this trap is sent. The EM can clear the alarm then.
				The corresponding parameters are included in the trap."
			::= { sheTssmEvents 4 }

		
		sheTssmMibConformance OBJECT IDENTIFIER ::= { sheTssmMib 100 }

		
		sheTssmMibCompliances OBJECT IDENTIFIER ::= { sheTssmMibConformance 1 }

		
		sheTssmMibCompliance MODULE-COMPLIANCE
			STATUS current
			DESCRIPTION 
				"Description."
			MODULE -- this module
				MANDATORY-GROUPS { sheTssmMibGroup, sheTssmMibControlGroup, sheTssmMibNotificationGroup }
			::= { sheTssmMibCompliances 1 }

		
		sheTssmMibGroups OBJECT IDENTIFIER ::= { sheTssmMibConformance 2 }

		
		sheTssmMibGroup OBJECT-GROUP
			OBJECTS { sheTssmFtpRootDir, sheTssmFtpIp, sheTssmFtpUser, sheTssmFtpPassword, sheTssmUploadInterval, 
				sheTssmUploadEnabled, sheTssmLogEnabled, sheTssmMissTargetRateCriteria, sheTssmLastUploadStatus, sheTssmLastUploadTimeStamp, 
				sheTssmLastUploadFileName, sheTssmLastUploadErrorString, sheTssmPortTrapEnabled, sheTssmPortThresholdUnit, sheTssmPortThresholdRateDownKbps, 
				sheTssmPortThresholdRateUpKbps, sheTssmPortThresholdRateDownRatio, sheTssmPortThresholdRateUpRatio, sheTssmLastLinkUpLogLinkTime, sheTssmLastLinkUpLogAtucTxRate, 
				sheTssmLastLinkUpLogAturTxRate, sheTssmLastLinkUpLogAtucSnrMgn, sheTssmLastLinkUpLogAturSnrMgn, sheTssmLastLinkUpLogAtucAtn, sheTssmLastLinkUpLogAturAtn, 
				sheTssmLastLinkUpLogAtucAttainableRate, sheTssmLastLinkUpLogAturAttainableRate, sheTssmLastLinkUpLogAtucTxRateThreshold, sheTssmLastLinkUpLogAturTxRateThreshold, sheTssmLastLinkUpLogAtucChanInterleaveDelay, 
				sheTssmLastLinkUpLogAturChanInterleaveDelay, sheTssmLastLinkUpLogAtucTargetSnrMgn, sheTssmLastLinkUpLogAturTargetSnrMgn, sheTssmLastLinkUpLogConfiguredRateDown, sheTssmLastLinkUpLogConfiguredRateUp, 
				sheTssmLastLinkDownLogLinkTime }
			STATUS current
			DESCRIPTION 
				"Description."
			::= { sheTssmMibGroups 1 }

		
		sheTssmMibControlGroup OBJECT-GROUP
			OBJECTS { sheTssmControlRequest, sheTssmControlStatus, sheTssmControlTimer, sheTssmControlReqResult, sheTssmControlTimeStamp, 
				sheTssmControlFtpRootDir, sheTssmControlFtpIp, sheTssmControlFtpUser, sheTssmControlFtpPassword, sheTssmControlUploadInterval, 
				sheTssmControlUploadEnabled, sheTssmControlLogEnabled, sheTssmControlMissTargetRateCriteria, sheTssmPortControlRequest, sheTssmPortControlStatus, 
				sheTssmPortControlTimer, sheTssmPortControlReqResult, sheTssmPortControlTimeStamp, sheTssmPortControlType, sheTssmPortControlRange, 
				sheTssmPortControlIndex, sheTssmPortControlTrapEnabled, sheTssmPortControlThresholdUnit, sheTssmPortControlThresholdRateDownKbps, sheTssmPortControlThresholdRateUpKbps, 
				sheTssmPortControlThresholdRateDownRatio, sheTssmPortControlThresholdRateUpRatio }
			STATUS current
			DESCRIPTION 
				"Description."
			::= { sheTssmMibGroups 2 }

		
		sheTssmMibNotificationGroup NOTIFICATION-GROUP
			NOTIFICATIONS { sheTssmControlResult, sheTssmUploadFailedTrap, sheTssmMissTargetRateTrap, sheTssmReachTargetRateTrap }
			STATUS current
			DESCRIPTION 
				"Description."
			::= { sheTssmMibGroups 3 }

		
	
	END

--
-- she-tssm-mib.mib
--
