ELTEX-MES-eltFtp-MIB DEFINITIONS ::= BEGIN

-- Title:      Eltex MES Ftp Configuration
-- Version:    1.0
-- Date:       28 Feb 2013

IMPORTS
    eltMesFtp                                               FROM ELTEX-MES-MNG-MIB
    MODULE-IDENTITY, OBJECT-TYPE                            FROM SNMPv2-SMI
    TruthValue,DisplayString,
    TEXTUAL-CONVENTION                                      FROM SNMPv2-TC;

eltFtpServerEnable OBJECT-TYPE
    SYNTAX      TruthValue
    MAX-ACCESS  read-write
    STATUS      current
    DESCRIPTION
        "Enable and disable FTP server."
    ::= { eltMesFtp 1 }

END
