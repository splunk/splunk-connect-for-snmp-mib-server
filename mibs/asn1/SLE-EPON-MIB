--
-- sle-epon-mib.mib
-- MIB generated by MG-SOFT Visual MIB Builder Version 6.0  Build 88
-- Wednesday, April 20, 2016 at 17:07:15
--

	SLE-EPON-MIB DEFINITIONS ::= BEGIN
 
		IMPORTS
			sleMgmt			
				FROM DASAN-SMI			
			ifIndex			
				FROM IF-MIB			
			VlanIndex, PortList			
				FROM Q-BRIDGE-MIB			
			sysDescr			
				FROM RFC1213-MIB			
			SleControlStatusType, SleControlRequestResultType			
				FROM SLE-TC-MIB			
			OBJECT-GROUP, NOTIFICATION-GROUP			
				FROM SNMPv2-CONF			
			TimeTicks, IpAddress, Integer32, Unsigned32, Gauge32, 
			Counter32, Counter64, BITS, OBJECT-TYPE, MODULE-IDENTITY, 
			NOTIFICATION-TYPE			
				FROM SNMPv2-SMI			
			MacAddress, TEXTUAL-CONVENTION			
				FROM SNMPv2-TC;
	
	
		sleEpon MODULE-IDENTITY 
			LAST-UPDATED ""		-- 
			ORGANIZATION 
				"Organization."
			CONTACT-INFO 
				"Contact-info."
			DESCRIPTION 
				"Description."
			::= { sleMgmt 20 }

		
	
	
--
-- Textual conventions
--
	
		EnableFlag ::= TEXTUAL-CONVENTION
			STATUS current
			DESCRIPTION 
				"Description."
			SYNTAX INTEGER
				{
				enable(1),
				disable(2)
				}

	
--
-- Node definitions
--
	
		sleEponBase OBJECT IDENTIFIER ::= { sleEpon 1 }

		
		sleEponBaseInfo OBJECT IDENTIFIER ::= { sleEponBase 1 }

		
		sleEponBaseSlaPlatoMaxBandwdith OBJECT-TYPE
			SYNTAX INTEGER (1000..900000 | 1000000)
			UNITS "kbps"
			MAX-ACCESS read-only
			STATUS current
			DESCRIPTION
				"Description."
			::= { sleEponBaseInfo 1 }

		
		sleEponBaseDPShapingMaxBandwidth OBJECT-TYPE
			SYNTAX INTEGER (0 | 1000..900000)
			UNITS "kbps"
			MAX-ACCESS read-only
			STATUS current
			DESCRIPTION
				"Description."
			::= { sleEponBaseInfo 2 }

		
		sleEponBasePortMaxHost OBJECT-TYPE
			SYNTAX INTEGER (0 | 1..16)
			MAX-ACCESS read-only
			STATUS current
			DESCRIPTION
				"Description."
			::= { sleEponBaseInfo 3 }

		
		sleEponBaseOnuAutoUpgrade OBJECT-TYPE
			SYNTAX EnableFlag
			MAX-ACCESS read-only
			STATUS current
			DESCRIPTION
				"The status of ONU auto-upgrade."
			::= { sleEponBaseInfo 4 }

		
		sleEponBaseOnuAutoUpgradeRebootTime OBJECT-TYPE
			SYNTAX INTEGER (-1 | 0..23)
			UNITS "hour"
			MAX-ACCESS read-only
			STATUS current
			DESCRIPTION
				"The reboot-time of ONU auto-upgrade."
			::= { sleEponBaseInfo 5 }

		
		sleEponBaseOnuAgingTime OBJECT-TYPE
			SYNTAX Integer32 (0..30)
			UNITS "day"
			MAX-ACCESS read-only
			STATUS current
			DESCRIPTION
				"Description."
			::= { sleEponBaseInfo 6 }

		
		sleEponBaseAlarmStatus OBJECT-TYPE
			SYNTAX BITS
				{
				critical(0),
				major(1),
				minor(2)
				}
			MAX-ACCESS read-only
			STATUS current
			DESCRIPTION
				"Description."
			::= { sleEponBaseInfo 7 }

		
		sleEponBaseAlarmMode OBJECT-TYPE
			SYNTAX INTEGER
				{
				auto(0),
				manual(1)
				}
			MAX-ACCESS read-only
			STATUS current
			DESCRIPTION
				"Description."
			::= { sleEponBaseInfo 8 }

		
		sleEponBaseLGPAuthServer OBJECT-TYPE
			SYNTAX IpAddress
			MAX-ACCESS read-write
			STATUS current
			DESCRIPTION
				"LGP authentication server."
			::= { sleEponBaseInfo 9 }

		
		sleEponBaseLGPAuthMode OBJECT-TYPE
			SYNTAX Integer32
			MAX-ACCESS read-write
			STATUS current
			DESCRIPTION
				"LGP authentication mode."
			::= { sleEponBaseInfo 10 }

		
		sleEponBaseCableDownStatus OBJECT-TYPE
			SYNTAX EnableFlag
			MAX-ACCESS read-only
			STATUS current
			DESCRIPTION
				"Epon cable-down status."
			::= { sleEponBaseInfo 11 }

		
		sleEponBaseCableDownReferenceCount OBJECT-TYPE
			SYNTAX INTEGER (1..8)
			MAX-ACCESS read-only
			STATUS current
			DESCRIPTION
				"Epon cable-down reference count."
			::= { sleEponBaseInfo 12 }

		
		sleEponBaseOnuAutoUpgradeVersionMatchStatus OBJECT-TYPE
			SYNTAX EnableFlag
			MAX-ACCESS read-only
			STATUS current
			DESCRIPTION
				"Onu auto upgrade version match status."
			::= { sleEponBaseInfo 13 }

		
		sleEponBaseOltAutoUpgradeVersionMatchStatus OBJECT-TYPE
			SYNTAX EnableFlag
			MAX-ACCESS read-only
			STATUS current
			DESCRIPTION
				"Olt auto upgrade version match status."
			::= { sleEponBaseInfo 14 }

		
		sleEponBaseOltMacAgingTime OBJECT-TYPE
			SYNTAX INTEGER (60..86400)
			MAX-ACCESS read-only
			STATUS current
			DESCRIPTION
				"Olt mac aging time."
			::= { sleEponBaseInfo 15 }

		
		sleEponBaseRogueOnuDetectThreshold OBJECT-TYPE
			SYNTAX INTEGER (2..60)
			MAX-ACCESS read-only
			STATUS current
			DESCRIPTION
				"Epon rogue-onu detect threshold."
			::= { sleEponBaseInfo 16 }

		
		sleEponBaseRogueOnuTxPowerOffDuration OBJECT-TYPE
			SYNTAX INTEGER (10..60)
			MAX-ACCESS read-only
			STATUS current
			DESCRIPTION
				"Epon rogue-onu tx-power off duration."
			::= { sleEponBaseInfo 17 }

		
		sleEponBaseRogueOnuDetectMaxTurnLimit OBJECT-TYPE
			SYNTAX INTEGER (1..20)
			MAX-ACCESS read-only
			STATUS current
			DESCRIPTION
				"Epon rogue-onu detect max turn limit."
			::= { sleEponBaseInfo 18 }

		
		sleEponBaseRogueOnuDetectShutdownStartThreshold OBJECT-TYPE
			SYNTAX Integer32 (1..60)
			MAX-ACCESS read-only
			STATUS current
			DESCRIPTION
				"Epon rogue-onu detect shutdown start threshold"
			::= { sleEponBaseInfo 19 }

		
		sleEponBaseRogueOnuDetectShutdownInterval OBJECT-TYPE
			SYNTAX Integer32 (1..60)
			MAX-ACCESS read-only
			STATUS current
			DESCRIPTION
				"Epon rogue-onu detect shutdown interval"
			::= { sleEponBaseInfo 20 }

		
		sleEponBaseRogueOnuDetectverify OBJECT-TYPE
			SYNTAX EnableFlag
			MAX-ACCESS read-only
			STATUS current
			DESCRIPTION
				"Epon rogue-onu detect verify"
			::= { sleEponBaseInfo 21 }

		
		sleEponBaseOnuDailyRxPowerThresholdCount OBJECT-TYPE
			SYNTAX INTEGER (1..64)
			MAX-ACCESS read-only
			STATUS current
			DESCRIPTION
				"Onu daily rxPower threshold onu count."
			::= { sleEponBaseInfo 22 }

		
		sleEponBaseOnuDailyRxPowerThresholdDBM OBJECT-TYPE
			SYNTAX INTEGER (0..30)
			MAX-ACCESS read-only
			STATUS current
			DESCRIPTION
				"Onu daily rxPower threshold DBM."
			::= { sleEponBaseInfo 23 }

		
		sleEponBaseOnuDailyRxPowerThresholdChecktime OBJECT-TYPE
			SYNTAX INTEGER (0..23)
			MAX-ACCESS read-only
			STATUS current
			DESCRIPTION
				"Onu daily rxPower threshold check time."
			::= { sleEponBaseInfo 24 }

		
		sleEponBaseOnuDailyRxPowerThresholdSerious OBJECT-TYPE
			SYNTAX INTEGER
				{
				emerg(0),
				alert(1),
				crit(2),
				err(3),
				warning(4),
				notice(5),
				info(6),
				debug(7)
				}
			MAX-ACCESS read-only
			STATUS current
			DESCRIPTION
				"Onu daily rxPower threshold log level."
			::= { sleEponBaseInfo 25 }

		
		sleEponBaseControl OBJECT IDENTIFIER ::= { sleEponBase 2 }

		
		sleEponBaseControlRequest OBJECT-TYPE
			SYNTAX INTEGER
				{
				setEponBaseDefaultBandwidth(1),
				setEponBaseDefaultMaxhost(2),
				setEponBaseOnuAutoUpgrade(3),
				setEponBaseOnuAgingTime(4),
				setEponBaseAlarmStatus(5),
				setEponBaseAlarmMode(6),
				setEponBaseCableDownStatus(7),
				setEponBaseCableDownReferenceCount(8),
				setEponBaseOnuAutoUpgradeVersionMatch(9),
				setEponBaseOltAutoUpgradeVersionMatch(10),
				setEponBaseOltMacAgingTime(11),
				setEponBaseOltMacAgingTimeGlobalReset(12),
				setEponBaseRogueOnuDetectThreshold(13),
				noEponBaseRogueOnuDetectThreshold(14),
				setEponBaseRogueOnuTxPowerOffDuration(15),
				noEponBaseRogueOnuTxPowerOffDuration(16),
				setEponBaseRogueOnuDetectMaxTurnLimit(17),
				noEponBaseRogueOnuDetectMaxTurnLimit(18),
				noEponBaseCableDownReferenceCount(19),
				setEponBaseRogueOnuDetectShutdownStartThreshold(20),
				noEponBaseRogueOnuDetectShutdownStartThreshold(21),
				setEponBaseRogueOnuDetectShutdownInterval(22),
				noEponBaseRogueOnuDetectShutdownInterval(23),
				setEponBaseRogueOnuDetectVerify(24),
				noEponBaseRogueOnuDetectVerify(25),
				setEponBaseOnuDailyRxPowerThreshold(26),
				noEponBaseOnuDailyRxPowerThreshold(27)
				}
			MAX-ACCESS read-write
			STATUS current
			DESCRIPTION
				"Description."
			::= { sleEponBaseControl 1 }

		
		sleEponBaseControlStatus OBJECT-TYPE
			SYNTAX SleControlStatusType
			MAX-ACCESS read-only
			STATUS current
			DESCRIPTION
				"Description."
			::= { sleEponBaseControl 2 }

		
		sleEponBaseControlTimer OBJECT-TYPE
			SYNTAX Gauge32
			MAX-ACCESS read-write
			STATUS current
			DESCRIPTION
				"Description."
			::= { sleEponBaseControl 3 }

		
		sleEponBaseControlTimeStamp OBJECT-TYPE
			SYNTAX TimeTicks
			MAX-ACCESS read-only
			STATUS current
			DESCRIPTION
				"Description."
			::= { sleEponBaseControl 4 }

		
		sleEponBaseControlReqResult OBJECT-TYPE
			SYNTAX SleControlRequestResultType
			MAX-ACCESS read-only
			STATUS current
			DESCRIPTION
				"Description."
			::= { sleEponBaseControl 5 }

		
		sleEponBaseControlSlaPlatoMaxBandwdith OBJECT-TYPE
			SYNTAX INTEGER (1000..900000 | 1000000)
			UNITS "kbps"
			MAX-ACCESS read-write
			STATUS current
			DESCRIPTION
				"Description."
			::= { sleEponBaseControl 6 }

		
		sleEponBaseControlDPShapingMaxBandwidth OBJECT-TYPE
			SYNTAX INTEGER (0 | 1000..900000)
			UNITS "Mbps"
			MAX-ACCESS read-write
			STATUS current
			DESCRIPTION
				"Description."
			::= { sleEponBaseControl 7 }

		
		sleEponBaseControlPortMaxHost OBJECT-TYPE
			SYNTAX INTEGER (0 | 1..16)
			MAX-ACCESS read-write
			STATUS current
			DESCRIPTION
				"Description."
			::= { sleEponBaseControl 8 }

		
		sleEponBaseControlOnuAutoUpgrade OBJECT-TYPE
			SYNTAX EnableFlag
			MAX-ACCESS read-write
			STATUS current
			DESCRIPTION
				"The status of ONU auto-upgrade."
			::= { sleEponBaseControl 9 }

		
		sleEponBaseControlOnuAutoUpgradeRebootTime OBJECT-TYPE
			SYNTAX INTEGER (-1 | 0..23)
			UNITS "hour"
			MAX-ACCESS read-write
			STATUS current
			DESCRIPTION
				"The reboot-time of ONU auto-upgrade."
			::= { sleEponBaseControl 10 }

		
		sleEponBaseControlOnuAgingTime OBJECT-TYPE
			SYNTAX Integer32 (0..30)
			UNITS "day"
			MAX-ACCESS read-write
			STATUS current
			DESCRIPTION
				"Description."
			::= { sleEponBaseControl 11 }

		
		sleEponBaseControlAlarmStatus OBJECT-TYPE
			SYNTAX BITS
				{
				critical(0),
				major(1),
				minor(2)
				}
			MAX-ACCESS read-write
			STATUS current
			DESCRIPTION
				"Description."
			::= { sleEponBaseControl 12 }

		
		sleEponBaseControlAlarmMode OBJECT-TYPE
			SYNTAX INTEGER
				{
				auto(0),
				manual(1)
				}
			MAX-ACCESS read-write
			STATUS current
			DESCRIPTION
				"Description."
			::= { sleEponBaseControl 13 }

		
		sleEponBaseControlLGPAuthServer OBJECT-TYPE
			SYNTAX IpAddress
			MAX-ACCESS read-write
			STATUS current
			DESCRIPTION
				"LGP authentication server."
			::= { sleEponBaseControl 14 }

		
		sleEponBaseControlLGPAuthMode OBJECT-TYPE
			SYNTAX INTEGER
			MAX-ACCESS read-write
			STATUS current
			DESCRIPTION
				"LGP authentication mode."
			::= { sleEponBaseControl 15 }

		
		sleEponBaseControlCableDownStatus OBJECT-TYPE
			SYNTAX EnableFlag
			MAX-ACCESS read-write
			STATUS current
			DESCRIPTION
				"Epon cable-down status."
			::= { sleEponBaseControl 16 }

		
		sleEponBaseControlCableDownReferenceCount OBJECT-TYPE
			SYNTAX INTEGER (1..8)
			MAX-ACCESS read-write
			STATUS current
			DESCRIPTION
				"Epon cable-down reference count."
			::= { sleEponBaseControl 17 }

		
		sleEponBaseControlOnuAutoUpgradeVersionMatchStatus OBJECT-TYPE
			SYNTAX EnableFlag
			MAX-ACCESS read-write
			STATUS current
			DESCRIPTION
				"Onu auto upgrade version match status."
			::= { sleEponBaseControl 18 }

		
		sleEponBaseControlOltAutoUpgradeVersionMatchStatus OBJECT-TYPE
			SYNTAX EnableFlag
			MAX-ACCESS read-write
			STATUS current
			DESCRIPTION
				"Olt auto upgrade version match status."
			::= { sleEponBaseControl 19 }

		
		sleEponBaseControlOltMacAgingTime OBJECT-TYPE
			SYNTAX INTEGER (60..86400)
			MAX-ACCESS read-write
			STATUS current
			DESCRIPTION
				"Olt mac aging time."
			::= { sleEponBaseControl 20 }

		
		sleEponBaseControlRogueOnuDetectThreshold OBJECT-TYPE
			SYNTAX INTEGER (2..60)
			MAX-ACCESS read-write
			STATUS current
			DESCRIPTION
				"Epon rogue-onu detect threshold."
			::= { sleEponBaseControl 21 }

		
		sleEponBaseControlRogueOnuTxPowerOffDuration OBJECT-TYPE
			SYNTAX INTEGER (10..60)
			MAX-ACCESS read-write
			STATUS current
			DESCRIPTION
				"Epon rogue-onu tx-power off duration."
			::= { sleEponBaseControl 22 }

		
		sleEponBaseControlRogueOnuDetectMaxTurnLimit OBJECT-TYPE
			SYNTAX INTEGER (1..20)
			MAX-ACCESS read-write
			STATUS current
			DESCRIPTION
				"Epon rogue-onu detect max turn limit."
			::= { sleEponBaseControl 23 }

		
		sleEponBaseControlRogueOnuDetectShutdownStartThreshold OBJECT-TYPE
			SYNTAX Integer32 (1..60)
			MAX-ACCESS read-only
			STATUS current
			DESCRIPTION
				"Epon rogue-onu detect shutdown start threshold"
			::= { sleEponBaseControl 24 }

		
		sleEponBaseControlRogueOnuDetectShutdownInterval OBJECT-TYPE
			SYNTAX Integer32 (1..60)
			MAX-ACCESS read-only
			STATUS current
			DESCRIPTION
				"Epon rogue-onu detect shutdown interval"
			::= { sleEponBaseControl 25 }

		
		sleEponBaseControlRogueOnuDetectverify OBJECT-TYPE
			SYNTAX EnableFlag
			MAX-ACCESS read-only
			STATUS current
			DESCRIPTION
				"Epon rogue-onu detect verify"
			::= { sleEponBaseControl 26 }

		
		sleEponBaseControlOnuDailyRxPowerThresholdCount OBJECT-TYPE
			SYNTAX INTEGER (1..64)
			MAX-ACCESS read-write
			STATUS current
			DESCRIPTION
				"Onu daily rxPower threshold onu count."
			::= { sleEponBaseControl 27 }

		
		sleEponBaseControlOnuDailyRxPowerThresholdDBM OBJECT-TYPE
			SYNTAX INTEGER (0..30)
			MAX-ACCESS read-write
			STATUS current
			DESCRIPTION
				"Onu daily rxPower threshold DBM,it must be devided by 10000."
			::= { sleEponBaseControl 28 }

		
		sleEponBaseControlOnuDailyRxPowerThresholdChecktime OBJECT-TYPE
			SYNTAX INTEGER (0..23)
			MAX-ACCESS read-write
			STATUS current
			DESCRIPTION
				"Onu daily rxPower threshold check time."
			::= { sleEponBaseControl 29 }

		
		sleEponBaseControlOnuDailyRxPowerThresholdSerious OBJECT-TYPE
			SYNTAX INTEGER
				{
				emerg(0),
				alert(1),
				crit(2),
				err(3),
				warning(4),
				notice(5),
				info(6),
				debug(7)
				}
			MAX-ACCESS read-write
			STATUS current
			DESCRIPTION
				"Onu daily rxPower threshold log level."
			::= { sleEponBaseControl 30 }

		
		sleEponBaseNotification OBJECT IDENTIFIER ::= { sleEponBase 3 }

		
		sleEponBaseDefaultBandwidthChanged NOTIFICATION-TYPE
			OBJECTS { sleEponBaseControlRequest, sleEponBaseControlTimeStamp, sleEponBaseControlReqResult, sleEponBaseControlSlaPlatoMaxBandwdith, sleEponBaseControlDPShapingMaxBandwidth
				 }
			STATUS current
			DESCRIPTION 
				"Description."
			::= { sleEponBaseNotification 1 }

		
		sleEponBaseDefaultMaxHost NOTIFICATION-TYPE
			OBJECTS { sleEponBaseControlRequest, sleEponBaseControlTimeStamp, sleEponBaseControlReqResult, sleEponBaseControlPortMaxHost }
			STATUS current
			DESCRIPTION 
				"Description."
			::= { sleEponBaseNotification 2 }

		
		sleEponBaseOnuAutoUpgradeChanged NOTIFICATION-TYPE
			OBJECTS { sleEponBaseControlRequest, sleEponBaseControlTimeStamp, sleEponBaseControlReqResult, sleEponBaseControlOnuAutoUpgrade, sleEponBaseControlOnuAutoUpgradeRebootTime
				 }
			STATUS current
			DESCRIPTION 
				"Description."
			::= { sleEponBaseNotification 3 }

		
		sleEponBaseOnuAgingTimeChanged NOTIFICATION-TYPE
			OBJECTS { sleEponBaseControlRequest, sleEponBaseControlTimeStamp, sleEponBaseControlReqResult, sleEponBaseControlOnuAgingTime }
			STATUS current
			DESCRIPTION 
				"Description."
			::= { sleEponBaseNotification 4 }

		
		sleEponBaseAlarmStatusChanged NOTIFICATION-TYPE
			OBJECTS { sleEponBaseControlRequest, sleEponBaseControlTimeStamp, sleEponBaseControlReqResult, sleEponBaseControlAlarmStatus }
			STATUS current
			DESCRIPTION 
				"Description."
			::= { sleEponBaseNotification 5 }

		
		sleEponBaseAlarmModeChanged NOTIFICATION-TYPE
			OBJECTS { sleEponBaseControlRequest, sleEponBaseControlTimeStamp, sleEponBaseControlReqResult, sleEponBaseAlarmMode }
			STATUS current
			DESCRIPTION 
				"Description."
			::= { sleEponBaseNotification 6 }

		
		sleEponBaseCableDownStatusChanged NOTIFICATION-TYPE
			OBJECTS { sleEponBaseControlRequest, sleEponBaseControlTimeStamp, sleEponBaseControlReqResult, sleEponBaseControlCableDownStatus }
			STATUS current
			DESCRIPTION 
				"Description."
			::= { sleEponBaseNotification 7 }

		
		sleEponBaseCableDownReferenceCountChanged NOTIFICATION-TYPE
			OBJECTS { sleEponBaseControlRequest, sleEponBaseControlTimeStamp, sleEponBaseControlReqResult, sleEponBaseControlCableDownReferenceCount }
			STATUS current
			DESCRIPTION 
				"Description."
			::= { sleEponBaseNotification 8 }

		
		sleEponBaseOnuAutoUpgradeVersionMatchChanged NOTIFICATION-TYPE
			OBJECTS { sleEponBaseControlRequest, sleEponBaseControlTimeStamp, sleEponBaseControlReqResult, sleEponBaseControlOnuAutoUpgradeVersionMatchStatus }
			STATUS current
			DESCRIPTION 
				"Description."
			::= { sleEponBaseNotification 9 }

		
		sleEponBaseOltAutoUpgradeVersionMatchChanged NOTIFICATION-TYPE
			OBJECTS { sleEponBaseControlRequest, sleEponBaseControlTimeStamp, sleEponBaseControlReqResult, sleEponBaseControlOltAutoUpgradeVersionMatchStatus }
			STATUS current
			DESCRIPTION 
				"Description."
			::= { sleEponBaseNotification 10 }

		
		sleEponBaseOltMacAgingTimeChanged NOTIFICATION-TYPE
			OBJECTS { sleEponBaseControlRequest, sleEponBaseControlTimeStamp, sleEponBaseControlReqResult, sleEponBaseControlOltMacAgingTime }
			STATUS current
			DESCRIPTION 
				"Description."
			::= { sleEponBaseNotification 11 }

		
		sleEponBaseOltMacAgingTimeGlobalReset NOTIFICATION-TYPE
			OBJECTS { sleEponBaseControlRequest, sleEponBaseControlTimeStamp, sleEponBaseControlReqResult, sleEponBaseControlOltMacAgingTime }
			STATUS current
			DESCRIPTION 
				"Description."
			::= { sleEponBaseNotification 12 }

		
		sleEponBaseRogueOnuDetectThresholdChanged NOTIFICATION-TYPE
			OBJECTS { sleEponBaseControlRequest, sleEponBaseControlTimeStamp, sleEponBaseControlReqResult, sleEponBaseControlRogueOnuDetectThreshold }
			STATUS current
			DESCRIPTION 
				"Description."
			::= { sleEponBaseNotification 13 }

		
		sleEponBaseNoRogueOnuDetectThreshold NOTIFICATION-TYPE
			OBJECTS { sleEponBaseControlRequest, sleEponBaseControlTimeStamp, sleEponBaseControlReqResult, sleEponBaseControlRogueOnuDetectThreshold }
			STATUS current
			DESCRIPTION 
				"Description."
			::= { sleEponBaseNotification 14 }

		
		sleEponBaseRogueOnuTxPowerOffDurationChanged NOTIFICATION-TYPE
			OBJECTS { sleEponBaseControlRequest, sleEponBaseControlTimeStamp, sleEponBaseControlReqResult, sleEponBaseControlRogueOnuTxPowerOffDuration }
			STATUS current
			DESCRIPTION 
				"Description."
			::= { sleEponBaseNotification 15 }

		
		sleEponBaseNoRogueOnuTxPowerOffDuration NOTIFICATION-TYPE
			OBJECTS { sleEponBaseControlRequest, sleEponBaseControlTimeStamp, sleEponBaseControlReqResult, sleEponBaseControlRogueOnuTxPowerOffDuration }
			STATUS current
			DESCRIPTION 
				"Description."
			::= { sleEponBaseNotification 16 }

		
		sleEponBaseRogueOnuDetectMaxTurnLimitChanged NOTIFICATION-TYPE
			OBJECTS { sleEponBaseControlRequest, sleEponBaseControlTimeStamp, sleEponBaseControlReqResult, sleEponBaseControlRogueOnuDetectMaxTurnLimit }
			STATUS current
			DESCRIPTION 
				"Description."
			::= { sleEponBaseNotification 17 }

		
		sleEponBaseNoRogueOnuDetectMaxTurnLimit NOTIFICATION-TYPE
			OBJECTS { sleEponBaseControlRequest, sleEponBaseControlTimeStamp, sleEponBaseControlReqResult, sleEponBaseControlRogueOnuDetectMaxTurnLimit }
			STATUS current
			DESCRIPTION 
				"Description."
			::= { sleEponBaseNotification 18 }

		
		sleEponBaseOnuDailyRxPowerThreshold NOTIFICATION-TYPE
			OBJECTS { sleEponBaseControlRequest, sleEponBaseControlTimeStamp, sleEponBaseControlReqResult, sleEponBaseOnuDailyRxPowerThresholdCount, sleEponBaseOnuDailyRxPowerThresholdDBM, 
				sleEponBaseOnuDailyRxPowerThresholdChecktime, sleEponBaseOnuDailyRxPowerThresholdSerious }
			STATUS current
			DESCRIPTION 
				"Description."
			::= { sleEponBaseNotification 19 }

		
		sleEponBaseRogueOnuDetectShutdownStartThresholdChanged NOTIFICATION-TYPE
			OBJECTS { sleEponBaseControlRequest, sleEponBaseControlTimeStamp, sleEponBaseControlRogueOnuDetectShutdownStartThreshold, sleEponBaseControlReqResult }
			STATUS current
			DESCRIPTION 
				"Description."
			::= { sleEponBaseNotification 20 }

		
		sleEponBaseNoRogueOnuDetectShutdownStartThreshold NOTIFICATION-TYPE
			OBJECTS { sleEponBaseControlRequest, sleEponBaseControlTimeStamp, sleEponBaseControlRogueOnuDetectShutdownStartThreshold, sleEponBaseControlReqResult }
			STATUS current
			DESCRIPTION 
				"Description."
			::= { sleEponBaseNotification 21 }

		
		sleEponBaseRogueOnuDetectShutdownIntervalChanged NOTIFICATION-TYPE
			OBJECTS { sleEponBaseControlRequest, sleEponBaseControlTimeStamp, sleEponBaseControlRogueOnuDetectShutdownInterval, sleEponBaseControlReqResult }
			STATUS current
			DESCRIPTION 
				"Description."
			::= { sleEponBaseNotification 22 }

		
		sleEponBaseNoRogueOnuDetectShutdownInterval NOTIFICATION-TYPE
			OBJECTS { sleEponBaseControlRequest, sleEponBaseControlTimeStamp, sleEponBaseControlRogueOnuDetectShutdownInterval, sleEponBaseControlReqResult }
			STATUS current
			DESCRIPTION 
				"Description."
			::= { sleEponBaseNotification 23 }

		
		sleEponBaseRogueOnuDetectVerifyChanged NOTIFICATION-TYPE
			OBJECTS { sleEponBaseControlRequest, sleEponBaseControlTimeStamp, sleEponBaseControlRogueOnuDetectverify, sleEponBaseControlReqResult }
			STATUS current
			DESCRIPTION 
				"Description."
			::= { sleEponBaseNotification 24 }

		
		sleEponBaseNoRogueOnuDetectVerify NOTIFICATION-TYPE
			OBJECTS { sleEponBaseControlRequest, sleEponBaseControlTimeStamp, sleEponBaseControlRogueOnuDetectverify, sleEponBaseControlReqResult }
			STATUS current
			DESCRIPTION 
				"Description."
			::= { sleEponBaseNotification 25 }

		
		sleEponOlt OBJECT IDENTIFIER ::= { sleEpon 2 }

		
		sleEponOltTable OBJECT-TYPE
			SYNTAX SEQUENCE OF SleEponOltEntry
			MAX-ACCESS not-accessible
			STATUS current
			DESCRIPTION
				"Description."
			::= { sleEponOlt 1 }

		
		sleEponOltEntry OBJECT-TYPE
			SYNTAX SleEponOltEntry
			MAX-ACCESS not-accessible
			STATUS current
			DESCRIPTION
				"Description."
			INDEX { sleEponOltIndex }
			::= { sleEponOltTable 1 }

		
		SleEponOltEntry ::=
			SEQUENCE { 
				sleEponOltIndex
					INTEGER,
				sleEponOltRegMode
					INTEGER,
				sleEponOltAdminStatus
					EnableFlag,
				sleEponOltEncryptionPolicy
					INTEGER,
				sleEponOltP2pAccessControl
					EnableFlag,
				sleEponOltDbaInternal
					EnableFlag,
				sleEponOltDbaCycle
					INTEGER,
				sleEponOltDbaDiscoveryFrequency
					INTEGER,
				sleEponOltDbaDiscoveryLength
					INTEGER,
				sleEponOltProfile
					OCTET STRING,
				sleEponOltTxFault
					INTEGER,
				sleEponOltLossOfSignal
					INTEGER,
				sleEponOltAdminRegMode
					INTEGER,
				sleEponOltSC
					EnableFlag,
				sleEponOltSCAutoOnuBlock
					EnableFlag,
				sleEponOltOperStatus
					INTEGER,
				sleEponOltFirmwareRev
					OCTET STRING,
				sleEponOltKeyExchangeTimeout
					INTEGER,
				sleEponOltRssiStatus
					EnableFlag,
				sleEponOltOnuRegisterCount
					INTEGER,
				sleEponOltMaxDistance
					INTEGER,
				sleEponOltDhcpOption254Status
					EnableFlag,
				sleEponOltPonMode
					INTEGER,
				sleEponOltDiscardDlfMode
					EnableFlag,
				sleEponOltStatus
					INTEGER,
				sleEponOltProtectionMode
					INTEGER,
				sleEponOltDSFecMode
					EnableFlag,
				sleEponOltUSFecMode
					EnableFlag,
				sleEponOltSfpInsertMode
					INTEGER,
				sleEponOltSfpFaultMode
					INTEGER,
				sleEponOltRogueOnuMac
					OCTET STRING,
				sleEponOltRogueDetectStatus
					INTEGER,
				sleEponOltMaxOnuCount
					INTEGER,
				sleEponOltActiveOnuCount
					INTEGER,
				sleEponOltInactiveOnuCount
					INTEGER,
				sleEponOltInactiveAgingTime
					INTEGER
			 }

		sleEponOltIndex OBJECT-TYPE
			SYNTAX INTEGER (1..512)
			MAX-ACCESS read-only
			STATUS current
			DESCRIPTION
				"OLT port Index"
			::= { sleEponOltEntry 1 }

		
		sleEponOltRegMode OBJECT-TYPE
			SYNTAX INTEGER
				{
				auto(1),
				manual(2),
				fixed(3),
				autoToManual(4),
				webBasedRegistry(5)
				}
			MAX-ACCESS read-only
			STATUS current
			DESCRIPTION
				"OLT port registeraton Mode {auto(1), manual(2)}"
			DEFVAL { auto }
			::= { sleEponOltEntry 2 }

		
		sleEponOltAdminStatus OBJECT-TYPE
			SYNTAX EnableFlag
			MAX-ACCESS read-only
			STATUS current
			DESCRIPTION
				"OLT port status "
			::= { sleEponOltEntry 3 }

		
		sleEponOltEncryptionPolicy OBJECT-TYPE
			SYNTAX INTEGER
				{
				disable(1),
				down(2),
				both(3)
				}
			MAX-ACCESS read-only
			STATUS current
			DESCRIPTION
				"OLT port encryption policy"
			DEFVAL { disable }
			::= { sleEponOltEntry 4 }

		
		sleEponOltP2pAccessControl OBJECT-TYPE
			SYNTAX EnableFlag
			MAX-ACCESS read-only
			STATUS current
			DESCRIPTION
				"OLT port p2p access Control "
			DEFVAL { disable }
			::= { sleEponOltEntry 5 }

		
		sleEponOltDbaInternal OBJECT-TYPE
			SYNTAX EnableFlag
			MAX-ACCESS read-only
			STATUS current
			DESCRIPTION
				"OLT port DBA internal "
			DEFVAL { disable }
			::= { sleEponOltEntry 6 }

		
		sleEponOltDbaCycle OBJECT-TYPE
			SYNTAX INTEGER (0 | 200..16777215)
			MAX-ACCESS read-only
			STATUS current
			DESCRIPTION
				"OLT port DBA cycle "
			::= { sleEponOltEntry 7 }

		
		sleEponOltDbaDiscoveryFrequency OBJECT-TYPE
			SYNTAX INTEGER (0 | 1..65535)
			MAX-ACCESS read-only
			STATUS current
			DESCRIPTION
				"OLT port DBA Discovery Frequency"
			::= { sleEponOltEntry 8 }

		
		sleEponOltDbaDiscoveryLength OBJECT-TYPE
			SYNTAX INTEGER (0 | 1..65535)
			MAX-ACCESS read-only
			STATUS current
			DESCRIPTION
				"OLT port DBA Discovery Length"
			::= { sleEponOltEntry 9 }

		
		sleEponOltProfile OBJECT-TYPE
			SYNTAX OCTET STRING (SIZE (1..64))
			MAX-ACCESS read-only
			STATUS current
			DESCRIPTION
				"OLT port auto profile name"
			::= { sleEponOltEntry 10 }

		
		sleEponOltTxFault OBJECT-TYPE
			SYNTAX INTEGER
				{
				unknown(0),
				normal(1),
				lagerFault(2)
				}
			MAX-ACCESS read-only
			STATUS current
			DESCRIPTION
				"This object indicates the status of Tx fault."
			::= { sleEponOltEntry 11 }

		
		sleEponOltLossOfSignal OBJECT-TYPE
			SYNTAX INTEGER
				{
				unknown(0),
				normal(1),
				loss(2)
				}
			MAX-ACCESS read-only
			STATUS current
			DESCRIPTION
				"This object indicates the status of loss of signal"
			::= { sleEponOltEntry 12 }

		
		sleEponOltAdminRegMode OBJECT-TYPE
			SYNTAX INTEGER
				{
				auto(1),
				manual(2),
				autoToManual(3),
				webBasedRegistry(4)
				}
			MAX-ACCESS read-only
			STATUS current
			DESCRIPTION
				"OLT port admin registeraton Mode {auto(1), manual(2), auto-to-manual(3), web-based-registry(4)}"
			::= { sleEponOltEntry 13 }

		
		sleEponOltSC OBJECT-TYPE
			SYNTAX EnableFlag
			MAX-ACCESS read-only
			STATUS current
			DESCRIPTION
				"signal check"
			::= { sleEponOltEntry 14 }

		
		sleEponOltSCAutoOnuBlock OBJECT-TYPE
			SYNTAX EnableFlag
			MAX-ACCESS read-only
			STATUS current
			DESCRIPTION
				"signal check auto block"
			::= { sleEponOltEntry 15 }

		
		sleEponOltOperStatus OBJECT-TYPE
			SYNTAX INTEGER
				{
				up(1),
				down(2),
				cableDown(3)
				}
			MAX-ACCESS read-only
			STATUS current
			DESCRIPTION
				"Description."
			::= { sleEponOltEntry 16 }

		
		sleEponOltFirmwareRev OBJECT-TYPE
			SYNTAX OCTET STRING (SIZE (1..64))
			MAX-ACCESS read-only
			STATUS current
			DESCRIPTION
				"The firmware revision of OLT port."
			::= { sleEponOltEntry 17 }

		
		sleEponOltKeyExchangeTimeout OBJECT-TYPE
			SYNTAX INTEGER (600..65535)
			MAX-ACCESS read-only
			STATUS current
			DESCRIPTION
				"Key Exchange Timeout"
			::= { sleEponOltEntry 18 }

		
		sleEponOltRssiStatus OBJECT-TYPE
			SYNTAX EnableFlag
			MAX-ACCESS read-only
			STATUS current
			DESCRIPTION
				"Epon olt rssi disable/enable."
			::= { sleEponOltEntry 19 }

		
		sleEponOltOnuRegisterCount OBJECT-TYPE
			SYNTAX INTEGER (1..32)
			MAX-ACCESS read-only
			STATUS current
			DESCRIPTION
				"onu register count."
			::= { sleEponOltEntry 20 }

		
		sleEponOltMaxDistance OBJECT-TYPE
			SYNTAX INTEGER (20..50)
			MAX-ACCESS read-only
			STATUS current
			DESCRIPTION
				"Olt max distance."
			::= { sleEponOltEntry 21 }

		
		sleEponOltDhcpOption254Status OBJECT-TYPE
			SYNTAX EnableFlag
			MAX-ACCESS read-only
			STATUS current
			DESCRIPTION
				"Olt dhcp option254 status."
			::= { sleEponOltEntry 22 }

		
		sleEponOltPonMode OBJECT-TYPE
			SYNTAX INTEGER
				{
				unknown(0),
				mixed(1),
				real(2),
				hybrid(3)
				}
			MAX-ACCESS read-only
			STATUS current
			DESCRIPTION
				"Olt pon mode."
			::= { sleEponOltEntry 23 }

		
		sleEponOltDiscardDlfMode OBJECT-TYPE
			SYNTAX EnableFlag
			MAX-ACCESS read-only
			STATUS current
			DESCRIPTION
				"Olt discard DLF mode."
			::= { sleEponOltEntry 24 }

		
		sleEponOltStatus OBJECT-TYPE
			SYNTAX INTEGER
				{
				notReady(0),
				inactive(1),
				active(2),
				activePending(3),
				deactivePending(4),
				switchOverPending(5),
				disable(6),
				unknown(7)
				}
			MAX-ACCESS read-only
			STATUS current
			DESCRIPTION
				"OLT status, for V8500"
			::= { sleEponOltEntry 25 }

		
		sleEponOltProtectionMode OBJECT-TYPE
			SYNTAX INTEGER
				{
				working(0),
				standby(1),
				wPending(2),
				sPending(3),
				waiting(4),
				unknown(5)
				}
			MAX-ACCESS read-only
			STATUS current
			DESCRIPTION
				"protection mode"
			::= { sleEponOltEntry 26 }

		
		sleEponOltDSFecMode OBJECT-TYPE
			SYNTAX EnableFlag
			MAX-ACCESS read-only
			STATUS current
			DESCRIPTION
				"down stream fec mode"
			::= { sleEponOltEntry 27 }

		
		sleEponOltUSFecMode OBJECT-TYPE
			SYNTAX EnableFlag
			MAX-ACCESS read-only
			STATUS current
			DESCRIPTION
				"up stream fec mode"
			::= { sleEponOltEntry 28 }

		
		sleEponOltSfpInsertMode OBJECT-TYPE
			SYNTAX INTEGER
				{
				noInsert(0),
				insert(1)
				}
			MAX-ACCESS read-only
			STATUS current
			DESCRIPTION
				"sfp insert mode"
			::= { sleEponOltEntry 29 }

		
		sleEponOltSfpFaultMode OBJECT-TYPE
			SYNTAX INTEGER
				{
				noFault(0),
				fault(1)
				}
			MAX-ACCESS read-only
			STATUS current
			DESCRIPTION
				"sfp fault mode"
			::= { sleEponOltEntry 30 }

		
		sleEponOltRogueOnuMac OBJECT-TYPE
			SYNTAX OCTET STRING
			MAX-ACCESS read-only
			STATUS current
			DESCRIPTION
				"Rogue onu mac Address"
			::= { sleEponOltEntry 31 }

		
		sleEponOltRogueDetectStatus OBJECT-TYPE
			SYNTAX INTEGER
				{
				detectRogueOnu(1),
				clearRogueOnu(2),
				foundRogueOnu(3),
				unknownRogueOnu(4),
				normalRogueOnu(5)
				}
			MAX-ACCESS read-only
			STATUS current
			DESCRIPTION
				"Rogue detect status, for V8500"
			::= { sleEponOltEntry 32 }

		
		sleEponOltMaxOnuCount OBJECT-TYPE
			SYNTAX INTEGER (1..64)
			MAX-ACCESS read-only
			STATUS current
			DESCRIPTION
				"max onu count, for V8500"
			::= { sleEponOltEntry 33 }

		
		sleEponOltActiveOnuCount OBJECT-TYPE
			SYNTAX INTEGER (1..64)
			MAX-ACCESS read-only
			STATUS current
			DESCRIPTION
				"actinve onu count, for V8500"
			::= { sleEponOltEntry 34 }

		
		sleEponOltInactiveOnuCount OBJECT-TYPE
			SYNTAX INTEGER (1..64)
			MAX-ACCESS read-only
			STATUS current
			DESCRIPTION
				"Inactive onu count, for V8500"
			::= { sleEponOltEntry 35 }

		
		sleEponOltInactiveAgingTime OBJECT-TYPE
			SYNTAX INTEGER (0 | 1..100)
			MAX-ACCESS read-only
			STATUS current
			DESCRIPTION
				"Inactive aging time"
			::= { sleEponOltEntry 36 }

		
		sleEponOltControl OBJECT IDENTIFIER ::= { sleEponOlt 2 }

		
		sleEponOltControlRequest OBJECT-TYPE
			SYNTAX INTEGER
				{
				setEponOltRegMode(1),
				setEponOltAdminStatus(2),
				setEponOltAttributes(3),
				setEponOltProfile(4),
				setEponOltAttributeSC(5),
				setEponOltUpgrade(6),
				setEponOltReset(7),
				setEponOltRssiStatus(8),
				setEponOltMaxDistance(9),
				setEponOltDhcpOption254Status(10),
				setEponOltSignalCheckStatus(11),
				setEponOltPonMode(12),
				setEponOltDiscardDlfMode(13),
				setEponOltFecConfig(14),
				setEponOltInactiveAgingTime(15),
				setEponOltResetPonMac(16)
				}
			MAX-ACCESS read-write
			STATUS current
			DESCRIPTION
				"The request of a user command"
			::= { sleEponOltControl 1 }

		
		sleEponOltControlStatus OBJECT-TYPE
			SYNTAX SleControlStatusType
			MAX-ACCESS read-only
			STATUS current
			DESCRIPTION
				"The status of user command"
			::= { sleEponOltControl 2 }

		
		sleEponOltControlTimer OBJECT-TYPE
			SYNTAX Gauge32
			MAX-ACCESS read-write
			STATUS current
			DESCRIPTION
				"The maximum time for the manager for a long running user command"
			::= { sleEponOltControl 3 }

		
		sleEponOltControlTimeStamp OBJECT-TYPE
			SYNTAX TimeTicks
			MAX-ACCESS read-only
			STATUS current
			DESCRIPTION
				"The time stamp of the last command(end of command)"
			::= { sleEponOltControl 4 }

		
		sleEponOltControlReqResult OBJECT-TYPE
			SYNTAX SleControlRequestResultType
			MAX-ACCESS read-only
			STATUS current
			DESCRIPTION
				"The result of the last user command"
			::= { sleEponOltControl 5 }

		
		sleEponOltControlOltIndex OBJECT-TYPE
			SYNTAX Integer32
			MAX-ACCESS read-write
			STATUS current
			DESCRIPTION
				"OLT port Index"
			::= { sleEponOltControl 6 }

		
		sleEponOltControlRegMode OBJECT-TYPE
			SYNTAX INTEGER
				{
				auto(1),
				manual(2),
				fixed(3),
				autoToManual(4),
				webBasedRegistry(5)
				}
			MAX-ACCESS read-write
			STATUS current
			DESCRIPTION
				"auto(1), manual(2), fixed(3) / DEFVAL : auto"
			DEFVAL { auto }
			::= { sleEponOltControl 7 }

		
		sleEponOltControlAdminStatus OBJECT-TYPE
			SYNTAX EnableFlag
			MAX-ACCESS read-write
			STATUS current
			DESCRIPTION
				"enable(1), disable(2)"
			::= { sleEponOltControl 8 }

		
		sleEponOltControlEncryptionPolicy OBJECT-TYPE
			SYNTAX INTEGER
				{
				disable(1),
				down(2),
				both(3)
				}
			MAX-ACCESS read-write
			STATUS current
			DESCRIPTION
				"disable(1), down(2), both(3) / DEFVAL : disable"
			DEFVAL { disable }
			::= { sleEponOltControl 9 }

		
		sleEponOltControlP2pAccessControl OBJECT-TYPE
			SYNTAX EnableFlag
			MAX-ACCESS read-write
			STATUS current
			DESCRIPTION
				"enable(1), disable(2)  / DEFVAL : disable "
			DEFVAL { disable }
			::= { sleEponOltControl 10 }

		
		sleEponOltControlDbaInternal OBJECT-TYPE
			SYNTAX EnableFlag
			MAX-ACCESS read-write
			STATUS current
			DESCRIPTION
				"enable(1), disable(2)  / DEFVAL : disable"
			DEFVAL { disable }
			::= { sleEponOltControl 11 }

		
		sleEponOltControlDbaCycle OBJECT-TYPE
			SYNTAX INTEGER (200..16777215)
			MAX-ACCESS read-write
			STATUS current
			DESCRIPTION
				"< 0 | 200..16777215>  / DEFVAL : 65536"
			DEFVAL { 65536 }
			::= { sleEponOltControl 12 }

		
		sleEponOltControlDbaDiscoveryFrequency OBJECT-TYPE
			SYNTAX INTEGER (1..65535)
			MAX-ACCESS read-write
			STATUS current
			DESCRIPTION
				"< 0 | 1..65535>  /DEFVAL : 1792"
			DEFVAL { 1792 }
			::= { sleEponOltControl 13 }

		
		sleEponOltControlDbaDiscoveryLength OBJECT-TYPE
			SYNTAX INTEGER (1..65535)
			MAX-ACCESS read-write
			STATUS current
			DESCRIPTION
				"< 0 | 1..65535>  /DEFVAL : 500"
			DEFVAL { 500 }
			::= { sleEponOltControl 14 }

		
		sleEponOltControlProfile OBJECT-TYPE
			SYNTAX OCTET STRING (SIZE (1..64))
			MAX-ACCESS read-write
			STATUS current
			DESCRIPTION
				"OLT port auto profile name"
			::= { sleEponOltControl 15 }

		
		sleEponOltControlSC OBJECT-TYPE
			SYNTAX EnableFlag
			MAX-ACCESS read-write
			STATUS current
			DESCRIPTION
				"Description."
			::= { sleEponOltControl 16 }

		
		sleEponOltControlSCAutoOnuBlock OBJECT-TYPE
			SYNTAX EnableFlag
			MAX-ACCESS read-write
			STATUS current
			DESCRIPTION
				"Description."
			::= { sleEponOltControl 17 }

		
		sleEponOltControlUpgradeFilename OBJECT-TYPE
			SYNTAX OCTET STRING (SIZE (1..64))
			MAX-ACCESS read-write
			STATUS current
			DESCRIPTION
				"Description."
			::= { sleEponOltControl 18 }

		
		sleEponOltControlKeyExchangeTimeout OBJECT-TYPE
			SYNTAX INTEGER (600..65535)
			MAX-ACCESS read-write
			STATUS current
			DESCRIPTION
				"Key Exchange Timeout"
			::= { sleEponOltControl 19 }

		
		sleEponOltControlRssiStatus OBJECT-TYPE
			SYNTAX EnableFlag
			MAX-ACCESS read-write
			STATUS current
			DESCRIPTION
				"Epon olt rssi disable/enable."
			::= { sleEponOltControl 20 }

		
		sleEponOltControlMaxDistance OBJECT-TYPE
			SYNTAX INTEGER (20..50)
			MAX-ACCESS read-write
			STATUS current
			DESCRIPTION
				"Olt max distance."
			::= { sleEponOltControl 21 }

		
		sleEponOltControlDhcpOption254Status OBJECT-TYPE
			SYNTAX EnableFlag
			MAX-ACCESS read-write
			STATUS current
			DESCRIPTION
				"Olt dhcp option254 status."
			::= { sleEponOltControl 22 }

		
		sleEponOltControlPonMode OBJECT-TYPE
			SYNTAX INTEGER
				{
				mixed(1),
				real(2),
				hybrid(3)
				}
			MAX-ACCESS read-write
			STATUS current
			DESCRIPTION
				"Olt pon mode."
			::= { sleEponOltControl 23 }

		
		sleEponOltControlDiscardDlfMode OBJECT-TYPE
			SYNTAX EnableFlag
			MAX-ACCESS read-write
			STATUS current
			DESCRIPTION
				"Olt discard DLF mode."
			::= { sleEponOltControl 24 }

		
		sleEponOltControlFecConfigDirection OBJECT-TYPE
			SYNTAX INTEGER
				{
				both(0),
				up(1),
				down(2)
				}
			MAX-ACCESS read-write
			STATUS current
			DESCRIPTION
				"Olt fec config direction."
			::= { sleEponOltControl 25 }

		
		sleEponOltControlFecConfigStatus OBJECT-TYPE
			SYNTAX EnableFlag
			MAX-ACCESS read-write
			STATUS current
			DESCRIPTION
				"Olt fec config status.."
			::= { sleEponOltControl 26 }

		
		sleEponOltControlInactiveAgingTime OBJECT-TYPE
			SYNTAX INTEGER (0 | 1..100)
			MAX-ACCESS read-write
			STATUS current
			DESCRIPTION
				"OLT inactive aging time"
			::= { sleEponOltControl 27 }

		
		sleEponOltNotification OBJECT IDENTIFIER ::= { sleEponOlt 3 }

		
		sleEponOltRegModeChanged NOTIFICATION-TYPE
			OBJECTS { sleEponOltControlRequest, sleEponOltControlTimeStamp, sleEponOltControlReqResult, sleEponOltControlOltIndex, sleEponOltControlRegMode
				 }
			STATUS current
			DESCRIPTION 
				"Description."
			::= { sleEponOltNotification 1 }

		
		sleEponOltAdminStatusChanged NOTIFICATION-TYPE
			OBJECTS { sleEponOltControlRequest, sleEponOltControlTimeStamp, sleEponOltControlReqResult, sleEponOltControlOltIndex, sleEponOltControlAdminStatus
				 }
			STATUS current
			DESCRIPTION 
				"Description."
			::= { sleEponOltNotification 2 }

		
		sleEponOltAttributesChanged NOTIFICATION-TYPE
			OBJECTS { sleEponOltControlRequest, sleEponOltControlTimeStamp, sleEponOltControlReqResult, sleEponOltControlOltIndex, sleEponOltControlDbaInternal, 
				sleEponOltControlDbaCycle, sleEponOltControlDbaDiscoveryFrequency, sleEponOltControlDbaDiscoveryLength }
			STATUS current
			DESCRIPTION 
				"Description."
			::= { sleEponOltNotification 3 }

		
		sleEponOltProfileChanged NOTIFICATION-TYPE
			OBJECTS { sleEponOltControlRequest, sleEponOltControlTimeStamp, sleEponOltControlReqResult, sleEponOltControlOltIndex, sleEponOltControlProfile
				 }
			STATUS current
			DESCRIPTION 
				"Description."
			::= { sleEponOltNotification 4 }

		
		sleEponOltSCChanged NOTIFICATION-TYPE
			OBJECTS { sleEponOltControlRequest, sleEponOltControlTimeStamp, sleEponOltControlReqResult, sleEponOltControlOltIndex, sleEponOltControlSC, 
				sleEponOltControlSCAutoOnuBlock }
			STATUS current
			DESCRIPTION 
				"Description."
			::= { sleEponOltNotification 5 }

		
		sleEponOltUpgraded NOTIFICATION-TYPE
			OBJECTS { sleEponOltControlRequest, sleEponOltControlTimeStamp, sleEponOltControlReqResult, sleEponOltControlOltIndex, sleEponOltControlUpgradeFilename
				 }
			STATUS current
			DESCRIPTION 
				"Description."
			::= { sleEponOltNotification 6 }

		
		sleEponOltReset NOTIFICATION-TYPE
			OBJECTS { sleEponOltControlRequest, sleEponOltControlTimeStamp, sleEponOltControlReqResult, sleEponOltControlOltIndex }
			STATUS current
			DESCRIPTION 
				"Description."
			::= { sleEponOltNotification 7 }

		
		sleEponOltRssiStatusChanged NOTIFICATION-TYPE
			OBJECTS { sleEponOltControlRequest, sleEponOltControlTimeStamp, sleEponOltControlReqResult, sleEponOltControlOltIndex, sleEponOltControlRssiStatus
				 }
			STATUS current
			DESCRIPTION 
				"Description."
			::= { sleEponOltNotification 8 }

		
		sleEponOltMaxDistanceChanged NOTIFICATION-TYPE
			OBJECTS { sleEponOltControlRequest, sleEponOltControlTimeStamp, sleEponOltControlReqResult, sleEponOltControlOltIndex, sleEponOltControlMaxDistance
				 }
			STATUS current
			DESCRIPTION 
				"Description."
			::= { sleEponOltNotification 9 }

		
		sleEponOltDhcpOpt254Changed NOTIFICATION-TYPE
			OBJECTS { sleEponOltControlRequest, sleEponOltControlTimeStamp, sleEponOltControlReqResult, sleEponOltControlOltIndex, sleEponOltControlDhcpOption254Status
				 }
			STATUS current
			DESCRIPTION 
				"Description."
			::= { sleEponOltNotification 10 }

		
		sleEponOltSignalCheckStatusChanged NOTIFICATION-TYPE
			OBJECTS { sleEponOltControlRequest, sleEponOltControlTimeStamp, sleEponOltControlReqResult, sleEponOltControlOltIndex, sleEponOltControlSC, 
				sleEponOltControlSCAutoOnuBlock }
			STATUS current
			DESCRIPTION 
				"Description."
			::= { sleEponOltNotification 11 }

		
		sleEponOltPonModeChanged NOTIFICATION-TYPE
			OBJECTS { sleEponOltControlRequest, sleEponOltControlTimeStamp, sleEponOltControlReqResult, sleEponOltControlOltIndex, sleEponOltControlPonMode
				 }
			STATUS current
			DESCRIPTION 
				"Description."
			::= { sleEponOltNotification 12 }

		
		sleEponOltDiscardDlfModeChanged NOTIFICATION-TYPE
			OBJECTS { sleEponOltControlRequest, sleEponOltControlTimeStamp, sleEponOltControlReqResult, sleEponOltControlOltIndex, sleEponOltControlDiscardDlfMode
				 }
			STATUS current
			DESCRIPTION 
				"Description."
			::= { sleEponOltNotification 13 }

		
		sleEponOltFecConfigChanged NOTIFICATION-TYPE
			OBJECTS { sleEponOltControlRequest, sleEponOltControlTimeStamp, sleEponOltControlReqResult, sleEponOltControlOltIndex, sleEponOltControlFecConfigDirection, 
				sleEponOltControlFecConfigStatus }
			STATUS current
			DESCRIPTION 
				"Description."
			::= { sleEponOltNotification 14 }

		
		sleEponOltInactiveAgingTimeChanged NOTIFICATION-TYPE
			OBJECTS { sleEponOltControlRequest, sleEponOltControlTimeStamp, sleEponOltControlReqResult, sleEponOltControlOltIndex, sleEponOltControlInactiveAgingTime
				 }
			STATUS current
			DESCRIPTION 
				"Description."
			::= { sleEponOltNotification 15 }

		
		sleEponOltPonMacReset NOTIFICATION-TYPE
			OBJECTS { sleEponOltControlRequest, sleEponOltControlTimeStamp, sleEponOltControlReqResult, sleEponOltControlOltIndex }
			STATUS current
			DESCRIPTION 
				"setEponOltPonMacReset"
			::= { sleEponOltNotification 16 }

		
		sleEponOltP2PTable OBJECT-TYPE
			SYNTAX SEQUENCE OF SleEponOltP2PEntry
			MAX-ACCESS not-accessible
			STATUS current
			DESCRIPTION
				"Description."
			::= { sleEponOlt 4 }

		
		sleEponOltP2PEntry OBJECT-TYPE
			SYNTAX SleEponOltP2PEntry
			MAX-ACCESS not-accessible
			STATUS current
			DESCRIPTION
				"Description."
			INDEX { sleEponOltIndex, sleEponOltP2PIndex }
			::= { sleEponOltP2PTable 1 }

		
		SleEponOltP2PEntry ::=
			SEQUENCE { 
				sleEponOltP2PIndex
					INTEGER,
				sleEponOltP2PEnable
					OCTET STRING,
				sleEponOltP2POnuID1
					Integer32,
				sleEponOltP2POnuID2
					Integer32
			 }

		sleEponOltP2PIndex OBJECT-TYPE
			SYNTAX INTEGER (1..20)
			MAX-ACCESS read-only
			STATUS current
			DESCRIPTION
				"p2p index"
			::= { sleEponOltP2PEntry 1 }

		
		sleEponOltP2PEnable OBJECT-TYPE
			SYNTAX OCTET STRING
			MAX-ACCESS read-only
			STATUS current
			DESCRIPTION
				"status of p2p access control : enable "
			::= { sleEponOltP2PEntry 2 }

		
		sleEponOltP2POnuID1 OBJECT-TYPE
			SYNTAX Integer32 (1..64)
			MAX-ACCESS read-only
			STATUS current
			DESCRIPTION
				"p2p onu id 1"
			::= { sleEponOltP2PEntry 3 }

		
		sleEponOltP2POnuID2 OBJECT-TYPE
			SYNTAX Integer32 (1..64)
			MAX-ACCESS read-only
			STATUS current
			DESCRIPTION
				"p2p onu id 2"
			::= { sleEponOltP2PEntry 4 }

		
		sleEponOltP2PControl OBJECT IDENTIFIER ::= { sleEponOlt 5 }

		
		sleEponOltP2PControlRequest OBJECT-TYPE
			SYNTAX INTEGER { setEponOltP2PAccessControl(1) }
			MAX-ACCESS read-write
			STATUS current
			DESCRIPTION
				"The request of a user command"
			::= { sleEponOltP2PControl 1 }

		
		sleEponOltP2PControlStatus OBJECT-TYPE
			SYNTAX SleControlStatusType
			MAX-ACCESS read-only
			STATUS current
			DESCRIPTION
				"The status of user command"
			::= { sleEponOltP2PControl 2 }

		
		sleEponOltP2PControlTimer OBJECT-TYPE
			SYNTAX Gauge32
			MAX-ACCESS read-write
			STATUS current
			DESCRIPTION
				"The maximum time for the manager for a long running user command"
			::= { sleEponOltP2PControl 3 }

		
		sleEponOltP2PControlTimeStamp OBJECT-TYPE
			SYNTAX TimeTicks
			MAX-ACCESS read-only
			STATUS current
			DESCRIPTION
				"The time stamp of the last command(end of command)"
			::= { sleEponOltP2PControl 4 }

		
		sleEponOltP2PControlReqResult OBJECT-TYPE
			SYNTAX SleControlRequestResultType
			MAX-ACCESS read-only
			STATUS current
			DESCRIPTION
				"The result of the last user command"
			::= { sleEponOltP2PControl 5 }

		
		sleEponOltP2PControlOltIndex OBJECT-TYPE
			SYNTAX Integer32
			MAX-ACCESS read-write
			STATUS current
			DESCRIPTION
				"OLT port Index"
			::= { sleEponOltP2PControl 6 }

		
		sleEponOltP2PControlEnable OBJECT-TYPE
			SYNTAX EnableFlag
			MAX-ACCESS read-write
			STATUS current
			DESCRIPTION
				"enable(1), disable(2)  / DEFVAL : disable "
			DEFVAL { disable }
			::= { sleEponOltP2PControl 7 }

		
		sleEponOltP2PControlOnuID1 OBJECT-TYPE
			SYNTAX Integer32 (1..64)
			MAX-ACCESS read-write
			STATUS current
			DESCRIPTION
				"P2p onu id 1."
			::= { sleEponOltP2PControl 8 }

		
		sleEponOltP2PControlOnuID2 OBJECT-TYPE
			SYNTAX Integer32 (1..64)
			MAX-ACCESS read-write
			STATUS current
			DESCRIPTION
				"P2p onu id 2."
			::= { sleEponOltP2PControl 9 }

		
		sleEponOltP2PNotification OBJECT IDENTIFIER ::= { sleEponOlt 6 }

		
		sleEponOltP2PAccessControlChanged NOTIFICATION-TYPE
			OBJECTS { sleEponOltP2PControlRequest, sleEponOltP2PControlTimeStamp, sleEponOltP2PControlReqResult, sleEponOltP2PControlOltIndex }
			STATUS current
			DESCRIPTION 
				"Description."
			::= { sleEponOltP2PNotification 1 }

		
		sleEponOltDMI OBJECT IDENTIFIER ::= { sleEponOlt 7 }

		
		sleEponOltDMITable OBJECT-TYPE
			SYNTAX SEQUENCE OF SleEponOltDMIEntry
			MAX-ACCESS not-accessible
			STATUS current
			DESCRIPTION
				"Description."
			::= { sleEponOltDMI 1 }

		
		sleEponOltDMIEntry OBJECT-TYPE
			SYNTAX SleEponOltDMIEntry
			MAX-ACCESS not-accessible
			STATUS current
			DESCRIPTION
				"Description."
			INDEX { sleEponOltIndex, sleEponOnuIndex }
			::= { sleEponOltDMITable 1 }

		
		SleEponOltDMIEntry ::=
			SEQUENCE { 
				sleEponOltDMITemper
					OCTET STRING,
				sleEponOltDMIVoltage
					OCTET STRING,
				sleEponOltDMITxBias
					OCTET STRING,
				sleEponOltDMITxPower
					OCTET STRING,
				sleEponOltDMIRxPower
					OCTET STRING
			 }

		sleEponOltDMITemper OBJECT-TYPE
			SYNTAX OCTET STRING
			MAX-ACCESS read-only
			STATUS current
			DESCRIPTION
				"onu DMI Temperature ,range is (-128 ~ 127.99 C)
				"
			::= { sleEponOltDMIEntry 1 }

		
		sleEponOltDMIVoltage OBJECT-TYPE
			SYNTAX OCTET STRING
			MAX-ACCESS read-only
			STATUS current
			DESCRIPTION
				"onu DMI voltage,range is (0 ~ 6.5535 V).
				
				"
			::= { sleEponOltDMIEntry 2 }

		
		sleEponOltDMITxBias OBJECT-TYPE
			SYNTAX OCTET STRING
			MAX-ACCESS read-only
			STATUS current
			DESCRIPTION
				"onu DMI txbias,range is (0 ~ 131 mA).
				"
			::= { sleEponOltDMIEntry 3 }

		
		sleEponOltDMITxPower OBJECT-TYPE
			SYNTAX OCTET STRING
			MAX-ACCESS read-only
			STATUS current
			DESCRIPTION
				"onu DMI txpower, range is (-40 ~ 8.1647 dBm).
				"
			::= { sleEponOltDMIEntry 4 }

		
		sleEponOltDMIRxPower OBJECT-TYPE
			SYNTAX OCTET STRING
			MAX-ACCESS read-only
			STATUS current
			DESCRIPTION
				"onu DMI rxpower,range is (-40 ~ 8.1647 dBm)."
			::= { sleEponOltDMIEntry 5 }

		
		sleEponOltDMIThresholdTable OBJECT-TYPE
			SYNTAX SEQUENCE OF SleEponOltDMIThresholdEntry
			MAX-ACCESS not-accessible
			STATUS current
			DESCRIPTION
				"Description."
			::= { sleEponOltDMI 2 }

		
		sleEponOltDMIThresholdEntry OBJECT-TYPE
			SYNTAX SleEponOltDMIThresholdEntry
			MAX-ACCESS not-accessible
			STATUS current
			DESCRIPTION
				"Description."
			INDEX { sleEponOltDMIModuleName }
			::= { sleEponOltDMIThresholdTable 1 }

		
		SleEponOltDMIThresholdEntry ::=
			SEQUENCE { 
				sleEponOltDMIModuleName
					OCTET STRING,
				sleEponOltDMIThresholdType
					INTEGER,
				sleEponOltDMIThresholdAlarmLow
					Integer32,
				sleEponOltDMIThresholdAlarmHigh
					Integer32,
				sleEponOltDMIThresholdWarnLow
					Integer32,
				sleEponOltDMIThresholdWarnHigh
					Integer32
			 }

		sleEponOltDMIModuleName OBJECT-TYPE
			SYNTAX OCTET STRING
			MAX-ACCESS read-only
			STATUS current
			DESCRIPTION
				"Module name"
			::= { sleEponOltDMIThresholdEntry 1 }

		
		sleEponOltDMIThresholdType OBJECT-TYPE
			SYNTAX INTEGER { rxPower(5) }
			MAX-ACCESS read-only
			STATUS current
			DESCRIPTION
				"Threshold type, always be rx power"
			::= { sleEponOltDMIThresholdEntry 2 }

		
		sleEponOltDMIThresholdAlarmLow OBJECT-TYPE
			SYNTAX Integer32
			MAX-ACCESS read-only
			STATUS current
			DESCRIPTION
				"Low value of alarm threshold,it must be devided by 10000."
			::= { sleEponOltDMIThresholdEntry 3 }

		
		sleEponOltDMIThresholdAlarmHigh OBJECT-TYPE
			SYNTAX Integer32
			MAX-ACCESS read-only
			STATUS current
			DESCRIPTION
				"High value of alarm threshold,it must be devided by 10000."
			::= { sleEponOltDMIThresholdEntry 4 }

		
		sleEponOltDMIThresholdWarnLow OBJECT-TYPE
			SYNTAX Integer32
			MAX-ACCESS read-only
			STATUS current
			DESCRIPTION
				"Low value of warn threshold,it must be devided by 10000."
			::= { sleEponOltDMIThresholdEntry 5 }

		
		sleEponOltDMIThresholdWarnHigh OBJECT-TYPE
			SYNTAX Integer32
			MAX-ACCESS read-only
			STATUS current
			DESCRIPTION
				"High value of warn threshold,it must be devided by 10000."
			::= { sleEponOltDMIThresholdEntry 6 }

		
		sleEponOltDMIThresholdControl OBJECT IDENTIFIER ::= { sleEponOltDMI 3 }

		
		sleEponOltDMIThresholdControlRequest OBJECT-TYPE
			SYNTAX INTEGER
				{
				createThreshold(1),
				modifyThreshold(2),
				deleteThreshold(3)
				}
			MAX-ACCESS read-write
			STATUS current
			DESCRIPTION
				"Request of user command"
			::= { sleEponOltDMIThresholdControl 1 }

		
		sleEponOltDMIThresholdControlStatus OBJECT-TYPE
			SYNTAX SleControlStatusType
			MAX-ACCESS read-only
			STATUS current
			DESCRIPTION
				"Status of a contral command"
			::= { sleEponOltDMIThresholdControl 2 }

		
		sleEponOltDMIThresholdControlTimer OBJECT-TYPE
			SYNTAX Gauge32
			MAX-ACCESS read-write
			STATUS current
			DESCRIPTION
				"Timer of control command"
			::= { sleEponOltDMIThresholdControl 3 }

		
		sleEponOltDMIThresholdControlTimeStamp OBJECT-TYPE
			SYNTAX TimeTicks
			MAX-ACCESS read-only
			STATUS current
			DESCRIPTION
				"Time stamp of control command"
			::= { sleEponOltDMIThresholdControl 4 }

		
		sleEponOltDMIThresholdControlReqResult OBJECT-TYPE
			SYNTAX SleControlRequestResultType
			MAX-ACCESS read-only
			STATUS current
			DESCRIPTION
				"Result of a control command"
			::= { sleEponOltDMIThresholdControl 5 }

		
		sleEponOltDMIThresholdControlModuleName OBJECT-TYPE
			SYNTAX OCTET STRING
			MAX-ACCESS read-write
			STATUS current
			DESCRIPTION
				"module name"
			::= { sleEponOltDMIThresholdControl 6 }

		
		sleEponOltDMIThresholdControlValueType OBJECT-TYPE
			SYNTAX INTEGER
				{
				rxPowerWarn(9),
				rxPowerAlarm(10)
				}
			MAX-ACCESS read-write
			STATUS current
			DESCRIPTION
				"threshold type, so far always rx power"
			::= { sleEponOltDMIThresholdControl 7 }

		
		sleEponOltDMIThresholdControlLowValue OBJECT-TYPE
			SYNTAX Integer32
			MAX-ACCESS read-write
			STATUS current
			DESCRIPTION
				"low value of threshold, must be multiplying real value by 10000"
			::= { sleEponOltDMIThresholdControl 8 }

		
		sleEponOltDMIThresholdControlHighValue OBJECT-TYPE
			SYNTAX Integer32
			MAX-ACCESS read-write
			STATUS current
			DESCRIPTION
				"high value of threshold, must be multiplying real value by 10000"
			::= { sleEponOltDMIThresholdControl 9 }

		
		sleEponOltDMIThresholdNotification OBJECT IDENTIFIER ::= { sleEponOltDMI 4 }

		
		sleEponOltDMIThresholdChanged NOTIFICATION-TYPE
			OBJECTS { sleEponOltDMIThresholdControlRequest, sleEponOltDMIThresholdControlTimeStamp, sleEponOltDMIThresholdControlReqResult, sleEponOltDMIThresholdControlModuleName }
			STATUS current
			DESCRIPTION 
				"Description."
			::= { sleEponOltDMIThresholdNotification 1 }

		
		sleEponOltDMIThresholdPortTable OBJECT-TYPE
			SYNTAX SEQUENCE OF SleEponOltDMIThresholdPortEntry
			MAX-ACCESS not-accessible
			STATUS current
			DESCRIPTION
				"Description."
			::= { sleEponOltDMI 5 }

		
		sleEponOltDMIThresholdPortEntry OBJECT-TYPE
			SYNTAX SleEponOltDMIThresholdPortEntry
			MAX-ACCESS not-accessible
			STATUS current
			DESCRIPTION
				"Description."
			INDEX { sleEponOltIndex }
			::= { sleEponOltDMIThresholdPortTable 1 }

		
		SleEponOltDMIThresholdPortEntry ::=
			SEQUENCE { 
				sleEponOltDMIThresholdPortRxPowerAlarmLow
					Integer32,
				sleEponOltDMIThresholdPortRxPowerAlarmHigh
					Integer32,
				sleEponOltDMIThresholdPortRxPowerWarnLow
					Integer32,
				sleEponOltDMIThresholdPortRxPowerWarnHigh
					Integer32
			 }

		sleEponOltDMIThresholdPortRxPowerAlarmLow OBJECT-TYPE
			SYNTAX Integer32
			MAX-ACCESS read-only
			STATUS current
			DESCRIPTION
				"Low value of alarm threshold
				It must be devided by 10000
				"
			::= { sleEponOltDMIThresholdPortEntry 1 }

		
		sleEponOltDMIThresholdPortRxPowerAlarmHigh OBJECT-TYPE
			SYNTAX Integer32
			MAX-ACCESS read-only
			STATUS current
			DESCRIPTION
				"High value of alarm threshold
				It must be devided by 10000
				"
			::= { sleEponOltDMIThresholdPortEntry 2 }

		
		sleEponOltDMIThresholdPortRxPowerWarnLow OBJECT-TYPE
			SYNTAX Integer32
			MAX-ACCESS read-only
			STATUS current
			DESCRIPTION
				"Low value of warn threshold
				It must be devided by 10000"
			::= { sleEponOltDMIThresholdPortEntry 3 }

		
		sleEponOltDMIThresholdPortRxPowerWarnHigh OBJECT-TYPE
			SYNTAX Integer32
			MAX-ACCESS read-only
			STATUS current
			DESCRIPTION
				"High value of warn threshold
				It must be devided by 10000"
			::= { sleEponOltDMIThresholdPortEntry 4 }

		
		sleEponOltDMIThresholdPortControl OBJECT IDENTIFIER ::= { sleEponOltDMI 6 }

		
		sleEponOltDMIThresholdPortControlRequest OBJECT-TYPE
			SYNTAX INTEGER
				{
				setEponOltDMIThreshold(1),
				noEponOltDMIThreshold(2)
				}
			MAX-ACCESS read-write
			STATUS current
			DESCRIPTION
				"Request of user command"
			::= { sleEponOltDMIThresholdPortControl 1 }

		
		sleEponOltDMIThresholdPortControlStatus OBJECT-TYPE
			SYNTAX SleControlStatusType
			MAX-ACCESS read-only
			STATUS current
			DESCRIPTION
				"Status of a contral command"
			::= { sleEponOltDMIThresholdPortControl 2 }

		
		sleEponOltDMIThresholdPortControlTimer OBJECT-TYPE
			SYNTAX Gauge32
			MAX-ACCESS read-write
			STATUS current
			DESCRIPTION
				"Timer of control command"
			::= { sleEponOltDMIThresholdPortControl 3 }

		
		sleEponOltDMIThresholdPortControlTimeStamp OBJECT-TYPE
			SYNTAX TimeTicks
			MAX-ACCESS read-only
			STATUS current
			DESCRIPTION
				"Time stamp of control command"
			::= { sleEponOltDMIThresholdPortControl 4 }

		
		sleEponOltDMIThresholdPortControlReqResult OBJECT-TYPE
			SYNTAX SleControlRequestResultType
			MAX-ACCESS read-only
			STATUS current
			DESCRIPTION
				"Result of a control command"
			::= { sleEponOltDMIThresholdPortControl 5 }

		
		sleEponOltDMIThresholdPortControlOltIndex OBJECT-TYPE
			SYNTAX INTEGER
			MAX-ACCESS read-write
			STATUS current
			DESCRIPTION
				"OLT Port Index"
			::= { sleEponOltDMIThresholdPortControl 6 }

		
		sleEponOltDMIThresholdPortControlType OBJECT-TYPE
			SYNTAX INTEGER
				{
				temper(1),
				voltage(2),
				txbias(3),
				txpower(4),
				rxpower(5)
				}
			MAX-ACCESS read-write
			STATUS current
			DESCRIPTION
				"OLT DMI Monitor type"
			::= { sleEponOltDMIThresholdPortControl 7 }

		
		sleEponOltDMIThresholdPortControlMode OBJECT-TYPE
			SYNTAX INTEGER
				{
				warning(1),
				alarm(2)
				}
			MAX-ACCESS read-write
			STATUS current
			DESCRIPTION
				"OLT DMI monitor threshold mode is alarm or warning"
			::= { sleEponOltDMIThresholdPortControl 8 }

		
		sleEponOltDMIThresholdPortControlLowValue OBJECT-TYPE
			SYNTAX Integer32
			MAX-ACCESS read-write
			STATUS current
			DESCRIPTION
				"It must multiplied by 10000 and less than high threshold.
				rxpower threshold (-40 ~ 8.1647 dBm)"
			::= { sleEponOltDMIThresholdPortControl 9 }

		
		sleEponOltDMIThresholdPortControlHighValue OBJECT-TYPE
			SYNTAX Integer32
			MAX-ACCESS read-write
			STATUS current
			DESCRIPTION
				"It must multiplied by 10000 and less than high threshold.
				rxpower threshold (-40 ~ 8.1647 dBm)"
			::= { sleEponOltDMIThresholdPortControl 10 }

		
		sleEponOltDMIThresholdPortNotification OBJECT IDENTIFIER ::= { sleEponOltDMI 7 }

		
		sleEponOltDMIThresholdPortChanged NOTIFICATION-TYPE
			OBJECTS { sleEponOltDMIThresholdPortControlRequest, sleEponOltDMIThresholdPortControlTimeStamp, sleEponOltDMIThresholdPortControlReqResult, sleEponOltDMIThresholdPortControlOltIndex, sleEponOltDMIThresholdPortControlType, 
				sleEponOltDMIThresholdPortControlMode, sleEponOltDMIThresholdPortControlLowValue, sleEponOltDMIThresholdPortControlHighValue }
			STATUS current
			DESCRIPTION 
				"Description."
			::= { sleEponOltDMIThresholdPortNotification 1 }

		
		sleEponOltSlot OBJECT IDENTIFIER ::= { sleEponOlt 8 }

		
		sleEponOltSlotTable OBJECT-TYPE
			SYNTAX SEQUENCE OF SleEponOltSlotEntry
			MAX-ACCESS not-accessible
			STATUS current
			DESCRIPTION
				"Description."
			::= { sleEponOltSlot 1 }

		
		sleEponOltSlotEntry OBJECT-TYPE
			SYNTAX SleEponOltSlotEntry
			MAX-ACCESS not-accessible
			STATUS current
			DESCRIPTION
				"Description."
			INDEX { sleEponOltSlotIndex }
			::= { sleEponOltSlotTable 1 }

		
		SleEponOltSlotEntry ::=
			SEQUENCE { 
				sleEponOltSlotIndex
					INTEGER,
				sleEponOltSlotType
					INTEGER,
				sleEponOltSlotNOSVer
					OCTET STRING,
				sleEponOltSlotStatus
					INTEGER,
				sleEponOltSlotConnectionFlag
					EnableFlag,
				sleEponOltSlotChip0UpgradeStatus
					INTEGER,
				sleEponOltSlotChip1UpgradeStatus
					INTEGER
			 }

		sleEponOltSlotIndex OBJECT-TYPE
			SYNTAX INTEGER (1..12)
			MAX-ACCESS read-only
			STATUS current
			DESCRIPTION
				"slot index"
			::= { sleEponOltSlotEntry 1 }

		
		sleEponOltSlotType OBJECT-TYPE
			SYNTAX INTEGER
				{
				unknownType(0),
				siuGe4(1),
				siuGpon4(2),
				niuGe8(3),
				sfu(4),
				niu10ge2plus(5),
				siuGe24(7),
				siuFe48(8),
				niu10ge2(9),
				siuGe48(10),
				iu10ge48(11),
				iu10ge8(12),
				iuGepon8(13),
				iu10gepon8(14),
				iu10ge44(15)
				}
			MAX-ACCESS read-only
			STATUS current
			DESCRIPTION
				"slot type"
			::= { sleEponOltSlotEntry 2 }

		
		sleEponOltSlotNOSVer OBJECT-TYPE
			SYNTAX OCTET STRING
			MAX-ACCESS read-only
			STATUS current
			DESCRIPTION
				"NOS version"
			::= { sleEponOltSlotEntry 3 }

		
		sleEponOltSlotStatus OBJECT-TYPE
			SYNTAX INTEGER
				{
				nonCreate(0),
				disconnect(1),
				waiting(2),
				connect(3),
				monitor(4),
				close(5),
				end(6)
				}
			MAX-ACCESS read-only
			STATUS current
			DESCRIPTION
				"slot status"
			::= { sleEponOltSlotEntry 4 }

		
		sleEponOltSlotConnectionFlag OBJECT-TYPE
			SYNTAX EnableFlag
			MAX-ACCESS read-only
			STATUS current
			DESCRIPTION
				"slot connection flag"
			::= { sleEponOltSlotEntry 5 }

		
		sleEponOltSlotChip0UpgradeStatus OBJECT-TYPE
			SYNTAX INTEGER
				{
				notUpgraded(0),
				upgradeWaiting(1),
				upgradeProceeding(2),
				upgradeDone(3),
				upgradeFailed(4),
				upgradeSameVersion(5),
				upgradeNewestVersion(6),
				upgradeUnavailable(7)
				}
			MAX-ACCESS read-only
			STATUS current
			DESCRIPTION
				"olt chip0 upgrade status,for V8500"
			::= { sleEponOltSlotEntry 6 }

		
		sleEponOltSlotChip1UpgradeStatus OBJECT-TYPE
			SYNTAX INTEGER
				{
				notUpgraded(0),
				upgradeWaiting(1),
				upgradeProceeding(2),
				upgradeDone(3),
				upgradeFailed(4),
				upgradeSameVersion(5),
				upgradeNewestVersion(6),
				upgradeUnavailable(7)
				}
			MAX-ACCESS read-only
			STATUS current
			DESCRIPTION
				"olt chip1 upgrade status,for V8500"
			::= { sleEponOltSlotEntry 7 }

		
		sleEponOltSlotControl OBJECT IDENTIFIER ::= { sleEponOltSlot 2 }

		
		sleEponOltSlotControlRequest OBJECT-TYPE
			SYNTAX INTEGER { fwUpgrade(1) }
			MAX-ACCESS read-write
			STATUS current
			DESCRIPTION
				"Request of user command"
			::= { sleEponOltSlotControl 1 }

		
		sleEponOltSlotControlStatus OBJECT-TYPE
			SYNTAX SleControlStatusType
			MAX-ACCESS read-only
			STATUS current
			DESCRIPTION
				"Status of a contral command"
			::= { sleEponOltSlotControl 2 }

		
		sleEponOltSlotControlTimer OBJECT-TYPE
			SYNTAX Gauge32
			MAX-ACCESS read-write
			STATUS current
			DESCRIPTION
				"Timer of control command"
			::= { sleEponOltSlotControl 3 }

		
		sleEponOltSlotControlTimeStamp OBJECT-TYPE
			SYNTAX TimeTicks
			MAX-ACCESS read-only
			STATUS current
			DESCRIPTION
				"Time stamp of control command"
			::= { sleEponOltSlotControl 4 }

		
		sleEponOltSlotControlReqResult OBJECT-TYPE
			SYNTAX SleControlRequestResultType
			MAX-ACCESS read-only
			STATUS current
			DESCRIPTION
				"Result of a control command"
			::= { sleEponOltSlotControl 5 }

		
		sleEponOltSlotControlIndex OBJECT-TYPE
			SYNTAX INTEGER (1..12)
			MAX-ACCESS read-write
			STATUS current
			DESCRIPTION
				"slot index"
			::= { sleEponOltSlotControl 6 }

		
		sleEponOltSlotControlUpgradePath OBJECT-TYPE
			SYNTAX OCTET STRING
			MAX-ACCESS read-write
			STATUS current
			DESCRIPTION
				"slot upgrade file path"
			::= { sleEponOltSlotControl 7 }

		
		sleEponOltSlotNotification OBJECT IDENTIFIER ::= { sleEponOltSlot 3 }

		
		sleEponOltSlotFWUpgrade NOTIFICATION-TYPE
			OBJECTS { sleEponOltSlotControlRequest, sleEponOltSlotControlTimeStamp, sleEponOltSlotControlReqResult, sleEponOltSlotControlIndex, sleEponOltSlotControlUpgradePath
				 }
			STATUS current
			DESCRIPTION 
				"Description."
			::= { sleEponOltSlotNotification 1 }

		
		sleEponOnu OBJECT IDENTIFIER ::= { sleEpon 3 }

		
		sleEponOnuTable OBJECT-TYPE
			SYNTAX SEQUENCE OF SleEponOnuEntry
			MAX-ACCESS not-accessible
			STATUS current
			DESCRIPTION
				"Description."
			::= { sleEponOnu 1 }

		
		sleEponOnuEntry OBJECT-TYPE
			SYNTAX SleEponOnuEntry
			MAX-ACCESS not-accessible
			STATUS current
			DESCRIPTION
				"Description."
			INDEX { sleEponOltIndex, sleEponOnuIndex }
			::= { sleEponOnuTable 1 }

		
		SleEponOnuEntry ::=
			SEQUENCE { 
				sleEponOnuIndex
					INTEGER,
				sleEponOnuLlid
					INTEGER,
				sleEponOnuRegMode
					INTEGER,
				sleEponOnuStatus
					INTEGER,
				sleEponOnuMacAddress
					MacAddress,
				sleEponOnuRtt
					INTEGER,
				sleEponOnuDescription
					OCTET STRING,
				sleEponOnuProfile
					OCTET STRING,
				sleEponOnuLoopbackProvision
					INTEGER,
				sleEponOnuVendor
					OCTET STRING,
				sleEponOnuFirmwareRev
					OCTET STRING,
				sleEponOnuTxPowerOffTimer
					INTEGER,
				sleEponOnuLgPathStatus
					INTEGER,
				sleEponOnuModelType
					OCTET STRING,
				sleEponOnuSipGlobalConfigMode
					INTEGER,
				sleEponOnuSipGlobalConfigIp
					IpAddress,
				sleEponOnuSipGlobalConfigNetmask
					IpAddress,
				sleEponOnuSipGlobalConfigGateway
					IpAddress,
				sleEponOnuSipGlobalUserName
					OCTET STRING,
				sleEponOnuSipGlobalPasswd
					OCTET STRING,
				sleEponOnuSipGlobalConfigVid
					INTEGER,
				sleEponOnuRxPower
					Gauge32,
				sleEponOnuRxPowerAlarmStatus
					INTEGER,
				sleEponOnuRssiInfo
					OCTET STRING,
				sleEponOnuLoopDetectUnblockStatus
					INTEGER,
				sleEponOnuUpgradeStatus
					INTEGER,
				sleEponOnuOltRssiStatus
					INTEGER,
				sleEponOnuOltRssiInfo
					OCTET STRING,
				sleEponOnuMultiLlid
					INTEGER,
				sleEponOnuMultiMacAddress
					MacAddress,
				sleEponOltDBAMutilLLidLinkOperate
					INTEGER,
				sleEponOnuPonMode
					INTEGER,
				sleEponOnuFecConfigDirection
					INTEGER,
				sleEponOnuFecConfigStatus
					EnableFlag,
				sleEponOnuFWVerInteger
					Integer32,
				sleEponOnuOltIndex
					Integer32,
				sleEponOnuMaxHost
					Integer32,
				sleEponOnuDcVoltage
					OCTET STRING,
				sleEponOnuBlockStatus
					OCTET STRING,
				sleEponOnuDistance
					Integer32,
				sleEponOnuChipId
					Integer32,
				sleEponOnu10GMpcpRate
					OCTET STRING,
				sleEponOnu10GMpcpLlid
					Integer32,
				sleEponOnu10GMpcpDiscover
					OCTET STRING,
				sleEponOnu10GMpcpUpTunnelID
					Integer32,
				sleEponOnu10GMpcpDnTunnelID
					Integer32,
				sleEponOnu10GOAMDiscoverStatus
					OCTET STRING,
				sleEponOnu10GOAMOUI
					Integer32,
				sleEponOnu10GOAMFWVersion
					Integer32,
				sleEponOnu10GOAMProductID
					Integer32,
				sleEponOnu10GOAMChipID
					Integer32,
				sleEponOnu10GOAMChipVersion
					Integer32,
				sleEponOnuRstpBridgePri
					Integer32,
				sleEponOnuRstpBridgeMode
					OCTET STRING,
				sleEponOnuRstpRootMaxAge
					Integer32,
				sleEponOnuRootHelloTime
					Integer32,
				sleEponOnuRootForwardDelay
					Integer32,
				sleEponOnuPortsCount
					Integer32,
				sleEponOnuLoopbackFrameSend
					Integer32,
				sleEponOnuLoopbackFrameRec
					Integer32,
				sleEponOnuLoopbackFrameCorrupt
					Integer32,
				sleEponOnuLoopbackMinDelay
					Integer32,
				sleEponOnuLoopbackMaxDelay
					Integer32,
				sleEponOnuLoopbackAvrDelay
					Integer32,
				sleEponOnuPortAlarm
					Integer32,
				sleEponOnuModelName
					OCTET STRING,
				sleEponOnuStormControlEnable
					EnableFlag,
				sleEponOnuStormControlBroadcast
					Integer32,
				sleEponOnuStormControlMulticast
					Integer32,
				sleEponOnuStormControlUnknownUnicast
					Integer32,
				sleEponOnuLlidIndex
					Integer32,
				sleEponOnuDistanceInitial
					Integer32,
				sleEponOnuDistanceDiff
					Integer32,
				sleEponOnuRegisterTime
					OCTET STRING
			 }

		sleEponOnuIndex OBJECT-TYPE
			SYNTAX INTEGER (1..64)
			MAX-ACCESS read-only
			STATUS current
			DESCRIPTION
				"ONU Index"
			::= { sleEponOnuEntry 1 }

		
		sleEponOnuLlid OBJECT-TYPE
			SYNTAX INTEGER (1..64)
			MAX-ACCESS read-only
			STATUS current
			DESCRIPTION
				"ONU LLID"
			::= { sleEponOnuEntry 2 }

		
		sleEponOnuRegMode OBJECT-TYPE
			SYNTAX INTEGER
				{
				auto(1),
				manual(2),
				static(3)
				}
			MAX-ACCESS read-only
			STATUS current
			DESCRIPTION
				"ONU registration mode"
			DEFVAL { auto }
			::= { sleEponOnuEntry 3 }

		
		sleEponOnuStatus OBJECT-TYPE
			SYNTAX INTEGER
				{
				inactive(1),
				deny(2),
				block(3),
				active(4),
				reset(5)
				}
			MAX-ACCESS read-only
			STATUS current
			DESCRIPTION
				"ONU current status"
			::= { sleEponOnuEntry 4 }

		
		sleEponOnuMacAddress OBJECT-TYPE
			SYNTAX MacAddress
			MAX-ACCESS read-only
			STATUS current
			DESCRIPTION
				"ONU Hardware address"
			::= { sleEponOnuEntry 5 }

		
		sleEponOnuRtt OBJECT-TYPE
			SYNTAX INTEGER
			MAX-ACCESS read-only
			STATUS current
			DESCRIPTION
				"ONU Round Trip Time"
			::= { sleEponOnuEntry 6 }

		
		sleEponOnuDescription OBJECT-TYPE
			SYNTAX OCTET STRING (SIZE (1..64))
			MAX-ACCESS read-only
			STATUS current
			DESCRIPTION
				"ONU Description"
			::= { sleEponOnuEntry 7 }

		
		sleEponOnuProfile OBJECT-TYPE
			SYNTAX OCTET STRING (SIZE (1..64))
			MAX-ACCESS read-only
			STATUS current
			DESCRIPTION
				"ONU assigned-profile"
			::= { sleEponOnuEntry 8 }

		
		sleEponOnuLoopbackProvision OBJECT-TYPE
			SYNTAX INTEGER
			MAX-ACCESS read-only
			STATUS current
			DESCRIPTION
				"ONU loopback test result
				-2 : not exist
				-1 : fail
				 X > 0  : Time.
				"
			::= { sleEponOnuEntry 9 }

		
		sleEponOnuVendor OBJECT-TYPE
			SYNTAX OCTET STRING
			MAX-ACCESS read-only
			STATUS current
			DESCRIPTION
				"The name of ONU vendor"
			::= { sleEponOnuEntry 10 }

		
		sleEponOnuFirmwareRev OBJECT-TYPE
			SYNTAX OCTET STRING
			MAX-ACCESS read-only
			STATUS current
			DESCRIPTION
				"The vendor-specific firmware revision"
			::= { sleEponOnuEntry 11 }

		
		sleEponOnuTxPowerOffTimer OBJECT-TYPE
			SYNTAX INTEGER (0 | 10..65535)
			MAX-ACCESS read-only
			STATUS current
			DESCRIPTION
				"Description."
			::= { sleEponOnuEntry 12 }

		
		sleEponOnuLgPathStatus OBJECT-TYPE
			SYNTAX INTEGER
			MAX-ACCESS read-only
			STATUS current
			DESCRIPTION
				"Description."
			::= { sleEponOnuEntry 13 }

		
		sleEponOnuModelType OBJECT-TYPE
			SYNTAX OCTET STRING (SIZE (1..32))
			MAX-ACCESS read-only
			STATUS current
			DESCRIPTION
				"Description."
			::= { sleEponOnuEntry 14 }

		
		sleEponOnuSipGlobalConfigMode OBJECT-TYPE
			SYNTAX INTEGER
				{
				ip(0),
				dhcp(1),
				pppoe(2)
				}
			MAX-ACCESS read-only
			STATUS current
			DESCRIPTION
				"Description."
			::= { sleEponOnuEntry 15 }

		
		sleEponOnuSipGlobalConfigIp OBJECT-TYPE
			SYNTAX IpAddress
			MAX-ACCESS read-only
			STATUS current
			DESCRIPTION
				"Description."
			::= { sleEponOnuEntry 16 }

		
		sleEponOnuSipGlobalConfigNetmask OBJECT-TYPE
			SYNTAX IpAddress
			MAX-ACCESS read-only
			STATUS current
			DESCRIPTION
				"Description."
			::= { sleEponOnuEntry 17 }

		
		sleEponOnuSipGlobalConfigGateway OBJECT-TYPE
			SYNTAX IpAddress
			MAX-ACCESS read-only
			STATUS current
			DESCRIPTION
				"Description."
			::= { sleEponOnuEntry 18 }

		
		sleEponOnuSipGlobalUserName OBJECT-TYPE
			SYNTAX OCTET STRING (SIZE (0..32))
			MAX-ACCESS read-only
			STATUS current
			DESCRIPTION
				"Description."
			::= { sleEponOnuEntry 19 }

		
		sleEponOnuSipGlobalPasswd OBJECT-TYPE
			SYNTAX OCTET STRING (SIZE (0..32))
			MAX-ACCESS read-only
			STATUS current
			DESCRIPTION
				"Description."
			::= { sleEponOnuEntry 20 }

		
		sleEponOnuSipGlobalConfigVid OBJECT-TYPE
			SYNTAX INTEGER
			MAX-ACCESS read-only
			STATUS current
			DESCRIPTION
				"Description."
			::= { sleEponOnuEntry 21 }

		
		sleEponOnuRxPower OBJECT-TYPE
			SYNTAX Gauge32
			MAX-ACCESS read-only
			STATUS current
			DESCRIPTION
				"Description."
			::= { sleEponOnuEntry 22 }

		
		sleEponOnuRxPowerAlarmStatus OBJECT-TYPE
			SYNTAX INTEGER
			MAX-ACCESS read-write
			STATUS current
			DESCRIPTION
				"Onu Rx Optical power alarm state of olt-side.
				1: RX Optical Power Alarm - Caution (orange)
				2: RX Optical Power Alarm cleard - OK (Green)
				"
			::= { sleEponOnuEntry 23 }

		
		sleEponOnuRssiInfo OBJECT-TYPE
			SYNTAX OCTET STRING
			MAX-ACCESS read-only
			STATUS current
			DESCRIPTION
				"Epon onu rssi-info."
			::= { sleEponOnuEntry 24 }

		
		sleEponOnuLoopDetectUnblockStatus OBJECT-TYPE
			SYNTAX INTEGER
				{
				blocked(1),
				unblocked(2)
				}
			MAX-ACCESS read-only
			STATUS current
			DESCRIPTION
				"Epon onu loopdetect unblock status."
			::= { sleEponOnuEntry 25 }

		
		sleEponOnuUpgradeStatus OBJECT-TYPE
			SYNTAX INTEGER
				{
				notUpgrade(1),
				inactiveONT(2),
				waitingUpgrade(3),
				firmwareSending(4),
				firmwareSend(5),
				writingFlashOnOnu(6),
				upgradeOK(7),
				upgradeFail(8)
				}
			MAX-ACCESS read-only
			STATUS current
			DESCRIPTION
				"Onu upgrade state."
			::= { sleEponOnuEntry 26 }

		
		sleEponOnuOltRssiStatus OBJECT-TYPE
			SYNTAX INTEGER
				{
				na(0),
				enable(1),
				disable(2),
				average(3)
				}
			MAX-ACCESS read-only
			STATUS current
			DESCRIPTION
				"Epon olt rssi-info."
			::= { sleEponOnuEntry 27 }

		
		sleEponOnuOltRssiInfo OBJECT-TYPE
			SYNTAX OCTET STRING
			MAX-ACCESS read-only
			STATUS current
			DESCRIPTION
				"Epon olt rssi-info value."
			::= { sleEponOnuEntry 28 }

		
		sleEponOnuMultiLlid OBJECT-TYPE
			SYNTAX INTEGER (1..64)
			MAX-ACCESS read-only
			STATUS current
			DESCRIPTION
				"ONU Multi LLID"
			::= { sleEponOnuEntry 29 }

		
		sleEponOnuMultiMacAddress OBJECT-TYPE
			SYNTAX MacAddress
			MAX-ACCESS read-only
			STATUS current
			DESCRIPTION
				"ONU Hardware address"
			::= { sleEponOnuEntry 30 }

		
		sleEponOltDBAMutilLLidLinkOperate OBJECT-TYPE
			SYNTAX INTEGER
				{
				disable(0),
				enable(1)
				}
			MAX-ACCESS read-write
			STATUS current
			DESCRIPTION
				"DBA multi llid link."
			::= { sleEponOnuEntry 31 }

		
		sleEponOnuPonMode OBJECT-TYPE
			SYNTAX INTEGER
				{
				mixed(1),
				hybrid(2),
				real(3),
				unknow(4)
				}
			MAX-ACCESS read-write
			STATUS current
			DESCRIPTION
				"Description."
			::= { sleEponOnuEntry 32 }

		
		sleEponOnuFecConfigDirection OBJECT-TYPE
			SYNTAX INTEGER
				{
				up(1),
				down(2),
				both(3)
				}
			MAX-ACCESS read-only
			STATUS current
			DESCRIPTION
				"Description."
			::= { sleEponOnuEntry 33 }

		
		sleEponOnuFecConfigStatus OBJECT-TYPE
			SYNTAX EnableFlag
			MAX-ACCESS read-only
			STATUS current
			DESCRIPTION
				"Description."
			::= { sleEponOnuEntry 34 }

		
		sleEponOnuFWVerInteger OBJECT-TYPE
			SYNTAX Integer32
			MAX-ACCESS read-only
			STATUS current
			DESCRIPTION
				"Description."
			::= { sleEponOnuEntry 35 }

		
		sleEponOnuOltIndex OBJECT-TYPE
			SYNTAX Integer32
			MAX-ACCESS read-only
			STATUS current
			DESCRIPTION
				"Description."
			::= { sleEponOnuEntry 36 }

		
		sleEponOnuMaxHost OBJECT-TYPE
			SYNTAX Integer32
			MAX-ACCESS read-only
			STATUS current
			DESCRIPTION
				"Description."
			::= { sleEponOnuEntry 37 }

		
		sleEponOnuDcVoltage OBJECT-TYPE
			SYNTAX OCTET STRING
			MAX-ACCESS read-only
			STATUS current
			DESCRIPTION
				"Description."
			::= { sleEponOnuEntry 38 }

		
		sleEponOnuBlockStatus OBJECT-TYPE
			SYNTAX OCTET STRING
			MAX-ACCESS read-only
			STATUS current
			DESCRIPTION
				"Description."
			::= { sleEponOnuEntry 39 }

		
		sleEponOnuDistance OBJECT-TYPE
			SYNTAX Integer32
			MAX-ACCESS read-only
			STATUS current
			DESCRIPTION
				"Description."
			::= { sleEponOnuEntry 40 }

		
		sleEponOnuChipId OBJECT-TYPE
			SYNTAX Integer32
			MAX-ACCESS read-only
			STATUS current
			DESCRIPTION
				"Description."
			::= { sleEponOnuEntry 41 }

		
		sleEponOnu10GMpcpRate OBJECT-TYPE
			SYNTAX OCTET STRING
			MAX-ACCESS read-only
			STATUS current
			DESCRIPTION
				"Description."
			::= { sleEponOnuEntry 42 }

		
		sleEponOnu10GMpcpLlid OBJECT-TYPE
			SYNTAX Integer32
			MAX-ACCESS read-only
			STATUS current
			DESCRIPTION
				"Description."
			::= { sleEponOnuEntry 43 }

		
		sleEponOnu10GMpcpDiscover OBJECT-TYPE
			SYNTAX OCTET STRING
			MAX-ACCESS read-only
			STATUS current
			DESCRIPTION
				"Description."
			::= { sleEponOnuEntry 44 }

		
		sleEponOnu10GMpcpUpTunnelID OBJECT-TYPE
			SYNTAX Integer32
			MAX-ACCESS read-only
			STATUS current
			DESCRIPTION
				"Description."
			::= { sleEponOnuEntry 45 }

		
		sleEponOnu10GMpcpDnTunnelID OBJECT-TYPE
			SYNTAX Integer32
			MAX-ACCESS read-only
			STATUS current
			DESCRIPTION
				"Description."
			::= { sleEponOnuEntry 46 }

		
		sleEponOnu10GOAMDiscoverStatus OBJECT-TYPE
			SYNTAX OCTET STRING
			MAX-ACCESS read-only
			STATUS current
			DESCRIPTION
				"Description."
			::= { sleEponOnuEntry 47 }

		
		sleEponOnu10GOAMOUI OBJECT-TYPE
			SYNTAX Integer32
			MAX-ACCESS read-only
			STATUS current
			DESCRIPTION
				"Description."
			::= { sleEponOnuEntry 48 }

		
		sleEponOnu10GOAMFWVersion OBJECT-TYPE
			SYNTAX Integer32
			MAX-ACCESS read-only
			STATUS current
			DESCRIPTION
				"Description."
			::= { sleEponOnuEntry 49 }

		
		sleEponOnu10GOAMProductID OBJECT-TYPE
			SYNTAX Integer32
			MAX-ACCESS read-only
			STATUS current
			DESCRIPTION
				"Description."
			::= { sleEponOnuEntry 50 }

		
		sleEponOnu10GOAMChipID OBJECT-TYPE
			SYNTAX Integer32
			MAX-ACCESS read-only
			STATUS current
			DESCRIPTION
				"Description."
			::= { sleEponOnuEntry 51 }

		
		sleEponOnu10GOAMChipVersion OBJECT-TYPE
			SYNTAX Integer32
			MAX-ACCESS read-only
			STATUS current
			DESCRIPTION
				"Description."
			::= { sleEponOnuEntry 52 }

		
		sleEponOnuRstpBridgePri OBJECT-TYPE
			SYNTAX Integer32
			MAX-ACCESS read-only
			STATUS current
			DESCRIPTION
				"Description."
			::= { sleEponOnuEntry 53 }

		
		sleEponOnuRstpBridgeMode OBJECT-TYPE
			SYNTAX OCTET STRING
			MAX-ACCESS read-only
			STATUS current
			DESCRIPTION
				"Description."
			::= { sleEponOnuEntry 54 }

		
		sleEponOnuRstpRootMaxAge OBJECT-TYPE
			SYNTAX Integer32
			MAX-ACCESS read-only
			STATUS current
			DESCRIPTION
				"Description."
			::= { sleEponOnuEntry 55 }

		
		sleEponOnuRootHelloTime OBJECT-TYPE
			SYNTAX Integer32
			MAX-ACCESS read-only
			STATUS current
			DESCRIPTION
				"Description."
			::= { sleEponOnuEntry 56 }

		
		sleEponOnuRootForwardDelay OBJECT-TYPE
			SYNTAX Integer32
			MAX-ACCESS read-only
			STATUS current
			DESCRIPTION
				"Description."
			::= { sleEponOnuEntry 57 }

		
		sleEponOnuPortsCount OBJECT-TYPE
			SYNTAX Integer32
			MAX-ACCESS read-only
			STATUS current
			DESCRIPTION
				"Description."
			::= { sleEponOnuEntry 58 }

		
		sleEponOnuLoopbackFrameSend OBJECT-TYPE
			SYNTAX Integer32
			MAX-ACCESS read-only
			STATUS current
			DESCRIPTION
				"Description."
			::= { sleEponOnuEntry 59 }

		
		sleEponOnuLoopbackFrameRec OBJECT-TYPE
			SYNTAX Integer32
			MAX-ACCESS read-only
			STATUS current
			DESCRIPTION
				"Description."
			::= { sleEponOnuEntry 60 }

		
		sleEponOnuLoopbackFrameCorrupt OBJECT-TYPE
			SYNTAX Integer32
			MAX-ACCESS read-only
			STATUS current
			DESCRIPTION
				"Description."
			::= { sleEponOnuEntry 61 }

		
		sleEponOnuLoopbackMinDelay OBJECT-TYPE
			SYNTAX Integer32
			MAX-ACCESS read-only
			STATUS current
			DESCRIPTION
				"Description."
			::= { sleEponOnuEntry 62 }

		
		sleEponOnuLoopbackMaxDelay OBJECT-TYPE
			SYNTAX Integer32
			MAX-ACCESS read-only
			STATUS current
			DESCRIPTION
				"Description."
			::= { sleEponOnuEntry 63 }

		
		sleEponOnuLoopbackAvrDelay OBJECT-TYPE
			SYNTAX Integer32
			MAX-ACCESS read-only
			STATUS current
			DESCRIPTION
				"Description."
			::= { sleEponOnuEntry 64 }

		
		sleEponOnuPortAlarm OBJECT-TYPE
			SYNTAX Integer32
			MAX-ACCESS read-only
			STATUS current
			DESCRIPTION
				"Description."
			::= { sleEponOnuEntry 65 }

		
		sleEponOnuModelName OBJECT-TYPE
			SYNTAX OCTET STRING
			MAX-ACCESS read-only
			STATUS current
			DESCRIPTION
				"ONU model name"
			::= { sleEponOnuEntry 66 }

		
		sleEponOnuStormControlEnable OBJECT-TYPE
			SYNTAX EnableFlag
			MAX-ACCESS read-only
			STATUS current
			DESCRIPTION
				"Onu strom status."
			::= { sleEponOnuEntry 67 }

		
		sleEponOnuStormControlBroadcast OBJECT-TYPE
			SYNTAX Integer32 (8..65535)
			MAX-ACCESS read-only
			STATUS current
			DESCRIPTION
				"Broadcast threshold (default 121 kbps)."
			::= { sleEponOnuEntry 68 }

		
		sleEponOnuStormControlMulticast OBJECT-TYPE
			SYNTAX Integer32 (8..65535)
			MAX-ACCESS read-only
			STATUS current
			DESCRIPTION
				"Multicast threshold (default 23 kbps)."
			::= { sleEponOnuEntry 69 }

		
		sleEponOnuStormControlUnknownUnicast OBJECT-TYPE
			SYNTAX Integer32 (8..65535)
			MAX-ACCESS read-only
			STATUS current
			DESCRIPTION
				"Unknown-Unicast threshold (default 23 kbps).."
			::= { sleEponOnuEntry 70 }

		
		sleEponOnuLlidIndex OBJECT-TYPE
			SYNTAX Integer32
			MAX-ACCESS read-only
			STATUS current
			DESCRIPTION
				"The LLID index"
			::= { sleEponOnuEntry 71 }

		
		sleEponOnuDistanceInitial OBJECT-TYPE
			SYNTAX Integer32
			MAX-ACCESS read-only
			STATUS current
			DESCRIPTION
				"The initial record of fiber length history"
			::= { sleEponOnuEntry 72 }

		
		sleEponOnuDistanceDiff OBJECT-TYPE
			SYNTAX Integer32
			MAX-ACCESS read-only
			STATUS current
			DESCRIPTION
				"The difference between initial and last record of fiber length history"
			::= { sleEponOnuEntry 73 }

		
		sleEponOnuRegisterTime OBJECT-TYPE
			SYNTAX OCTET STRING
			MAX-ACCESS read-only
			STATUS current
			DESCRIPTION
				"The time when ONU is registered"
			::= { sleEponOnuEntry 74 }

		
		sleEponOnuControl OBJECT IDENTIFIER ::= { sleEponOnu 2 }

		
		sleEponOnuControlRequest OBJECT-TYPE
			SYNTAX INTEGER
				{
				setEponOnuRegMode(1),
				setEponOnuStatus(2),
				setEponOnuAttributes(3),
				setEponOnuRegister(4),
				setEponOnuDeregister(5),
				setEponOnuProfile(6),
				setEponOnuUpgrade(7),
				setEPonOnuLoopbackProvision(8),
				setEponOnuTxPowerOffTimer(9),
				setEponOnuProfileByMac(10),
				setEponOnuDeregisterByMac(11),
				setEponOnuLgpAuthStatus(12),
				setEponOnuSipGlobalConfigIP(13),
				setEponOnuSipGlobalConfigDHCP(14),
				setEponOnuSipGlobalConfigPPPoE(15),
				destroyEponOnuSipGlobalConfig(16),
				setEponOnuPingTest(17),
				setEponOnuLoopDetectUnblock(18),
				setEponOltRssiOnuSingle(19),
				setDBAMultiLLidLinkEnable(20),
				setDBAMultLLidLinkDisable(21),
				setEponOnuFecConfig(22),
				setEponOnuMacConfig(23),
				sleEponOnuRebootHybridOnu(24),
				sleEponOnuRestoreOnu(25),
				sleEponOnuSetMaxHost(26),
				sleEponOnuFixOnu(27),
				setEponOnuStormControlStatus(28),
				setEponOnuStormControlThreshold(29),
				destoryEponOnuStormControlThreshold(30)
				}
			MAX-ACCESS read-write
			STATUS current
			DESCRIPTION
				"The request of a user command"
			::= { sleEponOnuControl 1 }

		
		sleEponOnuControlStatus OBJECT-TYPE
			SYNTAX SleControlStatusType
			MAX-ACCESS read-only
			STATUS current
			DESCRIPTION
				"The status of user command"
			::= { sleEponOnuControl 2 }

		
		sleEponOnuControlTimer OBJECT-TYPE
			SYNTAX Gauge32
			MAX-ACCESS read-write
			STATUS current
			DESCRIPTION
				"The maximum time for the manager for a long running user command"
			::= { sleEponOnuControl 3 }

		
		sleEponOnuControlTimeStamp OBJECT-TYPE
			SYNTAX TimeTicks
			MAX-ACCESS read-only
			STATUS current
			DESCRIPTION
				"The time stamp of the last command(end of command)"
			::= { sleEponOnuControl 4 }

		
		sleEponOnuControlReqResult OBJECT-TYPE
			SYNTAX SleControlRequestResultType
			MAX-ACCESS read-only
			STATUS current
			DESCRIPTION
				"The result of the last user command"
			::= { sleEponOnuControl 5 }

		
		sleEponOnuControlOltIndex OBJECT-TYPE
			SYNTAX INTEGER (1..512)
			MAX-ACCESS read-write
			STATUS current
			DESCRIPTION
				"OLT index"
			::= { sleEponOnuControl 6 }

		
		sleEponOnuControlOnuIndex OBJECT-TYPE
			SYNTAX INTEGER (1..64)
			MAX-ACCESS read-write
			STATUS current
			DESCRIPTION
				"ONU index <1-64>"
			::= { sleEponOnuControl 7 }

		
		sleEponOnuControlRegMode OBJECT-TYPE
			SYNTAX INTEGER
				{
				auto(1),
				manual(2),
				static(3)
				}
			MAX-ACCESS read-write
			STATUS current
			DESCRIPTION
				"ONU register mode {auto(1), manual(2)}"
			DEFVAL { auto }
			::= { sleEponOnuControl 8 }

		
		sleEponOnuControlOnuStatus OBJECT-TYPE
			SYNTAX INTEGER
				{
				inactive(1),
				deny(2),
				block(3),
				active(4),
				reset(5)
				}
			MAX-ACCESS read-write
			STATUS current
			DESCRIPTION
				"1 : inactive 
				2 : deny 
				3 : block
				4 : active
				5 : reset
				"
			::= { sleEponOnuControl 9 }

		
		sleEponOnuControlMacAddress OBJECT-TYPE
			SYNTAX MacAddress
			MAX-ACCESS read-write
			STATUS current
			DESCRIPTION
				"ONU MAC address"
			::= { sleEponOnuControl 10 }

		
		sleEponOnuControlDescription OBJECT-TYPE
			SYNTAX OCTET STRING
			MAX-ACCESS read-write
			STATUS current
			DESCRIPTION
				"ONU description"
			::= { sleEponOnuControl 11 }

		
		sleEponOnuControlProfile OBJECT-TYPE
			SYNTAX OCTET STRING (SIZE (1..64))
			MAX-ACCESS read-write
			STATUS current
			DESCRIPTION
				"Profile name"
			::= { sleEponOnuControl 12 }

		
		sleEponOnuControlUpgradePath OBJECT-TYPE
			SYNTAX OCTET STRING (SIZE (1..64))
			UNITS "byte"
			MAX-ACCESS read-write
			STATUS current
			DESCRIPTION
				"Upgrade path"
			::= { sleEponOnuControl 13 }

		
		sleEponOnuControlLoopbackProvision OBJECT-TYPE
			SYNTAX INTEGER { test(1) }
			MAX-ACCESS read-write
			STATUS current
			DESCRIPTION
				"1 : test"
			::= { sleEponOnuControl 14 }

		
		sleEponOnuControlTxPowerOffTimer OBJECT-TYPE
			SYNTAX INTEGER (0 | 10..65535)
			MAX-ACCESS read-write
			STATUS current
			DESCRIPTION
				"Description."
			::= { sleEponOnuControl 15 }

		
		sleEponOnuControlSipGlobalConfigMode OBJECT-TYPE
			SYNTAX INTEGER
				{
				ip(0),
				dhcp(1),
				pppoe(2)
				}
			MAX-ACCESS read-write
			STATUS current
			DESCRIPTION
				"Description."
			::= { sleEponOnuControl 18 }

		
		sleEponOnuControlSipGlobalConfigIp OBJECT-TYPE
			SYNTAX IpAddress
			MAX-ACCESS read-write
			STATUS current
			DESCRIPTION
				"Description."
			::= { sleEponOnuControl 19 }

		
		sleEponOnuControlSipGlobalConfigNetmask OBJECT-TYPE
			SYNTAX IpAddress
			MAX-ACCESS read-write
			STATUS current
			DESCRIPTION
				"Description."
			::= { sleEponOnuControl 20 }

		
		sleEponOnuControlSipGlobalConfigGateway OBJECT-TYPE
			SYNTAX IpAddress
			MAX-ACCESS read-write
			STATUS current
			DESCRIPTION
				"Description."
			::= { sleEponOnuControl 21 }

		
		sleEponOnuControlSipGlobalConfigUserName OBJECT-TYPE
			SYNTAX OCTET STRING (SIZE (0..32))
			MAX-ACCESS read-write
			STATUS current
			DESCRIPTION
				"Description."
			::= { sleEponOnuControl 22 }

		
		sleEponOnuControlSipGlobalConfigUserPasswd OBJECT-TYPE
			SYNTAX OCTET STRING (SIZE (0..32))
			MAX-ACCESS read-write
			STATUS current
			DESCRIPTION
				"Description."
			::= { sleEponOnuControl 23 }

		
		sleEponOnuControlSipGlobalConfigVid OBJECT-TYPE
			SYNTAX INTEGER
			MAX-ACCESS read-write
			STATUS current
			DESCRIPTION
				"Description."
			::= { sleEponOnuControl 24 }

		
		sleEponOnuControlPingCount OBJECT-TYPE
			SYNTAX Integer32 (1..20)
			MAX-ACCESS read-write
			STATUS current
			DESCRIPTION
				"Onu Ping Test count."
			::= { sleEponOnuControl 25 }

		
		sleEponOnuControlFecConfigDirection OBJECT-TYPE
			SYNTAX INTEGER
				{
				up(1),
				down(2),
				both(3)
				}
			MAX-ACCESS read-write
			STATUS current
			DESCRIPTION
				"set fec direction"
			::= { sleEponOnuControl 26 }

		
		sleEponOnuControlFecConfigStatus OBJECT-TYPE
			SYNTAX EnableFlag
			MAX-ACCESS read-write
			STATUS current
			DESCRIPTION
				"enable or disable fec config"
			::= { sleEponOnuControl 27 }

		
		sleEponOnuControlMacOperation OBJECT-TYPE
			SYNTAX INTEGER
				{
				staticMacAdd(1),
				staticMacDel(2),
				staticMacClear(3),
				dynamicMacClear(4)
				}
			MAX-ACCESS read-write
			STATUS current
			DESCRIPTION
				"mac address operation"
			::= { sleEponOnuControl 28 }

		
		sleEponOnuControlMaxHost OBJECT-TYPE
			SYNTAX INTEGER
			MAX-ACCESS read-write
			STATUS current
			DESCRIPTION
				"Description."
			::= { sleEponOnuControl 29 }

		
		sleEponOnuControlUpgradeTTY OBJECT-TYPE
			SYNTAX OCTET STRING
			MAX-ACCESS read-write
			STATUS current
			DESCRIPTION
				"upgrade TTY"
			::= { sleEponOnuControl 30 }

		
		sleEponOnuControlUpgradeForce OBJECT-TYPE
			SYNTAX EnableFlag
			MAX-ACCESS read-write
			STATUS current
			DESCRIPTION
				"upgrade forcedly or not"
			::= { sleEponOnuControl 31 }

		
		sleEponOnuControlStormControlEnable OBJECT-TYPE
			SYNTAX EnableFlag
			MAX-ACCESS read-write
			STATUS current
			DESCRIPTION
				"Onu strom status."
			::= { sleEponOnuControl 32 }

		
		sleEponOnuControlStormControlBroadcast OBJECT-TYPE
			SYNTAX Integer32 (8..65535)
			MAX-ACCESS read-write
			STATUS current
			DESCRIPTION
				"Broadcast threshold (default 121 kbps)."
			::= { sleEponOnuControl 33 }

		
		sleEponOnuControlStormControlMulticast OBJECT-TYPE
			SYNTAX Integer32 (8..65535)
			MAX-ACCESS read-write
			STATUS current
			DESCRIPTION
				"Multicast threshold (default 23 kbps)."
			::= { sleEponOnuControl 34 }

		
		sleEponOnuControlStormControlUnknownUnicast OBJECT-TYPE
			SYNTAX Integer32 (8..65535)
			MAX-ACCESS read-write
			STATUS current
			DESCRIPTION
				"Unknown-Unicast threshold (default 23 kbps)."
			::= { sleEponOnuControl 35 }

		
		sleEponOnuNotification OBJECT IDENTIFIER ::= { sleEponOnu 3 }

		
		sleEponOnuRegModeChanged NOTIFICATION-TYPE
			OBJECTS { sleEponOnuControlRequest, sleEponOnuControlTimeStamp, sleEponOnuControlReqResult, sleEponOnuControlOltIndex, sleEponOnuControlOnuIndex, 
				sleEponOnuControlRegMode }
			STATUS current
			DESCRIPTION 
				"Description."
			::= { sleEponOnuNotification 1 }

		
		sleEponOnuStatusChanged NOTIFICATION-TYPE
			OBJECTS { sleEponOnuControlRequest, sleEponOnuControlTimeStamp, sleEponOnuControlReqResult, sleEponOnuControlOltIndex, sleEponOnuControlOnuIndex, 
				sleEponOnuControlOnuStatus }
			STATUS current
			DESCRIPTION 
				"Description."
			::= { sleEponOnuNotification 2 }

		
		sleEponOnuAttibutesChanged NOTIFICATION-TYPE
			OBJECTS { sleEponOnuControlRequest, sleEponOnuControlTimeStamp, sleEponOnuControlReqResult, sleEponOnuControlOltIndex, sleEponOnuControlOnuIndex, 
				sleEponOnuControlDescription }
			STATUS current
			DESCRIPTION 
				"Description."
			::= { sleEponOnuNotification 3 }

		
		sleEponOnuRegistered NOTIFICATION-TYPE
			OBJECTS { sleEponOnuControlRequest, sleEponOnuControlTimeStamp, sleEponOnuControlReqResult, sleEponOnuControlOltIndex, sleEponOnuControlOnuIndex, 
				sleEponOnuControlMacAddress, sleEponOnuControlDescription }
			STATUS current
			DESCRIPTION 
				"Description."
			::= { sleEponOnuNotification 4 }

		
		sleEponOnuDeregistered NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 5 }

		
		sleEponOnuProfileChanged NOTIFICATION-TYPE
			OBJECTS { sleEponOnuControlRequest, sleEponOnuControlTimeStamp, sleEponOnuControlReqResult, sleEponOnuControlOltIndex, sleEponOnuControlOnuIndex, 
				sleEponOnuControlProfile }
			STATUS current
			DESCRIPTION 
				"Description."
			::= { sleEponOnuNotification 6 }

		
		sleEponOnuUpgraded NOTIFICATION-TYPE
			OBJECTS { sleEponOnuControlRequest, sleEponOnuControlTimeStamp, sleEponOnuControlReqResult, sleEponOnuControlOltIndex, sleEponOnuControlOnuIndex, 
				sleEponOnuControlUpgradePath }
			STATUS current
			DESCRIPTION 
				"Description."
			::= { sleEponOnuNotification 7 }

		
		sleEponOnuLoopbackProvisioned NOTIFICATION-TYPE
			OBJECTS { sleEponOnuControlRequest, sleEponOnuControlTimeStamp, sleEponOnuControlReqResult, sleEponOnuControlOltIndex, sleEponOnuControlOnuIndex, 
				sleEponOnuControlLoopbackProvision }
			STATUS current
			DESCRIPTION 
				"Description."
			::= { sleEponOnuNotification 8 }

		
		sleEponOnuTxPowerOffChanged NOTIFICATION-TYPE
			OBJECTS { sleEponOnuControlRequest, sleEponOnuControlTimeStamp, sleEponOnuControlReqResult, sleEponOnuControlOltIndex, sleEponOnuControlOnuIndex, 
				sleEponOnuControlTxPowerOffTimer }
			STATUS current
			DESCRIPTION 
				"Description."
			::= { sleEponOnuNotification 9 }

		
		sleEponOnuFristRegisteredOnAutoToManual NOTIFICATION-TYPE
			OBJECTS { sysDescr, sleEponOltIndex, sleEponOnuIndex }
			STATUS current
			DESCRIPTION 
				"Description."
			::= { sleEponOnuNotification 10 }

		
		sleEponOnuProfileChangedByMac NOTIFICATION-TYPE
			OBJECTS { sleEponOnuControlRequest, sleEponOnuControlTimeStamp, sleEponOnuControlReqResult, sleEponOnuControlOltIndex, sleEponOnuControlMacAddress, 
				sleEponOnuControlProfile }
			STATUS current
			DESCRIPTION 
				"Description."
			::= { sleEponOnuNotification 11 }

		
		sleEponOnuDeregisteredByMac NOTIFICATION-TYPE
			OBJECTS { sleEponOnuControlRequest, sleEponOnuControlTimeStamp, sleEponOnuControlReqResult, sleEponOnuControlOltIndex, sleEponOnuControlMacAddress
				 }
			STATUS current
			DESCRIPTION 
				"Description."
			::= { sleEponOnuNotification 12 }

		
		sleEponOnuLgpauthStatusChanged NOTIFICATION-TYPE
			OBJECTS { sleEponOnuControlRequest, sleEponOnuControlTimeStamp, sleEponOnuControlReqResult, sleEponOnuControlOltIndex, sleEponOnuControlOnuIndex
				 }
			STATUS current
			DESCRIPTION 
				"Lgpauth status changed trap."
			::= { sleEponOnuNotification 13 }

		
		sleEponOnuSipGlobalConfigIpChanged NOTIFICATION-TYPE
			OBJECTS { sleEponOnuControlRequest, sleEponOnuControlTimeStamp, sleEponOnuControlReqResult, sleEponOnuControlOltIndex, sleEponOnuControlOnuIndex, 
				sleEponOnuControlSipGlobalConfigMode, sleEponOnuControlSipGlobalConfigIp, sleEponOnuControlSipGlobalConfigNetmask, sleEponOnuControlSipGlobalConfigGateway, sleEponOnuControlSipGlobalConfigVid
				 }
			STATUS current
			DESCRIPTION 
				"Description."
			::= { sleEponOnuNotification 14 }

		
		sleEponOnuSipGlobalConfigDhcpChanged NOTIFICATION-TYPE
			OBJECTS { sleEponOnuControlRequest, sleEponOnuControlTimeStamp, sleEponOnuControlReqResult, sleEponOnuControlOltIndex, sleEponOnuControlOnuIndex, 
				sleEponOnuControlSipGlobalConfigMode, sleEponOnuControlSipGlobalConfigVid }
			STATUS current
			DESCRIPTION 
				"Description."
			::= { sleEponOnuNotification 15 }

		
		sleEponOnuSipGlobalConfigPPPoEChanged NOTIFICATION-TYPE
			OBJECTS { sleEponOnuControlRequest, sleEponOnuControlTimeStamp, sleEponOnuControlReqResult, sleEponOnuControlOltIndex, sleEponOnuControlOnuIndex, 
				sleEponOnuControlSipGlobalConfigMode, sleEponOnuControlSipGlobalConfigUserName, sleEponOnuControlSipGlobalConfigUserPasswd, sleEponOnuControlSipGlobalConfigVid }
			STATUS current
			DESCRIPTION 
				"Description."
			::= { sleEponOnuNotification 16 }

		
		sleEponOnuSipGlobalConfigDestroyed NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 17 }

		
		sleEponOnuPingTest NOTIFICATION-TYPE
			OBJECTS { sleEponOnuControlRequest, sleEponOnuControlTimeStamp, sleEponOnuControlReqResult, sleEponOnuControlOltIndex, sleEponOnuControlOnuIndex, 
				sleEponOnuControlPingCount }
			STATUS current
			DESCRIPTION 
				"Description."
			::= { sleEponOnuNotification 18 }

		
		sleEponOnuLoopDectectUnblock NOTIFICATION-TYPE
			OBJECTS { sleEponOnuControlRequest, sleEponOnuControlTimeStamp, sleEponOnuControlReqResult, sleEponOnuControlOltIndex, sleEponOnuControlOnuIndex
				 }
			STATUS current
			DESCRIPTION 
				"Loop dectect unblock trap."
			::= { sleEponOnuNotification 19 }

		
		setEponOnuOltRssiOnuSingle NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 20 }

		
		sleEponOnuDBAMultiLLidLink NOTIFICATION-TYPE
			OBJECTS { sleEponOnuControlRequest, sleEponOnuControlTimeStamp, sleEponOnuControlReqResult, sleEponOnuControlOltIndex, sleEponOnuControlOnuIndex
				 }
			STATUS current
			DESCRIPTION 
				"Multi-llid link enable and disable trap."
			::= { sleEponOnuNotification 21 }

		
		sleEponOnuFecChanged NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 22 }

		
		sleEponOnuMacChanged NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 23 }

		
		sleEponOnuRebootHybridOnu NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 24 }

		
		sleEponOnuRestoreOnu NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 25 }

		
		sleEponOnuSetMaxHost NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 26 }

		
		sleEponOnuFix NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 27 }

		
		sleEponOnuStormControlConfigChanged NOTIFICATION-TYPE
			OBJECTS { sleEponOnuControlRequest, sleEponOnuControlTimeStamp, sleEponOnuControlReqResult, sleEponOnuControlOltIndex, sleEponOnuControlOnuIndex
				 }
			STATUS current
			DESCRIPTION 
				"Description."
			::= { sleEponOnuNotification 28 }

		
		sleEponOnuDMI OBJECT IDENTIFIER ::= { sleEponOnu 4 }

		
		sleEponOnuDMITable OBJECT-TYPE
			SYNTAX SEQUENCE OF SleEponOnuDMIEntry
			MAX-ACCESS not-accessible
			STATUS current
			DESCRIPTION
				"Description."
			::= { sleEponOnuDMI 1 }

		
		sleEponOnuDMIEntry OBJECT-TYPE
			SYNTAX SleEponOnuDMIEntry
			MAX-ACCESS not-accessible
			STATUS current
			DESCRIPTION
				"Description."
			INDEX { sleEponOltIndex, sleEponOnuIndex }
			::= { sleEponOnuDMITable 1 }

		
		SleEponOnuDMIEntry ::=
			SEQUENCE { 
				sleEponOnuDMITemper
					OCTET STRING,
				sleEponOnuDMIVoltage
					OCTET STRING,
				sleEponOnuDMITxBias
					OCTET STRING,
				sleEponOnuDMITxPower
					OCTET STRING,
				sleEponOnuDMIRxPower
					OCTET STRING
			 }

		sleEponOnuDMITemper OBJECT-TYPE
			SYNTAX OCTET STRING
			MAX-ACCESS read-only
			STATUS current
			DESCRIPTION
				"Onu DMI Temperature ,range is (-128 ~ 127.99 C)
				"
			::= { sleEponOnuDMIEntry 1 }

		
		sleEponOnuDMIVoltage OBJECT-TYPE
			SYNTAX OCTET STRING
			MAX-ACCESS read-only
			STATUS current
			DESCRIPTION
				"Onu DMI voltage,range is (0 ~ 6.5535 V).
				
				"
			::= { sleEponOnuDMIEntry 2 }

		
		sleEponOnuDMITxBias OBJECT-TYPE
			SYNTAX OCTET STRING
			MAX-ACCESS read-only
			STATUS current
			DESCRIPTION
				"Onu DMI txbias,range is (0 ~ 131 mA).
				"
			::= { sleEponOnuDMIEntry 3 }

		
		sleEponOnuDMITxPower OBJECT-TYPE
			SYNTAX OCTET STRING
			MAX-ACCESS read-only
			STATUS current
			DESCRIPTION
				"Onu DMI txpower, range is (-40 ~ 8.1647 dBm).
				"
			::= { sleEponOnuDMIEntry 4 }

		
		sleEponOnuDMIRxPower OBJECT-TYPE
			SYNTAX OCTET STRING
			MAX-ACCESS read-only
			STATUS current
			DESCRIPTION
				"Onu DMI rxpower,range is (-40 ~ 8.1647 dBm)."
			::= { sleEponOnuDMIEntry 5 }

		
		sleEponOnuDMIThresholdTable OBJECT-TYPE
			SYNTAX SEQUENCE OF SleEponOnuDMIThresholdEntry
			MAX-ACCESS not-accessible
			STATUS current
			DESCRIPTION
				"Description."
			::= { sleEponOnuDMI 2 }

		
		sleEponOnuDMIThresholdEntry OBJECT-TYPE
			SYNTAX SleEponOnuDMIThresholdEntry
			MAX-ACCESS not-accessible
			STATUS current
			DESCRIPTION
				"Description."
			INDEX { sleEponOltIndex, sleEponOnuIndex }
			::= { sleEponOnuDMIThresholdTable 1 }

		
		SleEponOnuDMIThresholdEntry ::=
			SEQUENCE { 
				sleEponOnuDMIThresholdWarnTemperLow
					Integer32,
				sleEponOnuDMIThresholdWarnTemperHigh
					Integer32,
				sleEponOnuDMIThresholdAlarmTemperLow
					Integer32,
				sleEponOnuDMIThresholdAlarmTemperHigh
					Integer32,
				sleEponOnuDMIThresholdWarnVoltageLow
					Integer32,
				sleEponOnuDMIThresholdWarnVoltageHigh
					Integer32,
				sleEponOnuDMIThresholdAlarmVoltageLow
					Integer32,
				sleEponOnuDMIThresholdAlarmVoltageHigh
					Integer32,
				sleEponOnuDMIThresholdWarnTxbiasLow
					Integer32,
				sleEponOnuDMIThresholdWarnTxbiasHigh
					Integer32,
				sleEponOnuDMIThresholdAlarmTxbiasLow
					Integer32,
				sleEponOnuDMIThresholdAlarmTxbiasHigh
					Integer32,
				sleEponOnuDMIThresholdWarnTxPowerLow
					Integer32,
				sleEponOnuDMIThresholdWarnTxPowerHigh
					Integer32,
				sleEponOnuDMIThresholdAlarmTxPowerLow
					Integer32,
				sleEponOnuDMIThresholdAlarmTxPowerHigh
					Integer32,
				sleEponOnuDMIThresholdWarnRxPowerLow
					Integer32,
				sleEponOnuDMIThresholdWarnRxPowerHigh
					Integer32,
				sleEponOnuDMIThresholdAlarmRxPowerLow
					Integer32,
				sleEponOnuDMIThresholdAlarmRxPowerHigh
					Integer32
			 }

		sleEponOnuDMIThresholdWarnTemperLow OBJECT-TYPE
			SYNTAX Integer32
			MAX-ACCESS read-only
			STATUS current
			DESCRIPTION
				"The Temperature threshold -128~127.99(C)
				It must be devided by 10000."
			::= { sleEponOnuDMIThresholdEntry 1 }

		
		sleEponOnuDMIThresholdWarnTemperHigh OBJECT-TYPE
			SYNTAX Integer32
			MAX-ACCESS read-only
			STATUS current
			DESCRIPTION
				"The Temperature threshold -128~127.99(C)
				It must be devided by 10000."
			::= { sleEponOnuDMIThresholdEntry 2 }

		
		sleEponOnuDMIThresholdAlarmTemperLow OBJECT-TYPE
			SYNTAX Integer32
			MAX-ACCESS read-only
			STATUS current
			DESCRIPTION
				"The Temperature threshold -128~127.99(C)
				It must be devided by 10000."
			::= { sleEponOnuDMIThresholdEntry 3 }

		
		sleEponOnuDMIThresholdAlarmTemperHigh OBJECT-TYPE
			SYNTAX Integer32
			MAX-ACCESS read-only
			STATUS current
			DESCRIPTION
				"The Temperature threshold -128~127.99(C)
				It must be devided by 10000."
			::= { sleEponOnuDMIThresholdEntry 4 }

		
		sleEponOnuDMIThresholdWarnVoltageLow OBJECT-TYPE
			SYNTAX Integer32
			MAX-ACCESS read-only
			STATUS current
			DESCRIPTION
				"The Voltage threshold 0~6.5535(V)
				It must be devided by 10000."
			::= { sleEponOnuDMIThresholdEntry 5 }

		
		sleEponOnuDMIThresholdWarnVoltageHigh OBJECT-TYPE
			SYNTAX Integer32
			MAX-ACCESS read-only
			STATUS current
			DESCRIPTION
				"The Voltage threshold 0~6.5535(V)
				It must be devided by 10000."
			::= { sleEponOnuDMIThresholdEntry 6 }

		
		sleEponOnuDMIThresholdAlarmVoltageLow OBJECT-TYPE
			SYNTAX Integer32
			MAX-ACCESS read-only
			STATUS current
			DESCRIPTION
				"The Voltage threshold 0~6.5535(V)
				It must be devided by 10000."
			::= { sleEponOnuDMIThresholdEntry 7 }

		
		sleEponOnuDMIThresholdAlarmVoltageHigh OBJECT-TYPE
			SYNTAX Integer32
			MAX-ACCESS read-only
			STATUS current
			DESCRIPTION
				"The Voltage threshold 0~6.5535(V)
				It must be devided by 10000."
			::= { sleEponOnuDMIThresholdEntry 8 }

		
		sleEponOnuDMIThresholdWarnTxbiasLow OBJECT-TYPE
			SYNTAX Integer32 (0..131)
			MAX-ACCESS read-only
			STATUS current
			DESCRIPTION
				"The Txbias Threshold 0~131(mA)
				It must be devided by 10000.
				"
			::= { sleEponOnuDMIThresholdEntry 9 }

		
		sleEponOnuDMIThresholdWarnTxbiasHigh OBJECT-TYPE
			SYNTAX Integer32 (0..131)
			MAX-ACCESS read-only
			STATUS current
			DESCRIPTION
				"The Txbias Threshold 0~131(mA)
				It must be devided by 10000."
			::= { sleEponOnuDMIThresholdEntry 10 }

		
		sleEponOnuDMIThresholdAlarmTxbiasLow OBJECT-TYPE
			SYNTAX Integer32 (0..131)
			MAX-ACCESS read-only
			STATUS current
			DESCRIPTION
				"The Txbias Threshold 0~131(mA)
				It must be devided by 10000.
				"
			::= { sleEponOnuDMIThresholdEntry 11 }

		
		sleEponOnuDMIThresholdAlarmTxbiasHigh OBJECT-TYPE
			SYNTAX Integer32 (0..131)
			MAX-ACCESS read-only
			STATUS current
			DESCRIPTION
				"The Txbias Threshold 0~131(mA)
				It must be devided by 10000.
				"
			::= { sleEponOnuDMIThresholdEntry 12 }

		
		sleEponOnuDMIThresholdWarnTxPowerLow OBJECT-TYPE
			SYNTAX Integer32
			MAX-ACCESS read-only
			STATUS current
			DESCRIPTION
				"The Power threshold -40~8,1647 (dBm)
				It must be devided by 10000.
				"
			::= { sleEponOnuDMIThresholdEntry 13 }

		
		sleEponOnuDMIThresholdWarnTxPowerHigh OBJECT-TYPE
			SYNTAX Integer32
			MAX-ACCESS read-only
			STATUS current
			DESCRIPTION
				"The Power threshold -40~8,1647 (dBm)
				It must be devided by 10000."
			::= { sleEponOnuDMIThresholdEntry 14 }

		
		sleEponOnuDMIThresholdAlarmTxPowerLow OBJECT-TYPE
			SYNTAX Integer32
			MAX-ACCESS read-only
			STATUS current
			DESCRIPTION
				"The Power threshold -40~8,1647 (dBm)
				It must be devided by 10000.
				"
			::= { sleEponOnuDMIThresholdEntry 15 }

		
		sleEponOnuDMIThresholdAlarmTxPowerHigh OBJECT-TYPE
			SYNTAX Integer32
			MAX-ACCESS read-only
			STATUS current
			DESCRIPTION
				"The Power threshold -40~8,1647 (dBm)
				It must be devided by 10000.
				"
			::= { sleEponOnuDMIThresholdEntry 16 }

		
		sleEponOnuDMIThresholdWarnRxPowerLow OBJECT-TYPE
			SYNTAX Integer32
			MAX-ACCESS read-only
			STATUS current
			DESCRIPTION
				"The Power threshold -40~8,1647 (dBm)
				It must be devided by 10000.
				"
			::= { sleEponOnuDMIThresholdEntry 17 }

		
		sleEponOnuDMIThresholdWarnRxPowerHigh OBJECT-TYPE
			SYNTAX Integer32
			MAX-ACCESS read-only
			STATUS current
			DESCRIPTION
				"The Power threshold -40~8,1647 (dBm)
				It must be devided by 10000.
				"
			::= { sleEponOnuDMIThresholdEntry 18 }

		
		sleEponOnuDMIThresholdAlarmRxPowerLow OBJECT-TYPE
			SYNTAX Integer32
			MAX-ACCESS read-only
			STATUS current
			DESCRIPTION
				"The Power threshold -40~8,1647 (dBm)
				It must be devided by 10000.
				"
			::= { sleEponOnuDMIThresholdEntry 19 }

		
		sleEponOnuDMIThresholdAlarmRxPowerHigh OBJECT-TYPE
			SYNTAX Integer32
			MAX-ACCESS read-only
			STATUS current
			DESCRIPTION
				"The Power threshold -40~8,1647 (dBm)
				It must be devided by 10000.
				"
			::= { sleEponOnuDMIThresholdEntry 20 }

		
		sleEponOnuDMIThresholdControl OBJECT IDENTIFIER ::= { sleEponOnuDMI 3 }

		
		sleEponOnuDMIThresholdControlRequest OBJECT-TYPE
			SYNTAX INTEGER
				{
				setEponOnuDMIThreshold(1),
				noEponOnuDMIThreshold(2)
				}
			MAX-ACCESS read-write
			STATUS current
			DESCRIPTION
				"The request of a user command"
			::= { sleEponOnuDMIThresholdControl 1 }

		
		sleEponOnuDMIThresholdControlStatus OBJECT-TYPE
			SYNTAX SleControlStatusType
			MAX-ACCESS read-only
			STATUS current
			DESCRIPTION
				"The status of user command"
			::= { sleEponOnuDMIThresholdControl 2 }

		
		sleEponOnuDMIThresholdControlTimer OBJECT-TYPE
			SYNTAX Gauge32
			MAX-ACCESS read-write
			STATUS current
			DESCRIPTION
				"The maximum time for the manager for a long running user command"
			::= { sleEponOnuDMIThresholdControl 3 }

		
		sleEponOnuDMIThresholdControlTimeStamp OBJECT-TYPE
			SYNTAX TimeTicks
			MAX-ACCESS read-only
			STATUS current
			DESCRIPTION
				"The time stamp of the last command(end of command)"
			::= { sleEponOnuDMIThresholdControl 4 }

		
		sleEponOnuDMIThresholdControlReqResult OBJECT-TYPE
			SYNTAX SleControlRequestResultType
			MAX-ACCESS read-only
			STATUS current
			DESCRIPTION
				"The result of the last user command"
			::= { sleEponOnuDMIThresholdControl 5 }

		
		sleEponOnuDMIThresholdControlOltIndex OBJECT-TYPE
			SYNTAX INTEGER (1..255)
			MAX-ACCESS read-write
			STATUS current
			DESCRIPTION
				"OLT index"
			::= { sleEponOnuDMIThresholdControl 6 }

		
		sleEponOnuDMIThresholdControlOnuIndex OBJECT-TYPE
			SYNTAX Integer32 (1..64)
			MAX-ACCESS read-write
			STATUS current
			DESCRIPTION
				"ONU index"
			::= { sleEponOnuDMIThresholdControl 7 }

		
		sleEponOnuDMIThresholdControlMonitorType OBJECT-TYPE
			SYNTAX INTEGER
				{
				temper(1),
				voltage(2),
				txbias(3),
				txpower(4),
				rxpower(5)
				}
			MAX-ACCESS read-write
			STATUS current
			DESCRIPTION
				"Onu DMI monitor type."
			::= { sleEponOnuDMIThresholdControl 8 }

		
		sleEponOnuDMIThresholdControlMode OBJECT-TYPE
			SYNTAX INTEGER
				{
				warning(1),
				alarm(2)
				}
			MAX-ACCESS read-write
			STATUS current
			DESCRIPTION
				"Onu DMI monitor threshold mode ,alarm or warning."
			::= { sleEponOnuDMIThresholdControl 9 }

		
		sleEponOnuDMIThresholdControlLowThreshold OBJECT-TYPE
			SYNTAX Integer32
			MAX-ACCESS read-write
			STATUS current
			DESCRIPTION
				"onu DMI monitor low threshold, it must multiplied by 10000 and less than high threshold.
				temper threshold (-128 ~ 127.99 C)
				voltage threshold (0 ~ 6.5535 V)
				txbias threshold (0 ~ 131 mA)
				txpower threshold (-40 ~ 8.1647 dBm)
				rxpower threshold (-40 ~ 8.1647 dBm)"
			::= { sleEponOnuDMIThresholdControl 10 }

		
		sleEponOnuDMIThresholdControlHighThreshold OBJECT-TYPE
			SYNTAX Integer32
			MAX-ACCESS read-write
			STATUS current
			DESCRIPTION
				"onu DMI monitor high threshold,it must multiplied by 10000 and more than low threshold.
				temper threshold (-128 ~ 127.99 C)
				voltage threshold (0 ~ 6.5535 V)
				txbias threshold (0 ~ 131 mA)
				txpower threshold (-40 ~ 8.1647 dBm)
				rxpower threshold (-40 ~ 8.1647 dBm)"
			::= { sleEponOnuDMIThresholdControl 11 }

		
		sleEponOnuDMIThresholdNotification OBJECT IDENTIFIER ::= { sleEponOnuDMI 4 }

		
		sleEponOnuDMIMonitorThresholdChanged NOTIFICATION-TYPE
			OBJECTS { sleEponOnuDmiThresholdControlRequest, sleEponOnuDmiThresholdControlTimeStamp, sleEponOnuDmiThresholdControlReqResult, sleEponOnuDmiThresholdControlOltIndex, sleEponOnuDmiThresholdControlOnuIndex, 
				sleEponOnuDmiThresholdControlMonitorType, sleEponOnuDmiThresholdControlMode, sleEponOnuDmiThresholdControlLowThreshold, sleEponOnuDmiThresholdControlHighThreshold }
			STATUS current
			DESCRIPTION 
				"Description."
			::= { sleEponOnuDMIThresholdNotification 1 }

		
		sleEponOnuAutoUpgrade OBJECT IDENTIFIER ::= { sleEponOnu 5 }

		
		sleEponOnuAutoUpgradeTable OBJECT-TYPE
			SYNTAX SEQUENCE OF SleEponOnuAutoUpgradeEntry
			MAX-ACCESS not-accessible
			STATUS current
			DESCRIPTION
				"Description."
			::= { sleEponOnuAutoUpgrade 1 }

		
		sleEponOnuAutoUpgradeEntry OBJECT-TYPE
			SYNTAX SleEponOnuAutoUpgradeEntry
			MAX-ACCESS not-accessible
			STATUS current
			DESCRIPTION
				"Description."
			INDEX { sleEponOltIndex, sleEponOnuAutoUpgradeOnuId }
			::= { sleEponOnuAutoUpgradeTable 1 }

		
		SleEponOnuAutoUpgradeEntry ::=
			SEQUENCE { 
				sleEponOnuAutoUpgradeOnuId
					INTEGER,
				sleEponOnuAutoUpgradeOnuMac
					MacAddress,
				sleEponOnuAutoUpgradeStatus
					INTEGER
			 }

		sleEponOnuAutoUpgradeOnuId OBJECT-TYPE
			SYNTAX INTEGER (1..64)
			MAX-ACCESS read-only
			STATUS current
			DESCRIPTION
				"Onu Id"
			::= { sleEponOnuAutoUpgradeEntry 1 }

		
		sleEponOnuAutoUpgradeOnuMac OBJECT-TYPE
			SYNTAX MacAddress
			MAX-ACCESS read-only
			STATUS current
			DESCRIPTION
				"Onu Mac address"
			::= { sleEponOnuAutoUpgradeEntry 2 }

		
		sleEponOnuAutoUpgradeStatus OBJECT-TYPE
			SYNTAX INTEGER
				{
				init(0),
				wait(1),
				upgrading(2),
				upgradeOk(3),
				noFirmware(4),
				noNeed(5),
				noModel(6),
				rebootOk(7),
				upgradeFail(8),
				unknownUpgrade(9)
				}
			MAX-ACCESS read-only
			STATUS current
			DESCRIPTION
				"upgrade status"
			::= { sleEponOnuAutoUpgradeEntry 3 }

		
		sleEponIopOnu OBJECT IDENTIFIER ::= { sleEponOnu 6 }

		
		sleEponIopOnuTable OBJECT-TYPE
			SYNTAX SEQUENCE OF SleEponIopOnuEntry
			MAX-ACCESS not-accessible
			STATUS current
			DESCRIPTION
				"Description."
			::= { sleEponIopOnu 1 }

		
		sleEponIopOnuEntry OBJECT-TYPE
			SYNTAX SleEponIopOnuEntry
			MAX-ACCESS not-accessible
			STATUS current
			DESCRIPTION
				"Description."
			INDEX { sleEponIopOnuIndex }
			::= { sleEponIopOnuTable 1 }

		
		SleEponIopOnuEntry ::=
			SEQUENCE { 
				sleEponIopOnuIndex
					Integer32,
				sleEponIopOnuVendorName
					OCTET STRING,
				sleEponIopOnuVendorModel
					OCTET STRING,
				sleEponIopOnuPonMode
					INTEGER
			 }

		sleEponIopOnuIndex OBJECT-TYPE
			SYNTAX Integer32 (0..66535)
			MAX-ACCESS read-only
			STATUS current
			DESCRIPTION
				"Description."
			::= { sleEponIopOnuEntry 1 }

		
		sleEponIopOnuVendorName OBJECT-TYPE
			SYNTAX OCTET STRING
			MAX-ACCESS read-only
			STATUS current
			DESCRIPTION
				"Description."
			::= { sleEponIopOnuEntry 2 }

		
		sleEponIopOnuVendorModel OBJECT-TYPE
			SYNTAX OCTET STRING
			MAX-ACCESS read-only
			STATUS current
			DESCRIPTION
				"Description."
			::= { sleEponIopOnuEntry 3 }

		
		sleEponIopOnuPonMode OBJECT-TYPE
			SYNTAX INTEGER
				{
				real(1),
				hybrid(2),
				unknown(3)
				}
			MAX-ACCESS read-only
			STATUS current
			DESCRIPTION
				"Description."
			::= { sleEponIopOnuEntry 4 }

		
		sleEponIopOnuControl OBJECT IDENTIFIER ::= { sleEponIopOnu 2 }

		
		sleEponIopOnuControlRequest OBJECT-TYPE
			SYNTAX INTEGER
				{
				addIopOnuInfo(1),
				delIopOnuInfo(2)
				}
			MAX-ACCESS read-write
			STATUS current
			DESCRIPTION
				"Description."
			::= { sleEponIopOnuControl 1 }

		
		sleEponIopOnuControlStatus OBJECT-TYPE
			SYNTAX SleControlStatusType
			MAX-ACCESS read-only
			STATUS current
			DESCRIPTION
				"Description."
			::= { sleEponIopOnuControl 2 }

		
		sleEponIopOnuControlTimer OBJECT-TYPE
			SYNTAX Gauge32
			MAX-ACCESS read-write
			STATUS current
			DESCRIPTION
				"Description."
			::= { sleEponIopOnuControl 3 }

		
		sleEponIopOnuControlTimeStamp OBJECT-TYPE
			SYNTAX TimeTicks
			MAX-ACCESS read-only
			STATUS current
			DESCRIPTION
				"Description."
			::= { sleEponIopOnuControl 4 }

		
		sleEponIopOnuControlReqResult OBJECT-TYPE
			SYNTAX SleControlRequestResultType
			MAX-ACCESS read-only
			STATUS current
			DESCRIPTION
				"Description."
			::= { sleEponIopOnuControl 5 }

		
		sleEponIopOnuControlVendorName OBJECT-TYPE
			SYNTAX OCTET STRING
			MAX-ACCESS read-write
			STATUS current
			DESCRIPTION
				"Description."
			::= { sleEponIopOnuControl 6 }

		
		sleEponIopOnuControlVendorOui OBJECT-TYPE
			SYNTAX OCTET STRING
			MAX-ACCESS read-write
			STATUS current
			DESCRIPTION
				"Description."
			::= { sleEponIopOnuControl 7 }

		
		sleEponIopOnuControlModelName OBJECT-TYPE
			SYNTAX OCTET STRING
			MAX-ACCESS read-write
			STATUS current
			DESCRIPTION
				"Description."
			::= { sleEponIopOnuControl 8 }

		
		sleEponIopOnuControlMaxPortNum OBJECT-TYPE
			SYNTAX Integer32
			MAX-ACCESS read-write
			STATUS current
			DESCRIPTION
				"Description."
			::= { sleEponIopOnuControl 9 }

		
		sleEponIopOnuControlPortSpeed OBJECT-TYPE
			SYNTAX INTEGER (100 | 1000 | 10000)
			MAX-ACCESS read-write
			STATUS current
			DESCRIPTION
				"Description."
			::= { sleEponIopOnuControl 10 }

		
		sleEponIopOnuControlChipVendorName OBJECT-TYPE
			SYNTAX INTEGER
				{
				eChipVendorPmc(1),
				eChipVendorTk(2),
				eChipVendorCortina(3)
				}
			MAX-ACCESS read-write
			STATUS current
			DESCRIPTION
				"Description."
			::= { sleEponIopOnuControl 11 }

		
		sleEponIopOnuControlChipVendorID OBJECT-TYPE
			SYNTAX OCTET STRING
			MAX-ACCESS read-write
			STATUS current
			DESCRIPTION
				"Description."
			::= { sleEponIopOnuControl 12 }

		
		sleEponIopOnuControlPonMode OBJECT-TYPE
			SYNTAX INTEGER
				{
				realMode(1),
				hybridMode(2)
				}
			MAX-ACCESS read-write
			STATUS current
			DESCRIPTION
				"Description."
			::= { sleEponIopOnuControl 13 }

		
		sleEponIopOnuNotification OBJECT IDENTIFIER ::= { sleEponIopOnu 3 }

		
		sleEponIopOnuAdd NOTIFICATION-TYPE
			OBJECTS { sleEponIopOnuControlChipVendorName, sleEponIopOnuIndex, sleEponIopOnuVendorName, sleEponIopOnuVendorModel, sleEponIopOnuPonMode, 
				sleEponIopOnuControlRequest, sleEponIopOnuControlStatus, sleEponIopOnuControlTimer, sleEponIopOnuControlTimeStamp, sleEponIopOnuControlReqResult, 
				sleEponIopOnuControlVendorName, sleEponIopOnuControlVendorOui, sleEponIopOnuControlModelName, sleEponIopOnuControlMaxPortNum, sleEponIopOnuControlPortSpeed, 
				sleEponIopOnuControlChipVendorID, sleEponIopOnuControlHybrid }
			STATUS current
			DESCRIPTION 
				"Description."
			::= { sleEponIopOnuNotification 1 }

		
		sleEponIopOnuDel NOTIFICATION-TYPE
			OBJECTS { sleEponIopOnuControlChipVendorID, sleEponIopOnuIndex, sleEponIopOnuVendorName, sleEponIopOnuVendorModel, sleEponIopOnuPonMode, 
				sleEponIopOnuControlRequest, sleEponIopOnuControlStatus, sleEponIopOnuControlTimer, sleEponIopOnuControlTimeStamp, sleEponIopOnuControlReqResult, 
				sleEponIopOnuControlVendorName, sleEponIopOnuControlVendorOui, sleEponIopOnuControlModelName, sleEponIopOnuControlMaxPortNum, sleEponIopOnuControlPortSpeed, 
				sleEponIopOnuControlChipVendorName, sleEponIopOnuControlHybrid }
			STATUS current
			DESCRIPTION 
				"Description."
			::= { sleEponIopOnuNotification 2 }

		
		sleEponOnuThreshold OBJECT IDENTIFIER ::= { sleEponOnu 7 }

		
		sleEponOnuThresholdAlarmTable OBJECT-TYPE
			SYNTAX SEQUENCE OF SleEponOnuThresholdAlarmEntry
			MAX-ACCESS not-accessible
			STATUS current
			DESCRIPTION
				"Description."
			::= { sleEponOnuThreshold 1 }

		
		sleEponOnuThresholdAlarmEntry OBJECT-TYPE
			SYNTAX SleEponOnuThresholdAlarmEntry
			MAX-ACCESS not-accessible
			STATUS current
			DESCRIPTION
				"Description."
			INDEX { sleEponOltIndex, sleEponOnuIndex }
			::= { sleEponOnuThresholdAlarmTable 1 }

		
		SleEponOnuThresholdAlarmEntry ::=
			SEQUENCE { 
				sleEponOnuThresholdMacAddress
					MacAddress,
				sleEponOnuThresholdCrcUpCount
					Integer32,
				sleEponOnuThresholdCrcDownCount
					Integer32,
				sleEponOnuThresholdCrcUpDownCount
					Integer32,
				sleEponOnuThresholdCrcRaisedCount
					Integer32,
				sleEponOnuThresholdCrcReleasedCount
					Integer32,
				sleEponOnuThresholdRegisteredEventCount
					Integer32,
				sleEponOnuThresholdRegisteredAlarmCount
					Integer32,
				sleEponOnuThresholdRegisteredFirstEventTime
					OCTET STRING,
				sleEponOnuThresholdRegisteredLastEventTime
					OCTET STRING,
				sleEponOnuThresholdRegisteredDuration
					OCTET STRING,
				sleEponOnuThresholdOpticPowerEventCount
					Integer32,
				sleEponOnuThresholdOpticPowerAlarmCount
					Integer32,
				sleEponOnuThresholdOpticPowerFirstEventTime
					OCTET STRING,
				sleEponOnuThresholdOpticPowerLastEventTime
					OCTET STRING,
				sleEponOnuThresholdOpticPowerDuration
					OCTET STRING,
				sleEponOnuThresholdDcVoltateEventCount
					Integer32,
				sleEponOnuThresholdDcVoltateAlarmCount
					Integer32,
				sleEponOnuThresholdDcVoltateFirstEventTime
					OCTET STRING,
				sleEponOnuThresholdDcVoltateLastEventTime
					OCTET STRING,
				sleEponOnuThresholdDcVoltateDuration
					OCTET STRING,
				sleEponOnuThresholdLoopingEventCount
					Integer32,
				sleEponOnuThresholdLoopingAlarmCount
					Integer32,
				sleEponOnuThresholdLoopingFirstEventTime
					OCTET STRING,
				sleEponOnuThresholdLoopingLastEventTime
					OCTET STRING,
				sleEponOnuThresholdLoopingDuration
					OCTET STRING,
				sleEponOnuThresholdRegisteredCount
					Integer32
			 }

		sleEponOnuThresholdMacAddress OBJECT-TYPE
			SYNTAX MacAddress
			MAX-ACCESS read-only
			STATUS current
			DESCRIPTION
				"ONU Hardware address"
			::= { sleEponOnuThresholdAlarmEntry 1 }

		
		sleEponOnuThresholdCrcUpCount OBJECT-TYPE
			SYNTAX Integer32
			MAX-ACCESS read-only
			STATUS current
			DESCRIPTION
				"ONU upstream CRC count during interval time"
			::= { sleEponOnuThresholdAlarmEntry 2 }

		
		sleEponOnuThresholdCrcDownCount OBJECT-TYPE
			SYNTAX Integer32
			MAX-ACCESS read-only
			STATUS current
			DESCRIPTION
				"ONU downstream CRC count during interval time"
			::= { sleEponOnuThresholdAlarmEntry 3 }

		
		sleEponOnuThresholdCrcUpDownCount OBJECT-TYPE
			SYNTAX Integer32
			MAX-ACCESS read-only
			STATUS current
			DESCRIPTION
				"ONU CRC count during interval time"
			::= { sleEponOnuThresholdAlarmEntry 4 }

		
		sleEponOnuThresholdCrcRaisedCount OBJECT-TYPE
			SYNTAX Integer32
			MAX-ACCESS read-only
			STATUS current
			DESCRIPTION
				"Occurred ONU CRC threshold raise alarm count"
			::= { sleEponOnuThresholdAlarmEntry 5 }

		
		sleEponOnuThresholdCrcReleasedCount OBJECT-TYPE
			SYNTAX Integer32
			MAX-ACCESS read-only
			STATUS current
			DESCRIPTION
				"Occurred ONU CRC threshold release alarm count"
			::= { sleEponOnuThresholdAlarmEntry 6 }

		
		sleEponOnuThresholdRegisteredEventCount OBJECT-TYPE
			SYNTAX Integer32
			MAX-ACCESS read-only
			STATUS current
			DESCRIPTION
				"Occurred event count"
			::= { sleEponOnuThresholdAlarmEntry 7 }

		
		sleEponOnuThresholdRegisteredAlarmCount OBJECT-TYPE
			SYNTAX Integer32
			MAX-ACCESS read-only
			STATUS current
			DESCRIPTION
				"Threshold alarm count"
			::= { sleEponOnuThresholdAlarmEntry 8 }

		
		sleEponOnuThresholdRegisteredFirstEventTime OBJECT-TYPE
			SYNTAX OCTET STRING
			MAX-ACCESS read-only
			STATUS current
			DESCRIPTION
				"First event time"
			::= { sleEponOnuThresholdAlarmEntry 9 }

		
		sleEponOnuThresholdRegisteredLastEventTime OBJECT-TYPE
			SYNTAX OCTET STRING
			MAX-ACCESS read-only
			STATUS current
			DESCRIPTION
				"Last event time"
			::= { sleEponOnuThresholdAlarmEntry 10 }

		
		sleEponOnuThresholdRegisteredDuration OBJECT-TYPE
			SYNTAX OCTET STRING
			MAX-ACCESS read-only
			STATUS current
			DESCRIPTION
				"Last time - First time"
			::= { sleEponOnuThresholdAlarmEntry 11 }

		
		sleEponOnuThresholdOpticPowerEventCount OBJECT-TYPE
			SYNTAX Integer32
			MAX-ACCESS read-only
			STATUS current
			DESCRIPTION
				"Occurred event count"
			::= { sleEponOnuThresholdAlarmEntry 12 }

		
		sleEponOnuThresholdOpticPowerAlarmCount OBJECT-TYPE
			SYNTAX Integer32
			MAX-ACCESS read-only
			STATUS current
			DESCRIPTION
				"Threshold alarm count"
			::= { sleEponOnuThresholdAlarmEntry 13 }

		
		sleEponOnuThresholdOpticPowerFirstEventTime OBJECT-TYPE
			SYNTAX OCTET STRING
			MAX-ACCESS read-only
			STATUS current
			DESCRIPTION
				"First event time"
			::= { sleEponOnuThresholdAlarmEntry 14 }

		
		sleEponOnuThresholdOpticPowerLastEventTime OBJECT-TYPE
			SYNTAX OCTET STRING
			MAX-ACCESS read-only
			STATUS current
			DESCRIPTION
				"Last event time"
			::= { sleEponOnuThresholdAlarmEntry 15 }

		
		sleEponOnuThresholdOpticPowerDuration OBJECT-TYPE
			SYNTAX OCTET STRING
			MAX-ACCESS read-only
			STATUS current
			DESCRIPTION
				"Last time - First time"
			::= { sleEponOnuThresholdAlarmEntry 16 }

		
		sleEponOnuThresholdDcVoltateEventCount OBJECT-TYPE
			SYNTAX Integer32
			MAX-ACCESS read-only
			STATUS current
			DESCRIPTION
				"Occurred event count"
			::= { sleEponOnuThresholdAlarmEntry 17 }

		
		sleEponOnuThresholdDcVoltateAlarmCount OBJECT-TYPE
			SYNTAX Integer32
			MAX-ACCESS read-only
			STATUS current
			DESCRIPTION
				"Threshold alarm count"
			::= { sleEponOnuThresholdAlarmEntry 18 }

		
		sleEponOnuThresholdDcVoltateFirstEventTime OBJECT-TYPE
			SYNTAX OCTET STRING
			MAX-ACCESS read-only
			STATUS current
			DESCRIPTION
				"First event time"
			::= { sleEponOnuThresholdAlarmEntry 19 }

		
		sleEponOnuThresholdDcVoltateLastEventTime OBJECT-TYPE
			SYNTAX OCTET STRING
			MAX-ACCESS read-only
			STATUS current
			DESCRIPTION
				"Last event time"
			::= { sleEponOnuThresholdAlarmEntry 20 }

		
		sleEponOnuThresholdDcVoltateDuration OBJECT-TYPE
			SYNTAX OCTET STRING
			MAX-ACCESS read-only
			STATUS current
			DESCRIPTION
				"Last time - First time"
			::= { sleEponOnuThresholdAlarmEntry 21 }

		
		sleEponOnuThresholdLoopingEventCount OBJECT-TYPE
			SYNTAX Integer32
			MAX-ACCESS read-only
			STATUS current
			DESCRIPTION
				"Occurred event count"
			::= { sleEponOnuThresholdAlarmEntry 22 }

		
		sleEponOnuThresholdLoopingAlarmCount OBJECT-TYPE
			SYNTAX Integer32
			MAX-ACCESS read-only
			STATUS current
			DESCRIPTION
				"Threshold alarm count"
			::= { sleEponOnuThresholdAlarmEntry 23 }

		
		sleEponOnuThresholdLoopingFirstEventTime OBJECT-TYPE
			SYNTAX OCTET STRING
			MAX-ACCESS read-only
			STATUS current
			DESCRIPTION
				"First event time"
			::= { sleEponOnuThresholdAlarmEntry 24 }

		
		sleEponOnuThresholdLoopingLastEventTime OBJECT-TYPE
			SYNTAX OCTET STRING
			MAX-ACCESS read-only
			STATUS current
			DESCRIPTION
				"Last event time"
			::= { sleEponOnuThresholdAlarmEntry 25 }

		
		sleEponOnuThresholdLoopingDuration OBJECT-TYPE
			SYNTAX OCTET STRING
			MAX-ACCESS read-only
			STATUS current
			DESCRIPTION
				"Last time - First time"
			::= { sleEponOnuThresholdAlarmEntry 26 }

		
		sleEponOnuThresholdRegisteredCount OBJECT-TYPE
			SYNTAX Integer32
			MAX-ACCESS read-only
			STATUS current
			DESCRIPTION
				"onu registered count"
			::= { sleEponOnuThresholdAlarmEntry 27 }

		
		sleEponOnuThresholdInfo OBJECT IDENTIFIER ::= { sleEponOnuThreshold 2 }

		
		sleEponOnuThresholdCrcValue OBJECT-TYPE
			SYNTAX INTEGER { disable(0) }
			MAX-ACCESS read-only
			STATUS current
			DESCRIPTION
				"Onu threshold Value (Default:45)"
			::= { sleEponOnuThresholdInfo 1 }

		
		sleEponOnuThresholdCrcCheckInterval OBJECT-TYPE
			SYNTAX Integer32 (1..525600)
			MAX-ACCESS read-only
			STATUS current
			DESCRIPTION
				"Onu threshold Check Interval (Step:minute, Default:15)"
			::= { sleEponOnuThresholdInfo 2 }

		
		sleEponOnuThresholdRegisterValue OBJECT-TYPE
			SYNTAX INTEGER { disable(0) }
			MAX-ACCESS read-only
			STATUS current
			DESCRIPTION
				"Onu threshold Value (Default:10)"
			::= { sleEponOnuThresholdInfo 3 }

		
		sleEponOnuThresholdRegisterCheckInterval OBJECT-TYPE
			SYNTAX Integer32 (1..525600)
			MAX-ACCESS read-only
			STATUS current
			DESCRIPTION
				"Onu threshold Check Interval (Step:minute, Default:60)"
			::= { sleEponOnuThresholdInfo 4 }

		
		sleEponOnuThresholdOpticPowerValue OBJECT-TYPE
			SYNTAX INTEGER { disable(0) }
			MAX-ACCESS read-only
			STATUS current
			DESCRIPTION
				"Onu threshold Value (Default:10)"
			::= { sleEponOnuThresholdInfo 5 }

		
		sleEponOnuThresholdOpticPowerCheckInterval OBJECT-TYPE
			SYNTAX Integer32 (1..525600)
			MAX-ACCESS read-only
			STATUS current
			DESCRIPTION
				"Onu threshold Check Interval (Step:minute, Default:15)"
			::= { sleEponOnuThresholdInfo 6 }

		
		sleEponOnuThresholdDcVoltageValue OBJECT-TYPE
			SYNTAX INTEGER { disable(0) }
			MAX-ACCESS read-only
			STATUS current
			DESCRIPTION
				"Onu threshold Value (Default:3)"
			::= { sleEponOnuThresholdInfo 7 }

		
		sleEponOnuThresholdDcVoltageCheckInterval OBJECT-TYPE
			SYNTAX Integer32 (1..525600)
			MAX-ACCESS read-only
			STATUS current
			DESCRIPTION
				"Onu threshold Check Interval (Step:minute, Default:60)"
			::= { sleEponOnuThresholdInfo 8 }

		
		sleEponOnuThresholdLoopingValue OBJECT-TYPE
			SYNTAX INTEGER { disable(0) }
			MAX-ACCESS read-only
			STATUS current
			DESCRIPTION
				"Onu threshold Value (Default:2)"
			::= { sleEponOnuThresholdInfo 9 }

		
		sleEponOnuThresholdLoopingCheckInterval OBJECT-TYPE
			SYNTAX Integer32 (1..525600)
			MAX-ACCESS read-only
			STATUS current
			DESCRIPTION
				"Onu threshold Check Interval (Step:minute, Default:20)"
			::= { sleEponOnuThresholdInfo 10 }

		
		sleEponOnuThresholdControl OBJECT IDENTIFIER ::= { sleEponOnuThreshold 3 }

		
		sleEponOnuThresholdControlRequest OBJECT-TYPE
			SYNTAX INTEGER
				{
				setEponOnuThreshold(1),
				noEponOnuThreshold(2)
				}
			MAX-ACCESS read-write
			STATUS current
			DESCRIPTION
				"Description."
			::= { sleEponOnuThresholdControl 1 }

		
		sleEponOnuThresholdControlStatus OBJECT-TYPE
			SYNTAX SleControlStatusType
			MAX-ACCESS read-only
			STATUS current
			DESCRIPTION
				"Description."
			::= { sleEponOnuThresholdControl 2 }

		
		sleEponOnuThresholdControlTimer OBJECT-TYPE
			SYNTAX Gauge32
			MAX-ACCESS read-write
			STATUS current
			DESCRIPTION
				"Description."
			::= { sleEponOnuThresholdControl 3 }

		
		sleEponOnuThresholdControlTimeStamp OBJECT-TYPE
			SYNTAX TimeTicks
			MAX-ACCESS read-only
			STATUS current
			DESCRIPTION
				"Description."
			::= { sleEponOnuThresholdControl 4 }

		
		sleEponOnuThresholdControlReqResult OBJECT-TYPE
			SYNTAX SleControlRequestResultType
			MAX-ACCESS read-only
			STATUS current
			DESCRIPTION
				"Description."
			::= { sleEponOnuThresholdControl 5 }

		
		sleEponOnuThresholdControlType OBJECT-TYPE
			SYNTAX INTEGER
				{
				crc(1),
				register(2),
				opticPowerAlarm(3),
				dcVoltageAlarm(4),
				looping(5)
				}
			MAX-ACCESS read-write
			STATUS current
			DESCRIPTION
				"Onu threshold type."
			::= { sleEponOnuThresholdControl 6 }

		
		sleEponOnuThresholdControlValue OBJECT-TYPE
			SYNTAX INTEGER { disable(0) }
			MAX-ACCESS read-write
			STATUS current
			DESCRIPTION
				"Onu threshold value"
			::= { sleEponOnuThresholdControl 7 }

		
		sleEponOnuThresholdControlCheckInterval OBJECT-TYPE
			SYNTAX Integer32 (1..525600)
			MAX-ACCESS read-write
			STATUS current
			DESCRIPTION
				"Description."
			::= { sleEponOnuThresholdControl 8 }

		
		sleEponOnuThresholdNotification OBJECT IDENTIFIER ::= { sleEponOnuThreshold 4 }

		
		sleEponOnuThresholdChanged NOTIFICATION-TYPE
			OBJECTS { sleEponOnuThresholdControlRequest, sleEponOnuThresholdControlTimeStamp, sleEponOnuThresholdControlReqResult, sleEponOnuThresholdControlType, sleEponOnuThresholdControlValue, 
				sleEponOnuThresholdControlCheckInterval }
			STATUS current
			DESCRIPTION 
				"Description."
			::= { sleEponOnuThresholdNotification 1 }

		
		sleEponOnuAuth OBJECT IDENTIFIER ::= { sleEponOnu 8 }

		
		sleEponOnuAuthAlarmTable OBJECT-TYPE
			SYNTAX SEQUENCE OF SleEponOnuAuthAlarmEntry
			MAX-ACCESS not-accessible
			STATUS current
			DESCRIPTION
				"Description."
			::= { sleEponOnuAuth 1 }

		
		sleEponOnuAuthAlarmEntry OBJECT-TYPE
			SYNTAX SleEponOnuAuthAlarmEntry
			MAX-ACCESS not-accessible
			STATUS current
			DESCRIPTION
				"Description."
			INDEX { sleEponOnuAuthOltIndex, sleEponOnuAuthOnuIndex, sleEponOnuAuthMac }
			::= { sleEponOnuAuthAlarmTable 1 }

		
		SleEponOnuAuthAlarmEntry ::=
			SEQUENCE { 
				sleEponOnuAuthOltIndex
					Integer32,
				sleEponOnuAuthOnuIndex
					Integer32,
				sleEponOnuAuthMac
					MacAddress,
				sleEponOnuAuthId
					OCTET STRING,
				sleEponOnuAuthPw
					OCTET STRING
			 }

		sleEponOnuAuthOltIndex OBJECT-TYPE
			SYNTAX Integer32 (1..65535)
			MAX-ACCESS read-only
			STATUS current
			DESCRIPTION
				"OLT port Index"
			::= { sleEponOnuAuthAlarmEntry 1 }

		
		sleEponOnuAuthOnuIndex OBJECT-TYPE
			SYNTAX Integer32 (1..64)
			MAX-ACCESS read-only
			STATUS current
			DESCRIPTION
				"ONU Index"
			::= { sleEponOnuAuthAlarmEntry 2 }

		
		sleEponOnuAuthMac OBJECT-TYPE
			SYNTAX MacAddress
			MAX-ACCESS read-only
			STATUS current
			DESCRIPTION
				"HGW MAC address"
			::= { sleEponOnuAuthAlarmEntry 3 }

		
		sleEponOnuAuthId OBJECT-TYPE
			SYNTAX OCTET STRING
			MAX-ACCESS read-only
			STATUS current
			DESCRIPTION
				"HGW ID"
			::= { sleEponOnuAuthAlarmEntry 4 }

		
		sleEponOnuAuthPw OBJECT-TYPE
			SYNTAX OCTET STRING
			MAX-ACCESS read-only
			STATUS current
			DESCRIPTION
				"HGW password"
			::= { sleEponOnuAuthAlarmEntry 5 }

		
		sleEponOnuAuthInfo OBJECT IDENTIFIER ::= { sleEponOnuAuth 2 }

		
		sleEponOnuAuthControl OBJECT IDENTIFIER ::= { sleEponOnuAuth 3 }

		
		sleEponOnuAuthControlRequest OBJECT-TYPE
			SYNTAX INTEGER
				{
				setEponOnuAuth(1),
				noEponOnuAuth(2)
				}
			MAX-ACCESS read-write
			STATUS current
			DESCRIPTION
				"Description."
			::= { sleEponOnuAuthControl 1 }

		
		sleEponOnuAuthControlStatus OBJECT-TYPE
			SYNTAX SleControlStatusType
			MAX-ACCESS read-only
			STATUS current
			DESCRIPTION
				"Description."
			::= { sleEponOnuAuthControl 2 }

		
		sleEponOnuAuthControlTimer OBJECT-TYPE
			SYNTAX Gauge32
			MAX-ACCESS read-write
			STATUS current
			DESCRIPTION
				"Description."
			::= { sleEponOnuAuthControl 3 }

		
		sleEponOnuAuthControlTimeStamp OBJECT-TYPE
			SYNTAX TimeTicks
			MAX-ACCESS read-only
			STATUS current
			DESCRIPTION
				"Description."
			::= { sleEponOnuAuthControl 4 }

		
		sleEponOnuAuthControlReqResult OBJECT-TYPE
			SYNTAX SleControlRequestResultType
			MAX-ACCESS read-only
			STATUS current
			DESCRIPTION
				"Description."
			::= { sleEponOnuAuthControl 5 }

		
		sleEponOnuAuthControlOltIndex OBJECT-TYPE
			SYNTAX Integer32 (1..65535)
			MAX-ACCESS read-write
			STATUS current
			DESCRIPTION
				"OLT port Index"
			::= { sleEponOnuAuthControl 6 }

		
		sleEponOnuAuthControlOnuIndex OBJECT-TYPE
			SYNTAX Integer32 (1..64)
			MAX-ACCESS read-write
			STATUS current
			DESCRIPTION
				"ONU Index"
			::= { sleEponOnuAuthControl 7 }

		
		sleEponOnuAuthControlMac OBJECT-TYPE
			SYNTAX MacAddress
			MAX-ACCESS read-write
			STATUS current
			DESCRIPTION
				"HGW MAC address"
			::= { sleEponOnuAuthControl 8 }

		
		sleEponOnuAuthControlId OBJECT-TYPE
			SYNTAX OCTET STRING
			MAX-ACCESS read-write
			STATUS current
			DESCRIPTION
				"	
				HGW ID"
			::= { sleEponOnuAuthControl 9 }

		
		sleEponOnuAuthControlPw OBJECT-TYPE
			SYNTAX OCTET STRING
			MAX-ACCESS read-write
			STATUS current
			DESCRIPTION
				"	
				HGW password"
			::= { sleEponOnuAuthControl 10 }

		
		sleEponOnuAuthNotification OBJECT IDENTIFIER ::= { sleEponOnuAuth 4 }

		
		sleEponOnuAuthChanged NOTIFICATION-TYPE
			OBJECTS { sleEponOnuAuthControlRequest, sleEponOnuAuthControlTimeStamp, sleEponOnuAuthControlReqResult, sleEponOnuAuthControlOltIndex, sleEponOnuAuthControlOnuIndex, 
				sleEponOnuAuthControlMac, sleEponOnuAuthControlId, sleEponOnuAuthControlPw }
			STATUS current
			DESCRIPTION 
				"setEponOnuAuth"
			::= { sleEponOnuAuthNotification 1 }

		
		sleEponOnuAuthDeleted NOTIFICATION-TYPE
			OBJECTS { sleEponOnuAuthControlRequest, sleEponOnuAuthControlTimeStamp, sleEponOnuAuthControlReqResult, sleEponOnuAuthControlOltIndex, sleEponOnuAuthControlOnuIndex, 
				sleEponOnuAuthControlMac }
			STATUS current
			DESCRIPTION 
				"noEponOnuAuth"
			::= { sleEponOnuAuthNotification 2 }

		
		sleEponOnuBridge OBJECT IDENTIFIER ::= { sleEpon 4 }

		
		sleEponOnuVlan OBJECT IDENTIFIER ::= { sleEponOnuBridge 1 }

		
		sleEponOnuVlanTable OBJECT-TYPE
			SYNTAX SEQUENCE OF SleEponOnuVlanEntry
			MAX-ACCESS not-accessible
			STATUS current
			DESCRIPTION
				"Description."
			::= { sleEponOnuVlan 1 }

		
		sleEponOnuVlanEntry OBJECT-TYPE
			SYNTAX SleEponOnuVlanEntry
			MAX-ACCESS not-accessible
			STATUS current
			DESCRIPTION
				"Description."
			INDEX { sleEponOltIndex, sleEponOnuIndex, sleEponOnuVlanIndex }
			::= { sleEponOnuVlanTable 1 }

		
		SleEponOnuVlanEntry ::=
			SEQUENCE { 
				sleEponOnuVlanIndex
					VlanIndex,
				sleEponOnuVlanEgressPorts
					PortList,
				sleEponOnuVlanUntaggedPorts
					PortList
			 }

		sleEponOnuVlanIndex OBJECT-TYPE
			SYNTAX VlanIndex (1..4094)
			MAX-ACCESS read-only
			STATUS current
			DESCRIPTION
				"The index of ONU VLAN"
			::= { sleEponOnuVlanEntry 1 }

		
		sleEponOnuVlanEgressPorts OBJECT-TYPE
			SYNTAX PortList
			MAX-ACCESS read-only
			STATUS current
			DESCRIPTION
				"The set of ports which are transmitting traffic for this ONU VLAN as either tagged or untagged frames."
			::= { sleEponOnuVlanEntry 2 }

		
		sleEponOnuVlanUntaggedPorts OBJECT-TYPE
			SYNTAX PortList
			MAX-ACCESS read-only
			STATUS current
			DESCRIPTION
				"The set of ports which are transmitting traffic for this VLAN as untagged frames"
			::= { sleEponOnuVlanEntry 3 }

		
		sleEponOnuPort OBJECT IDENTIFIER ::= { sleEponOnuBridge 2 }

		
		sleEponOnuPortTable OBJECT-TYPE
			SYNTAX SEQUENCE OF SleEponOnuPortEntry
			MAX-ACCESS not-accessible
			STATUS current
			DESCRIPTION
				"Description."
			::= { sleEponOnuPort 1 }

		
		sleEponOnuPortEntry OBJECT-TYPE
			SYNTAX SleEponOnuPortEntry
			MAX-ACCESS not-accessible
			STATUS current
			DESCRIPTION
				"Description."
			INDEX { sleEponOltIndex, sleEponOnuIndex, sleEponOnuPortIndex }
			::= { sleEponOnuPortTable 1 }

		
		SleEponOnuPortEntry ::=
			SEQUENCE { 
				sleEponOnuPortIndex
					INTEGER,
				sleEponOnuPortAdminStatus
					INTEGER,
				sleEponOnuPortOperStatus
					INTEGER,
				sleEponOnuPortNego
					INTEGER,
				sleEponOnuPortSpeed
					Integer32,
				sleEponOnuPortDuplex
					INTEGER,
				sleEponOnuPortMaxHost
					Integer32,
				sleEponOnuPortPvid
					VlanIndex,
				sleEponOnuPortIngressRateLimitMode
					INTEGER,
				sleEponOnuPortIngressRateLimit
					INTEGER,
				sleEponOnuPortEgressRateLimit
					INTEGER,
				sleEponOnuPortFlowControl
					INTEGER,
				sleEponOnuPortAgingTime
					Integer32,
				sleEponOnuPortForwardMode
					EnableFlag,
				sleEponOnuPortConfigEnable
					INTEGER,
				sleEponOnuPortLink
					INTEGER
			 }

		sleEponOnuPortIndex OBJECT-TYPE
			SYNTAX INTEGER (1..256)
			MAX-ACCESS read-only
			STATUS current
			DESCRIPTION
				"The index of the ONU port"
			::= { sleEponOnuPortEntry 1 }

		
		sleEponOnuPortAdminStatus OBJECT-TYPE
			SYNTAX INTEGER
				{
				na(0),
				enable(1),
				disable(2)
				}
			MAX-ACCESS read-only
			STATUS current
			DESCRIPTION
				"The desired state of the ONU port"
			::= { sleEponOnuPortEntry 2 }

		
		sleEponOnuPortOperStatus OBJECT-TYPE
			SYNTAX INTEGER
				{
				na(0),
				enable(1),
				disable(2)
				}
			MAX-ACCESS read-only
			STATUS current
			DESCRIPTION
				"The current operational state of the ONU port"
			::= { sleEponOnuPortEntry 3 }

		
		sleEponOnuPortNego OBJECT-TYPE
			SYNTAX INTEGER
				{
				na(0),
				on(1),
				off(2)
				}
			MAX-ACCESS read-only
			STATUS current
			DESCRIPTION
				"It's auto-negotiation for a port, automatically to match the transmission speed and the duplex mode of the attached device"
			::= { sleEponOnuPortEntry 4 }

		
		sleEponOnuPortSpeed OBJECT-TYPE
			SYNTAX Integer32
			MAX-ACCESS read-only
			STATUS current
			DESCRIPTION
				"It express port speed that configure transmit rate of each port."
			::= { sleEponOnuPortEntry 5 }

		
		sleEponOnuPortDuplex OBJECT-TYPE
			SYNTAX INTEGER
				{
				na(0),
				full(1),
				half(2)
				}
			MAX-ACCESS read-only
			STATUS current
			DESCRIPTION
				"It express half duplex or full duplex mode. Only unidirectional communication is possible on half duplex mode and bi-directional communication is possible on full duplex mode to transmit packet for two ways."
			::= { sleEponOnuPortEntry 6 }

		
		sleEponOnuPortMaxHost OBJECT-TYPE
			SYNTAX Integer32
			MAX-ACCESS read-only
			STATUS current
			DESCRIPTION
				"It can limit the number of users by configuring maximum number of users also named as Max host for each ONU port"
			::= { sleEponOnuPortEntry 7 }

		
		sleEponOnuPortPvid OBJECT-TYPE
			SYNTAX VlanIndex
			MAX-ACCESS read-only
			STATUS current
			DESCRIPTION
				"It is PVID that configure in ONU port"
			::= { sleEponOnuPortEntry 8 }

		
		sleEponOnuPortIngressRateLimitMode OBJECT-TYPE
			SYNTAX INTEGER
				{
				all(0),
				multiBroadUnicast(1),
				multiBroadcast(2),
				broadcast(3)
				}
			MAX-ACCESS read-only
			STATUS current
			DESCRIPTION
				"It is rate limit mode in Ingress"
			::= { sleEponOnuPortEntry 9 }

		
		sleEponOnuPortIngressRateLimit OBJECT-TYPE
			SYNTAX INTEGER (0 | 62..100000)
			MAX-ACCESS read-only
			STATUS current
			DESCRIPTION
				"It is configurable port rate limit in Ingress"
			::= { sleEponOnuPortEntry 10 }

		
		sleEponOnuPortEgressRateLimit OBJECT-TYPE
			SYNTAX INTEGER (0 | 62..100000)
			MAX-ACCESS read-only
			STATUS current
			DESCRIPTION
				"It is configurable port rate limit in Egress"
			::= { sleEponOnuPortEntry 11 }

		
		sleEponOnuPortFlowControl OBJECT-TYPE
			SYNTAX INTEGER
				{
				none(0),
				on(1),
				off(2)
				}
			MAX-ACCESS read-only
			STATUS current
			DESCRIPTION
				"Description."
			::= { sleEponOnuPortEntry 12 }

		
		sleEponOnuPortAgingTime OBJECT-TYPE
			SYNTAX Integer32
			MAX-ACCESS read-only
			STATUS current
			DESCRIPTION
				"onu max-host aging time."
			::= { sleEponOnuPortEntry 13 }

		
		sleEponOnuPortForwardMode OBJECT-TYPE
			SYNTAX EnableFlag
			MAX-ACCESS read-write
			STATUS current
			DESCRIPTION
				"onu max-host forward mode."
			::= { sleEponOnuPortEntry 14 }

		
		sleEponOnuPortConfigEnable OBJECT-TYPE
			SYNTAX INTEGER
				{
				na(0),
				enable(1),
				disable(2)
				}
			MAX-ACCESS read-only
			STATUS current
			DESCRIPTION
				"enable or disable of configuration state"
			::= { sleEponOnuPortEntry 15 }

		
		sleEponOnuPortLink OBJECT-TYPE
			SYNTAX INTEGER
				{
				up(1),
				down(2)
				}
			MAX-ACCESS read-only
			STATUS current
			DESCRIPTION
				"Link type"
			::= { sleEponOnuPortEntry 16 }

		
		sleEponOnuPortControl OBJECT IDENTIFIER ::= { sleEponOnuPort 2 }

		
		sleEponOnuPortControlRequest OBJECT-TYPE
			SYNTAX INTEGER
				{
				setEponOnuPortReset(1),
				setEponOnuPortEnable(2)
				}
			MAX-ACCESS read-write
			STATUS current
			DESCRIPTION
				"The request of a user command"
			::= { sleEponOnuPortControl 1 }

		
		sleEponOnuPortControlStatus OBJECT-TYPE
			SYNTAX SleControlStatusType
			MAX-ACCESS read-only
			STATUS current
			DESCRIPTION
				"The status of user command"
			::= { sleEponOnuPortControl 2 }

		
		sleEponOnuPortControlTimer OBJECT-TYPE
			SYNTAX Gauge32
			MAX-ACCESS read-write
			STATUS current
			DESCRIPTION
				"The maximum time for the manager for a long running user command"
			::= { sleEponOnuPortControl 3 }

		
		sleEponOnuPortControlTimeStamp OBJECT-TYPE
			SYNTAX TimeTicks
			MAX-ACCESS read-only
			STATUS current
			DESCRIPTION
				"The time stamp of the last command(end of command)"
			::= { sleEponOnuPortControl 4 }

		
		sleEponOnuPortControlReqResult OBJECT-TYPE
			SYNTAX SleControlRequestResultType
			MAX-ACCESS read-only
			STATUS current
			DESCRIPTION
				"The result of the last user command"
			::= { sleEponOnuPortControl 5 }

		
		sleEponOnuPortControlOltIndex OBJECT-TYPE
			SYNTAX INTEGER (1..512)
			MAX-ACCESS read-write
			STATUS current
			DESCRIPTION
				"OLT port Index"
			::= { sleEponOnuPortControl 6 }

		
		sleEponOnuPortControlOnuIndex OBJECT-TYPE
			SYNTAX INTEGER (1..64)
			MAX-ACCESS read-write
			STATUS current
			DESCRIPTION
				"ONU Index"
			::= { sleEponOnuPortControl 7 }

		
		sleEponOnuPortControlPortIndex OBJECT-TYPE
			SYNTAX INTEGER (1..256)
			MAX-ACCESS read-write
			STATUS current
			DESCRIPTION
				"The index of the ONU port"
			::= { sleEponOnuPortControl 8 }

		
		sleEponOnuPortControlConfigEnable OBJECT-TYPE
			SYNTAX INTEGER
				{
				delete(0),
				enable(1),
				disable(2)
				}
			MAX-ACCESS read-write
			STATUS current
			DESCRIPTION
				"configuration enable"
			::= { sleEponOnuPortControl 9 }

		
		sleEponOnuPortNotification OBJECT IDENTIFIER ::= { sleEponOnuPort 3 }

		
		sleEponOnuPortReset NOTIFICATION-TYPE
			OBJECTS { sleEponOnuPortControlRequest, sleEponOnuPortControlTimeStamp, sleEponOnuPortControlReqResult, sleEponOnuPortControlOltIndex, sleEponOnuPortControlOnuIndex, 
				sleEponOnuPortControlPortIndex }
			STATUS current
			DESCRIPTION 
				"Description."
			::= { sleEponOnuPortNotification 1 }

		
		sleEponOnuPortEnableChanged NOTIFICATION-TYPE
			OBJECTS { sleEponOnuPortControlRequest, sleEponOnuPortControlTimeStamp, sleEponOnuPortControlReqResult, sleEponOnuPortControlOltIndex, sleEponOnuPortControlOnuIndex, 
				sleEponOnuPortControlPortIndex, sleEponOnuPortControlConfigEnable }
			STATUS current
			DESCRIPTION 
				"Description."
			::= { sleEponOnuPortNotification 2 }

		
		sleEponOnuFdb OBJECT IDENTIFIER ::= { sleEponOnuBridge 3 }

		
		sleEponOnuFdbTable OBJECT-TYPE
			SYNTAX SEQUENCE OF SleEponOnuFdbEntry
			MAX-ACCESS not-accessible
			STATUS current
			DESCRIPTION
				"Description."
			::= { sleEponOnuFdb 1 }

		
		sleEponOnuFdbEntry OBJECT-TYPE
			SYNTAX SleEponOnuFdbEntry
			MAX-ACCESS not-accessible
			STATUS current
			DESCRIPTION
				"Description."
			INDEX { sleEponOltIndex, sleEponOnuIndex, sleEponOnuFdbMacAddress }
			::= { sleEponOnuFdbTable 1 }

		
		SleEponOnuFdbEntry ::=
			SEQUENCE { 
				sleEponOnuFdbMacAddress
					MacAddress,
				sleEponOnuFdbType
					INTEGER,
				sleEponOnuFdbPermission
					INTEGER,
				sleEponOnuFdbOnuId
					INTEGER,
				sleEponOnuFdbIPAddress
					OCTET STRING
			 }

		sleEponOnuFdbMacAddress OBJECT-TYPE
			SYNTAX MacAddress
			MAX-ACCESS read-only
			STATUS current
			DESCRIPTION
				"The fdb address of ONT"
			::= { sleEponOnuFdbEntry 1 }

		
		sleEponOnuFdbType OBJECT-TYPE
			SYNTAX INTEGER
				{
				local(0),
				static(1),
				dynamic(2)
				}
			MAX-ACCESS read-only
			STATUS current
			DESCRIPTION
				"The type of fdb address."
			::= { sleEponOnuFdbEntry 2 }

		
		sleEponOnuFdbPermission OBJECT-TYPE
			SYNTAX INTEGER
				{
				deny(0),
				permit(1)
				}
			MAX-ACCESS read-only
			STATUS current
			DESCRIPTION
				"Description."
			::= { sleEponOnuFdbEntry 3 }

		
		sleEponOnuFdbOnuId OBJECT-TYPE
			SYNTAX INTEGER (1..64)
			MAX-ACCESS read-only
			STATUS current
			DESCRIPTION
				"ONU Index, for V8500"
			::= { sleEponOnuFdbEntry 4 }

		
		sleEponOnuFdbIPAddress OBJECT-TYPE
			SYNTAX OCTET STRING
			MAX-ACCESS read-only
			STATUS current
			DESCRIPTION
				"Allocated IP address list , for V8500"
			::= { sleEponOnuFdbEntry 5 }

		
		sleEponOnuFdbControl OBJECT IDENTIFIER ::= { sleEponOnuFdb 2 }

		
		sleEponOnuFdbControlRequest OBJECT-TYPE
			SYNTAX INTEGER { clearOltMac(1) }
			MAX-ACCESS read-write
			STATUS current
			DESCRIPTION
				"Description."
			::= { sleEponOnuFdbControl 1 }

		
		sleEponOnuFdbControlStatus OBJECT-TYPE
			SYNTAX SleControlStatusType
			MAX-ACCESS read-only
			STATUS current
			DESCRIPTION
				"Description."
			::= { sleEponOnuFdbControl 2 }

		
		sleEponOnuFdbControlTimer OBJECT-TYPE
			SYNTAX Gauge32
			MAX-ACCESS read-write
			STATUS current
			DESCRIPTION
				"Description."
			::= { sleEponOnuFdbControl 3 }

		
		sleEponOnuFdbControlTimeStamp OBJECT-TYPE
			SYNTAX TimeTicks
			MAX-ACCESS read-only
			STATUS current
			DESCRIPTION
				"Description."
			::= { sleEponOnuFdbControl 4 }

		
		sleEponOnuFdbControlReqResult OBJECT-TYPE
			SYNTAX SleControlRequestResultType
			MAX-ACCESS read-only
			STATUS current
			DESCRIPTION
				"Description."
			::= { sleEponOnuFdbControl 5 }

		
		sleEponOnuFdbControlOltIndex OBJECT-TYPE
			SYNTAX INTEGER (1..512)
			MAX-ACCESS read-write
			STATUS current
			DESCRIPTION
				"Description."
			::= { sleEponOnuFdbControl 6 }

		
		sleEponOnuFdbControlOnuIndex OBJECT-TYPE
			SYNTAX INTEGER (1..64)
			MAX-ACCESS read-write
			STATUS current
			DESCRIPTION
				"Description."
			::= { sleEponOnuFdbControl 7 }

		
		sleEponOnuFdbControlType OBJECT-TYPE
			SYNTAX INTEGER
				{
				dynamic(1),
				static(2),
				all(3)
				}
			MAX-ACCESS read-write
			STATUS current
			DESCRIPTION
				"Description."
			::= { sleEponOnuFdbControl 8 }

		
		sleEponOnuFdbNotification OBJECT IDENTIFIER ::= { sleEponOnuFdb 3 }

		
		sleEponOnuFdbMacCleared NOTIFICATION-TYPE
			OBJECTS { sleEponOnuFdbControlRequest, sleEponOnuFdbControlTimeStamp, sleEponOnuFdbControlReqResult, sleEponOnuFdbControlOltIndex, sleEponOnuFdbControlOnuIndex, 
				sleEponOnuFdbControlType }
			STATUS current
			DESCRIPTION 
				"Description."
			::= { sleEponOnuFdbNotification 1 }

		
		sleEponOnuUserMac OBJECT IDENTIFIER ::= { sleEponOnuBridge 4 }

		
		sleEponOnuUserMacTable OBJECT-TYPE
			SYNTAX SEQUENCE OF SleEponOnuUserMacEntry
			MAX-ACCESS not-accessible
			STATUS current
			DESCRIPTION
				"Description."
			::= { sleEponOnuUserMac 1 }

		
		sleEponOnuUserMacEntry OBJECT-TYPE
			SYNTAX SleEponOnuUserMacEntry
			MAX-ACCESS not-accessible
			STATUS current
			DESCRIPTION
				"Description."
			INDEX { sleEponOltIndex, sleEponOnuIndex, sleEponOnuUserMacIndex }
			::= { sleEponOnuUserMacTable 1 }

		
		SleEponOnuUserMacEntry ::=
			SEQUENCE { 
				sleEponOnuUserMacIndex
					INTEGER,
				sleEponOnuUserMacMacAddress
					MacAddress,
				sleEponOnuUserMacUsedTime
					TimeTicks,
				sleEponOnuUserUniDynamicMacAddress
					MacAddress,
				sleEponOnuUserUniStaticMacAddress
					MacAddress
			 }

		sleEponOnuUserMacIndex OBJECT-TYPE
			SYNTAX INTEGER (1..8)
			MAX-ACCESS read-only
			STATUS current
			DESCRIPTION
				"the MAC address index."
			::= { sleEponOnuUserMacEntry 1 }

		
		sleEponOnuUserMacMacAddress OBJECT-TYPE
			SYNTAX MacAddress
			MAX-ACCESS read-only
			STATUS current
			DESCRIPTION
				"the MAC address."
			::= { sleEponOnuUserMacEntry 2 }

		
		sleEponOnuUserMacUsedTime OBJECT-TYPE
			SYNTAX TimeTicks
			MAX-ACCESS read-only
			STATUS current
			DESCRIPTION
				"the MAC address used time."
			::= { sleEponOnuUserMacEntry 3 }

		
		sleEponOnuUserUniDynamicMacAddress OBJECT-TYPE
			SYNTAX MacAddress
			MAX-ACCESS read-only
			STATUS current
			DESCRIPTION
				"Dynamic MAC address learned by ONU UNI."
			::= { sleEponOnuUserMacEntry 4 }

		
		sleEponOnuUserUniStaticMacAddress OBJECT-TYPE
			SYNTAX MacAddress
			MAX-ACCESS read-only
			STATUS current
			DESCRIPTION
				"Static MAC address learned by ONU UNI."
			::= { sleEponOnuUserMacEntry 5 }

		
		sleEponOnuUserMacControl OBJECT IDENTIFIER ::= { sleEponOnuUserMac 2 }

		
		sleEponOnuUserMacControlRequest OBJECT-TYPE
			SYNTAX INTEGER
				{
				sleEponOnuUserMacControlStaticMacSet(1),
				sleEponOnuUserMacControlStaticMacCleared(2),
				sleEponOnuUserMacControlDynamicMacCleared(3)
				}
			MAX-ACCESS read-write
			STATUS current
			DESCRIPTION
				"The request of a user command."
			::= { sleEponOnuUserMacControl 1 }

		
		sleEponOnuUserMacControlStatus OBJECT-TYPE
			SYNTAX SleControlStatusType
			MAX-ACCESS read-only
			STATUS current
			DESCRIPTION
				"The status of user command."
			::= { sleEponOnuUserMacControl 2 }

		
		sleEponOnuUserMacControlTimer OBJECT-TYPE
			SYNTAX Gauge32
			MAX-ACCESS read-write
			STATUS current
			DESCRIPTION
				"The maximum time for the manager for a long running user command."
			::= { sleEponOnuUserMacControl 3 }

		
		sleEponOnuUserMacControlTimeStamp OBJECT-TYPE
			SYNTAX TimeTicks
			MAX-ACCESS read-only
			STATUS current
			DESCRIPTION
				"The time stamp of the last command(end of command)."
			::= { sleEponOnuUserMacControl 4 }

		
		sleEponOnuUserMacControlReqResult OBJECT-TYPE
			SYNTAX SleControlRequestResultType
			MAX-ACCESS read-only
			STATUS current
			DESCRIPTION
				"The result of the last user command."
			::= { sleEponOnuUserMacControl 5 }

		
		sleEponOnuUserMacControlOltIndex OBJECT-TYPE
			SYNTAX INTEGER (1..24)
			MAX-ACCESS read-write
			STATUS current
			DESCRIPTION
				"OLT index."
			::= { sleEponOnuUserMacControl 6 }

		
		sleEponOnuUserMacControlOnuIndex OBJECT-TYPE
			SYNTAX INTEGER (1..32)
			MAX-ACCESS read-write
			STATUS current
			DESCRIPTION
				"ONU index <1-64>."
			::= { sleEponOnuUserMacControl 7 }

		
		sleEponOnuUserMacControlStaticMac OBJECT-TYPE
			SYNTAX MacAddress
			MAX-ACCESS read-write
			STATUS current
			DESCRIPTION
				"Static MAC address learned by ONU UNI."
			::= { sleEponOnuUserMacControl 8 }

		
		sleEponOnuUserMacNotification OBJECT IDENTIFIER ::= { sleEponOnuUserMac 3 }

		
		sleEponOnuUserMacStaticMacSet NOTIFICATION-TYPE
			OBJECTS { sleEponOnuUserMacControlRequest, sleEponOnuUserMacControlReqResult, sleEponOnuUserMacControlOltIndex, sleEponOnuUserMacControlOnuIndex, sleEponOnuUserMacControlStaticMac
				 }
			STATUS current
			DESCRIPTION 
				"Description."
			::= { sleEponOnuUserMacNotification 1 }

		
		sleEponOnuUserMacStaticMacCleared NOTIFICATION-TYPE
			OBJECTS { sleEponOnuUserMacControlRequest, sleEponOnuUserMacControlReqResult, sleEponOnuUserMacControlOltIndex, sleEponOnuUserMacControlOnuIndex }
			STATUS current
			DESCRIPTION 
				"Description."
			::= { sleEponOnuUserMacNotification 2 }

		
		sleEponOnuUserMacDynamicMacCleared NOTIFICATION-TYPE
			OBJECTS { sleEponOnuUserMacControlRequest, sleEponOnuUserMacControlReqResult, sleEponOnuUserMacControlOltIndex, sleEponOnuUserMacControlOnuIndex }
			STATUS current
			DESCRIPTION 
				"Description."
			::= { sleEponOnuUserMacNotification 3 }

		
		sleEponOnuSubscriber OBJECT IDENTIFIER ::= { sleEponOnuBridge 5 }

		
		sleEponOnuSubscriberCurrentTable OBJECT-TYPE
			SYNTAX SEQUENCE OF SleEponOnuSubscriberCurrentEntry
			MAX-ACCESS not-accessible
			STATUS current
			DESCRIPTION
				"Description."
			::= { sleEponOnuSubscriber 1 }

		
		sleEponOnuSubscriberCurrentEntry OBJECT-TYPE
			SYNTAX SleEponOnuSubscriberCurrentEntry
			MAX-ACCESS not-accessible
			STATUS current
			DESCRIPTION
				"Description."
			INDEX { sleEponOltIndex, sleEponOnuIndex, sleEponOnuSubscriberCurrentIpAddress }
			::= { sleEponOnuSubscriberCurrentTable 1 }

		
		SleEponOnuSubscriberCurrentEntry ::=
			SEQUENCE { 
				sleEponOnuSubscriberCurrentIpAddress
					IpAddress,
				sleEponOnuSubscriberCurrentMacAddress
					MacAddress,
				sleEponOnuSubscriberCurrentPort
					INTEGER,
				sleEponOnuSubscriberCurrentTime
					Gauge32
			 }

		sleEponOnuSubscriberCurrentIpAddress OBJECT-TYPE
			SYNTAX IpAddress
			MAX-ACCESS read-only
			STATUS current
			DESCRIPTION
				"Description."
			::= { sleEponOnuSubscriberCurrentEntry 1 }

		
		sleEponOnuSubscriberCurrentMacAddress OBJECT-TYPE
			SYNTAX MacAddress
			MAX-ACCESS read-only
			STATUS current
			DESCRIPTION
				"Description."
			::= { sleEponOnuSubscriberCurrentEntry 2 }

		
		sleEponOnuSubscriberCurrentPort OBJECT-TYPE
			SYNTAX INTEGER (1..256)
			MAX-ACCESS read-only
			STATUS current
			DESCRIPTION
				"Description."
			::= { sleEponOnuSubscriberCurrentEntry 3 }

		
		sleEponOnuSubscriberCurrentTime OBJECT-TYPE
			SYNTAX Gauge32
			MAX-ACCESS read-only
			STATUS current
			DESCRIPTION
				"Description."
			::= { sleEponOnuSubscriberCurrentEntry 4 }

		
		sleEponOnuSubscriberHistoryTable OBJECT-TYPE
			SYNTAX SEQUENCE OF SleEponOnuSubscriberHistoryEntry
			MAX-ACCESS not-accessible
			STATUS current
			DESCRIPTION
				"Description."
			::= { sleEponOnuSubscriber 2 }

		
		sleEponOnuSubscriberHistoryEntry OBJECT-TYPE
			SYNTAX SleEponOnuSubscriberHistoryEntry
			MAX-ACCESS not-accessible
			STATUS current
			DESCRIPTION
				"Description."
			INDEX { sleEponOltIndex, sleEponOnuIndex, sleEponOnuSubscriberHistoryTime, sleEponOnuSubscriberHistoryIpAddress }
			::= { sleEponOnuSubscriberHistoryTable 1 }

		
		SleEponOnuSubscriberHistoryEntry ::=
			SEQUENCE { 
				sleEponOnuSubscriberHistoryIpAddress
					IpAddress,
				sleEponOnuSubscriberHistoryMacAddress
					MacAddress,
				sleEponOnuSubscriberHistoryPort
					INTEGER,
				sleEponOnuSubscriberHistoryTime
					Gauge32
			 }

		sleEponOnuSubscriberHistoryIpAddress OBJECT-TYPE
			SYNTAX IpAddress
			MAX-ACCESS read-only
			STATUS current
			DESCRIPTION
				"Description."
			::= { sleEponOnuSubscriberHistoryEntry 1 }

		
		sleEponOnuSubscriberHistoryMacAddress OBJECT-TYPE
			SYNTAX MacAddress
			MAX-ACCESS read-only
			STATUS current
			DESCRIPTION
				"Description."
			::= { sleEponOnuSubscriberHistoryEntry 2 }

		
		sleEponOnuSubscriberHistoryPort OBJECT-TYPE
			SYNTAX INTEGER (1..256)
			MAX-ACCESS read-only
			STATUS current
			DESCRIPTION
				"Description."
			::= { sleEponOnuSubscriberHistoryEntry 3 }

		
		sleEponOnuSubscriberHistoryTime OBJECT-TYPE
			SYNTAX Gauge32 (1..65535)
			MAX-ACCESS read-only
			STATUS current
			DESCRIPTION
				"Description."
			::= { sleEponOnuSubscriberHistoryEntry 4 }

		
		sleEponOnuSubscriberControl OBJECT IDENTIFIER ::= { sleEponOnuSubscriber 3 }

		
		sleEponOnuSubscriberControlRequest OBJECT-TYPE
			SYNTAX INTEGER
				{
				clearSubscriberHistoryOlt(1),
				clearSubscriberHistoryOnu(2)
				}
			MAX-ACCESS read-write
			STATUS current
			DESCRIPTION
				"Description."
			::= { sleEponOnuSubscriberControl 1 }

		
		sleEponOnuSubscriberControlStatus OBJECT-TYPE
			SYNTAX SleControlStatusType
			MAX-ACCESS read-only
			STATUS current
			DESCRIPTION
				"Description."
			::= { sleEponOnuSubscriberControl 2 }

		
		sleEponOnuSubscriberControlTimer OBJECT-TYPE
			SYNTAX Gauge32
			MAX-ACCESS read-write
			STATUS current
			DESCRIPTION
				"Description."
			::= { sleEponOnuSubscriberControl 3 }

		
		sleEponOnuSubscriberControlTimeStamp OBJECT-TYPE
			SYNTAX Counter64
			MAX-ACCESS read-only
			STATUS current
			DESCRIPTION
				"Description."
			::= { sleEponOnuSubscriberControl 4 }

		
		sleEponOnuSubscriberControlReqResult OBJECT-TYPE
			SYNTAX Integer32
			MAX-ACCESS read-write
			STATUS current
			DESCRIPTION
				"Description."
			::= { sleEponOnuSubscriberControl 5 }

		
		sleEponOnuSubscriberControlOltIndex OBJECT-TYPE
			SYNTAX INTEGER (1..512)
			MAX-ACCESS read-write
			STATUS current
			DESCRIPTION
				"Description."
			::= { sleEponOnuSubscriberControl 6 }

		
		sleEponOnuSubscriberControlOnuIndex OBJECT-TYPE
			SYNTAX INTEGER (1..64)
			MAX-ACCESS read-write
			STATUS current
			DESCRIPTION
				"Description."
			::= { sleEponOnuSubscriberControl 7 }

		
		sleEponOnuSubscriberNotification OBJECT IDENTIFIER ::= { sleEponOnuSubscriber 4 }

		
		sleEponOnuSubscriberHistoryOltCleared NOTIFICATION-TYPE
			OBJECTS { sleEponOnuSubscriberControlRequest, sleEponOnuSubscriberControlTimeStamp, sleEponOnuSubscriberControlReqResult, sleEponOnuSubscriberControlOltIndex }
			STATUS current
			DESCRIPTION 
				"Description."
			::= { sleEponOnuSubscriberNotification 1 }

		
		sleEponOnuSubscriberHistroyOnuCleared NOTIFICATION-TYPE
			OBJECTS { sleEponOnuSubscriberControlRequest, sleEponOnuSubscriberControlTimeStamp, sleEponOnuSubscriberControlReqResult, sleEponOnuSubscriberControlOltIndex, sleEponOnuSubscriberControlOnuIndex
				 }
			STATUS current
			DESCRIPTION 
				"Description."
			::= { sleEponOnuSubscriberNotification 2 }

		
		sleEponOnuMacTable OBJECT IDENTIFIER ::= { sleEponOnuBridge 6 }

		
		sleEponOnuMacTableTable OBJECT-TYPE
			SYNTAX SEQUENCE OF SleEponOnuMacTableEntry
			MAX-ACCESS not-accessible
			STATUS current
			DESCRIPTION
				"Description."
			::= { sleEponOnuMacTable 1 }

		
		sleEponOnuMacTableEntry OBJECT-TYPE
			SYNTAX SleEponOnuMacTableEntry
			MAX-ACCESS not-accessible
			STATUS current
			DESCRIPTION
				"Description."
			INDEX { sleEponOltIndex, sleEponOnuIndex, sleEponOnuFdbMacAddress }
			::= { sleEponOnuMacTableTable 1 }

		
		SleEponOnuMacTableEntry ::=
			SEQUENCE { 
				sleEponOnuMacTableDynamicMacAddress
					MacAddress,
				sleEponOnuMacTableStaticMacAddress
					MacAddress
			 }

		sleEponOnuMacTableDynamicMacAddress OBJECT-TYPE
			SYNTAX MacAddress
			MAX-ACCESS read-only
			STATUS current
			DESCRIPTION
				"The fdb address of ONT"
			::= { sleEponOnuMacTableEntry 1 }

		
		sleEponOnuMacTableStaticMacAddress OBJECT-TYPE
			SYNTAX MacAddress
			MAX-ACCESS read-only
			STATUS current
			DESCRIPTION
				"The fdb address of ONT"
			::= { sleEponOnuMacTableEntry 2 }

		
		sleEponOnuIGMP OBJECT IDENTIFIER ::= { sleEponOnuBridge 7 }

		
		sleEponOnuIGMPTable OBJECT-TYPE
			SYNTAX SEQUENCE OF SleEponOnuIGMPEntry
			MAX-ACCESS not-accessible
			STATUS current
			DESCRIPTION
				"Description."
			::= { sleEponOnuIGMP 1 }

		
		sleEponOnuIGMPEntry OBJECT-TYPE
			SYNTAX SleEponOnuIGMPEntry
			MAX-ACCESS not-accessible
			STATUS current
			DESCRIPTION
				"Description."
			INDEX { sleEponOltIndex, sleEponOnuIndex }
			::= { sleEponOnuIGMPTable 1 }

		
		SleEponOnuIGMPEntry ::=
			SEQUENCE { 
				sleEponOnuIGMPAddress
					IpAddress
			 }

		sleEponOnuIGMPAddress OBJECT-TYPE
			SYNTAX IpAddress
			MAX-ACCESS read-only
			STATUS current
			DESCRIPTION
				"IP address"
			::= { sleEponOnuIGMPEntry 1 }

		
		sleEponOnuProfilePort OBJECT IDENTIFIER ::= { sleEponOnuBridge 8 }

		
		sleEponOnuProfilePortTable OBJECT-TYPE
			SYNTAX SEQUENCE OF SleEponOnuProfilePortEntry
			MAX-ACCESS not-accessible
			STATUS current
			DESCRIPTION
				"Description."
			::= { sleEponOnuProfilePort 1 }

		
		sleEponOnuProfilePortEntry OBJECT-TYPE
			SYNTAX SleEponOnuProfilePortEntry
			MAX-ACCESS not-accessible
			STATUS current
			DESCRIPTION
				"Description."
			INDEX { sleEponOltIndex, sleEponOnuIndex, sleEponOnuPortIndex }
			::= { sleEponOnuProfilePortTable 1 }

		
		SleEponOnuProfilePortEntry ::=
			SEQUENCE { 
				sleEponOnuProfilePortIndex
					INTEGER,
				sleEponProfileOnuPortAdminStatus
					INTEGER,
				sleEponOnuProfilePortMaxHost
					INTEGER,
				sleEponOnuProfileUniPortMaxHost
					INTEGER,
				sleEponOnuProfilePortIngressRateLimitMode
					INTEGER,
				sleEponOnuProfilePortIngressRateLimit
					INTEGER,
				sleEponOnuProfilePortEgressRateLimit
					INTEGER
			 }

		sleEponOnuProfilePortIndex OBJECT-TYPE
			SYNTAX INTEGER (1..256)
			MAX-ACCESS read-only
			STATUS current
			DESCRIPTION
				"The index of the ONU port"
			::= { sleEponOnuProfilePortEntry 1 }

		
		sleEponProfileOnuPortAdminStatus OBJECT-TYPE
			SYNTAX INTEGER
				{
				enable(1),
				disable(2)
				}
			MAX-ACCESS read-only
			STATUS current
			DESCRIPTION
				"The desired state of the ONU port"
			::= { sleEponOnuProfilePortEntry 2 }

		
		sleEponOnuProfilePortMaxHost OBJECT-TYPE
			SYNTAX INTEGER (1..16)
			MAX-ACCESS read-only
			STATUS current
			DESCRIPTION
				"The max-host number of the ONU port"
			::= { sleEponOnuProfilePortEntry 3 }

		
		sleEponOnuProfileUniPortMaxHost OBJECT-TYPE
			SYNTAX INTEGER (1..120)
			MAX-ACCESS read-only
			STATUS current
			DESCRIPTION
				"The max-host number of the ONU UNI port"
			::= { sleEponOnuProfilePortEntry 4 }

		
		sleEponOnuProfilePortIngressRateLimitMode OBJECT-TYPE
			SYNTAX INTEGER
				{
				all(0),
				multiBroadUnicast(1),
				multiBroadcast(2),
				broadcast(3)
				}
			MAX-ACCESS read-only
			STATUS current
			DESCRIPTION
				"It is rate limit mode in Ingress
				0  Limit all frames
				 1  Limit multicast, broadcast and flooded unicast frame
				 2  Limit multicast, broadcast frame
				 3  Limit broadcast frame only"
			::= { sleEponOnuProfilePortEntry 5 }

		
		sleEponOnuProfilePortIngressRateLimit OBJECT-TYPE
			SYNTAX INTEGER (0 | 62..1000000)
			MAX-ACCESS read-only
			STATUS current
			DESCRIPTION
				"It is configurable port rate limit in Ingress
				The value of 0 is unlimit
				"
			DEFVAL { 0 }
			::= { sleEponOnuProfilePortEntry 6 }

		
		sleEponOnuProfilePortEgressRateLimit OBJECT-TYPE
			SYNTAX INTEGER (0 | 62..1000000)
			MAX-ACCESS read-only
			STATUS current
			DESCRIPTION
				"It is configurable port rate limit in Egress
				The value of 0 is unlimit
				"
			DEFVAL { 0 }
			::= { sleEponOnuProfilePortEntry 7 }

		
		sleEponOnuProfilePortControl OBJECT IDENTIFIER ::= { sleEponOnuProfilePort 2 }

		
		sleEponOnuProfilePortControlRequest OBJECT-TYPE
			SYNTAX INTEGER
				{
				setOnuPortAdminStatus(1),
				setOnuPortMaxHost(2),
				setOnuUniPortMaxHost(3),
				setOnuPortRateLimitIngress(4),
				setOnuPortRateLimitEgress(5),
				deleteOnuPortAdminstatus(6),
				deleteOnuPortMaxHost(7),
				deleteOnuUniPortMaxHost(8),
				deleteOnuPortRateLimitIngress(9),
				deleteOnuPortRateLimitEgress(10),
				resetOnuPortAdminStatus(11),
				resetOnuOnuPortMaxHost(12)
				}
			MAX-ACCESS read-write
			STATUS current
			DESCRIPTION
				"The request of a user command"
			::= { sleEponOnuProfilePortControl 1 }

		
		sleEponOnuProfilePortControlStatus OBJECT-TYPE
			SYNTAX SleControlStatusType
			MAX-ACCESS read-only
			STATUS current
			DESCRIPTION
				"The status of user command"
			::= { sleEponOnuProfilePortControl 2 }

		
		sleEponOnuProfilePortControlTimer OBJECT-TYPE
			SYNTAX Gauge32
			MAX-ACCESS read-write
			STATUS current
			DESCRIPTION
				"The maximum time for the manager for a long running user command"
			::= { sleEponOnuProfilePortControl 3 }

		
		sleEponOnuProfilePortControlTimeStamp OBJECT-TYPE
			SYNTAX TimeTicks
			MAX-ACCESS read-only
			STATUS current
			DESCRIPTION
				"The time stamp of the last command(end of command)"
			::= { sleEponOnuProfilePortControl 4 }

		
		sleEponOnuProfilePortControlReqResult OBJECT-TYPE
			SYNTAX SleControlRequestResultType
			MAX-ACCESS read-only
			STATUS current
			DESCRIPTION
				"The result of the last user command"
			::= { sleEponOnuProfilePortControl 5 }

		
		sleEponOnuProfilePortControlOltIndex OBJECT-TYPE
			SYNTAX INTEGER (1..512)
			MAX-ACCESS read-write
			STATUS current
			DESCRIPTION
				"OLT port Index"
			::= { sleEponOnuProfilePortControl 6 }

		
		sleEponOnuProfilePortControlOnuIndex OBJECT-TYPE
			SYNTAX INTEGER (1..64)
			MAX-ACCESS read-write
			STATUS current
			DESCRIPTION
				"ONU Index"
			::= { sleEponOnuProfilePortControl 7 }

		
		sleEponOnuProfilePortControlPortIndex OBJECT-TYPE
			SYNTAX INTEGER (1..256)
			MAX-ACCESS read-write
			STATUS current
			DESCRIPTION
				"The index of the ONU port"
			::= { sleEponOnuProfilePortControl 8 }

		
		sleEponOnuProfilePortControlAdminStatus OBJECT-TYPE
			SYNTAX INTEGER
				{
				enable(1),
				disable(2)
				}
			MAX-ACCESS read-write
			STATUS current
			DESCRIPTION
				"The desired state of the ONU port"
			DEFVAL { 0 }
			::= { sleEponOnuProfilePortControl 9 }

		
		sleEponOnuProfilePortControlMaxHost OBJECT-TYPE
			SYNTAX INTEGER (1..16)
			MAX-ACCESS read-write
			STATUS current
			DESCRIPTION
				"The max-host number of the ONU port"
			::= { sleEponOnuProfilePortControl 10 }

		
		sleEponOnuProfileUniPortControlMaxHost OBJECT-TYPE
			SYNTAX INTEGER (1..120)
			MAX-ACCESS read-write
			STATUS current
			DESCRIPTION
				"The max-host number of the ONU UNI port."
			::= { sleEponOnuProfilePortControl 11 }

		
		sleEponOnuProfilePortControlIngressRateLimitMode OBJECT-TYPE
			SYNTAX INTEGER
				{
				all(0),
				multiBroadUnicast(1),
				multiBroadcast(2),
				broadcast(3)
				}
			MAX-ACCESS read-write
			STATUS current
			DESCRIPTION
				"It is rate limit mode in Ingress 
				0  Limit all frames
				  1  Limit multicast, broadcast and flooded unicast frame
				  2  Limit multicast, broadcast frame
				  3  Limit broadcast frame only"
			DEFVAL { 0 }
			::= { sleEponOnuProfilePortControl 12 }

		
		sleEponOnuProfilePortControlIngressRateLimit OBJECT-TYPE
			SYNTAX INTEGER (62..1000000)
			MAX-ACCESS read-write
			STATUS current
			DESCRIPTION
				"It is configurable port rate limit in Ingress
				The value of 0 is unlimit
				"
			DEFVAL { 0 }
			::= { sleEponOnuProfilePortControl 13 }

		
		sleEponOnuProfilePortControlEgressRateLimit OBJECT-TYPE
			SYNTAX INTEGER (62..1000000)
			MAX-ACCESS read-write
			STATUS current
			DESCRIPTION
				"It is configurable port rate limit in Egress
				The value of 0 is unlimit
				"
			DEFVAL { 0 }
			::= { sleEponOnuProfilePortControl 14 }

		
		sleEponOnuProfilePortNotification OBJECT IDENTIFIER ::= { sleEponOnuProfilePort 3 }

		
		sleEponOnuProfilePortAdminStatusChanged NOTIFICATION-TYPE
			OBJECTS { sleEponOnuProfilePortControlRequest, sleEponOnuProfilePortControlTimeStamp, sleEponOnuProfilePortControlReqResult, sleEponOnuProfilePortControlOltIndex, sleEponOnuProfilePortControlOnuIndex, 
				sleEponOnuProfilePortControlPortIndex, sleEponOnuProfilePortControlAdminStatus }
			STATUS current
			DESCRIPTION 
				"Description."
			::= { sleEponOnuProfilePortNotification 1 }

		
		sleEponOnuProfilePortMaxHostChanged NOTIFICATION-TYPE
			OBJECTS { sleEponOnuProfilePortControlRequest, sleEponOnuProfilePortControlTimeStamp, sleEponOnuProfilePortControlReqResult, sleEponOnuProfilePortControlOltIndex, sleEponOnuProfilePortControlOnuIndex, 
				sleEponOnuProfilePortControlPortIndex, sleEponOnuProfilePortControlMaxHost }
			STATUS current
			DESCRIPTION 
				"Description."
			::= { sleEponOnuProfilePortNotification 2 }

		
		sleEponOnuProfileUniPortMaxHostChanged NOTIFICATION-TYPE
			OBJECTS { sleEponOnuProfilePortControlRequest, sleEponOnuProfilePortControlTimeStamp, sleEponOnuProfilePortControlReqResult, sleEponOnuProfilePortControlOltIndex, sleEponOnuProfilePortControlOnuIndex, 
				sleEponOnuProfilePortControlPortIndex, sleEponOnuProfileUniPortControlMaxHost }
			STATUS current
			DESCRIPTION 
				"Description."
			::= { sleEponOnuProfilePortNotification 3 }

		
		sleEponOnuProfilePortIngressRateLimitChanged NOTIFICATION-TYPE
			OBJECTS { sleEponOnuProfilePortControlRequest, sleEponOnuProfilePortControlTimeStamp, sleEponOnuProfilePortControlReqResult, sleEponOnuProfilePortControlOltIndex, sleEponOnuProfilePortControlOnuIndex, 
				sleEponOnuProfilePortControlPortIndex, sleEponOnuProfilePortControlIngressRateLimitMode, sleEponOnuProfilePortControlIngressRateLimit }
			STATUS current
			DESCRIPTION 
				"Description."
			::= { sleEponOnuProfilePortNotification 4 }

		
		sleEponOnuProfilePortEgressRateLimitChanged NOTIFICATION-TYPE
			OBJECTS { sleEponOnuProfilePortControlRequest, sleEponOnuProfilePortControlTimeStamp, sleEponOnuProfilePortControlReqResult, sleEponOnuProfilePortControlOltIndex, sleEponOnuProfilePortControlOnuIndex, 
				sleEponOnuProfilePortControlPortIndex, sleEponOnuProfilePortControlEgressRateLimit }
			STATUS current
			DESCRIPTION 
				"Description."
			::= { sleEponOnuProfilePortNotification 5 }

		
		sleEponOnuProfilePorResetOnuPortStatus NOTIFICATION-TYPE
			OBJECTS { sleEponOnuProfilePortControlRequest, sleEponOnuProfilePortControlTimeStamp, sleEponOnuProfilePortControlReqResult, sleEponOnuProfilePortControlOltIndex, sleEponOnuProfilePortControlOnuIndex, 
				sleEponOnuProfilePortControlPortIndex }
			STATUS current
			DESCRIPTION 
				"Description."
			::= { sleEponOnuProfilePortNotification 6 }

		
		sleEponProfile OBJECT IDENTIFIER ::= { sleEpon 5 }

		
		sleEponProfileBase OBJECT IDENTIFIER ::= { sleEponProfile 1 }

		
		sleEponProfileTable OBJECT-TYPE
			SYNTAX SEQUENCE OF SleEponProfileEntry
			MAX-ACCESS not-accessible
			STATUS current
			DESCRIPTION
				"Description."
			::= { sleEponProfileBase 1 }

		
		sleEponProfileEntry OBJECT-TYPE
			SYNTAX SleEponProfileEntry
			MAX-ACCESS not-accessible
			STATUS current
			DESCRIPTION
				"Description."
			INDEX { sleEponProfileIndex }
			::= { sleEponProfileTable 1 }

		
		SleEponProfileEntry ::=
			SEQUENCE { 
				sleEponProfileIndex
					INTEGER,
				sleEponProfileName
					OCTET STRING,
				sleEponProfileDPDownMaxBandwidth
					INTEGER,
				sleEponProfileDPDownMaxBurstSize
					INTEGER,
				sleEponProfileDPP2pMaxBandwidth
					INTEGER,
				sleEponProfileDPP2pMaxBurstSize
					INTEGER,
				sleEponProfileSlaGuaranteedBandwidth
					INTEGER,
				sleEponProfileSlaBestEffortBandwidth
					INTEGER,
				sleEponProfileSlaPlatoClass
					INTEGER,
				sleEponProfileSlaPlatoMinBandwidth1m
					INTEGER,
				sleEponProfileSlaPlatoMinBandwdith64k
					INTEGER,
				sleEponProfileSlaPlatoMaxBandwidth1m
					INTEGER,
				sleEponProfileSlaPlatoMaxBandwidth64k
					INTEGER,
				sleEponProfileSlaPlatoDelayLevel
					INTEGER,
				sleEponProfileExtendMtu
					EnableFlag,
				sleEponProfileIgmpFilter
					EnableFlag,
				sleEponProfileIgmpSnooping
					EnableFlag,
				sleEponProfileSTPenable
					EnableFlag,
				sleEponProfileSubscriberInfoCollection
					EnableFlag,
				sleEponProfileLoopDetectStatus
					EnableFlag,
				sleEponProfileLoopDetectBlockTimer
					INTEGER,
				sleEponProfileLoopDetectSendingpacket
					INTEGER,
				sleEponProfileSipMgPort
					INTEGER,
				sleEponProfileSipProxyServer
					OCTET STRING,
				sleEponProfileSipProxyServerPort
					INTEGER,
				sleEponProfileSipBackupProxyServer
					OCTET STRING,
				sleEponProfileSipBackupProxyServerPort
					INTEGER,
				sleEponProfileSipActiveServer
					OCTET STRING,
				sleEponProfileSipRegisterServer
					OCTET STRING,
				sleEponProfileSipRegisterServerPort
					INTEGER,
				sleEponProfileSipBackupRegisterServer
					OCTET STRING,
				sleEponProfileSipBackupRegisterServerPort
					INTEGER,
				sleEponProfileSipOutBindServer
					OCTET STRING,
				sleEponProfileSipOutBindServerPort
					INTEGER,
				sleEponProfileSipRegisterInterval
					INTEGER,
				sleEponProfileSipHeartBeatSwitch
					EnableFlag,
				sleEponProfileSipHeartBeatCycle
					INTEGER,
				sleEponProfileSipHeartBeatCount
					INTEGER,
				sleEponProfileSipDNS1Server
					OCTET STRING,
				sleEponProfileSipDNS2Server
					OCTET STRING,
				sleEponProfileVoiceT38enable
					EnableFlag,
				sleEponProfileModemControl
					EnableFlag,
				sleEponProfileDHCPEnable
					Integer32,
				sleEponProfileMacLearnStatus
					OCTET STRING,
				sleEponProfileMaxHostEnable
					Integer32,
				sleEponProfileDbaProfile
					OCTET STRING,
				sleEponProfileOnuListOltID
					Integer32,
				sleEponProfileOnuListOnuID
					Integer32,
				sleEponProfileStormControlEnable
					EnableFlag,
				sleEponProfileStormControlBroadcast
					Integer32,
				sleEponProfileStormControlMulticast
					Integer32,
				sleEponProfileStormControlUnknownUnicast
					Integer32
			 }

		sleEponProfileIndex OBJECT-TYPE
			SYNTAX INTEGER (1..32)
			MAX-ACCESS read-only
			STATUS current
			DESCRIPTION
				"Profile Index"
			::= { sleEponProfileEntry 1 }

		
		sleEponProfileName OBJECT-TYPE
			SYNTAX OCTET STRING (SIZE (1..64))
			MAX-ACCESS read-only
			STATUS current
			DESCRIPTION
				"Profile name"
			::= { sleEponProfileEntry 2 }

		
		sleEponProfileDPDownMaxBandwidth OBJECT-TYPE
			SYNTAX INTEGER (0 | 1..1000000)
			UNITS "kbps"
			MAX-ACCESS read-only
			STATUS current
			DESCRIPTION
				"Download policy Down Max Bandwidth 
				
				"
			::= { sleEponProfileEntry 3 }

		
		sleEponProfileDPDownMaxBurstSize OBJECT-TYPE
			SYNTAX INTEGER (0 | 128..8388479)
			UNITS "byte"
			MAX-ACCESS read-only
			STATUS current
			DESCRIPTION
				"Download policy Down Max Burst Size 
				
				"
			::= { sleEponProfileEntry 4 }

		
		sleEponProfileDPP2pMaxBandwidth OBJECT-TYPE
			SYNTAX INTEGER (0 | 1..1000000)
			UNITS "kbps"
			MAX-ACCESS read-only
			STATUS current
			DESCRIPTION
				"Download policy P2P Max Bandwidth "
			::= { sleEponProfileEntry 5 }

		
		sleEponProfileDPP2pMaxBurstSize OBJECT-TYPE
			SYNTAX INTEGER (0 | 128..8388479)
			UNITS "byte"
			MAX-ACCESS read-only
			STATUS current
			DESCRIPTION
				"Download policy P2P Max Burst Size "
			::= { sleEponProfileEntry 6 }

		
		sleEponProfileSlaGuaranteedBandwidth OBJECT-TYPE
			SYNTAX INTEGER (43..65535)
			UNITS "TQ"
			MAX-ACCESS read-only
			STATUS current
			DESCRIPTION
				"SLA-internal Guranteed Bandwidth"
			DEFVAL { 85 }
			::= { sleEponProfileEntry 7 }

		
		sleEponProfileSlaBestEffortBandwidth OBJECT-TYPE
			SYNTAX INTEGER (43..65535)
			UNITS "TQ"
			MAX-ACCESS read-only
			STATUS current
			DESCRIPTION
				"SLA-internal Best effort Bandwidth"
			DEFVAL { 85 }
			::= { sleEponProfileEntry 8 }

		
		sleEponProfileSlaPlatoClass OBJECT-TYPE
			SYNTAX INTEGER (0..7)
			MAX-ACCESS read-only
			STATUS current
			DESCRIPTION
				"SLA-Plato Class"
			DEFVAL { 1 }
			::= { sleEponProfileEntry 9 }

		
		sleEponProfileSlaPlatoMinBandwidth1m OBJECT-TYPE
			SYNTAX INTEGER (1..1000)
			UNITS "Mbps"
			MAX-ACCESS read-only
			STATUS current
			DESCRIPTION
				"SLA-Plato Minimum Bandwidth_1m"
			DEFVAL { '1'b }
			::= { sleEponProfileEntry 10 }

		
		sleEponProfileSlaPlatoMinBandwdith64k OBJECT-TYPE
			SYNTAX INTEGER (0..1024)
			UNITS "64Kbps"
			MAX-ACCESS read-only
			STATUS current
			DESCRIPTION
				"SLA-plato Minimum Bandwidth_64k"
			DEFVAL { '0'b }
			::= { sleEponProfileEntry 11 }

		
		sleEponProfileSlaPlatoMaxBandwidth1m OBJECT-TYPE
			SYNTAX INTEGER (1..1000)
			UNITS "Mbps"
			MAX-ACCESS read-only
			STATUS current
			DESCRIPTION
				"SLA-plato Max bandwidth_1m"
			DEFVAL { 2 }
			::= { sleEponProfileEntry 12 }

		
		sleEponProfileSlaPlatoMaxBandwidth64k OBJECT-TYPE
			SYNTAX INTEGER (0..1024)
			UNITS "64Kbps"
			MAX-ACCESS read-only
			STATUS current
			DESCRIPTION
				"SLA-plato Max bandwidth_64k"
			DEFVAL { 0 }
			::= { sleEponProfileEntry 13 }

		
		sleEponProfileSlaPlatoDelayLevel OBJECT-TYPE
			SYNTAX INTEGER (1..2)
			MAX-ACCESS read-only
			STATUS current
			DESCRIPTION
				"SLA-plato Delay  level"
			DEFVAL { 1 }
			::= { sleEponProfileEntry 14 }

		
		sleEponProfileExtendMtu OBJECT-TYPE
			SYNTAX EnableFlag
			MAX-ACCESS read-only
			STATUS current
			DESCRIPTION
				"Description."
			::= { sleEponProfileEntry 15 }

		
		sleEponProfileIgmpFilter OBJECT-TYPE
			SYNTAX EnableFlag
			MAX-ACCESS read-only
			STATUS current
			DESCRIPTION
				"Description."
			::= { sleEponProfileEntry 16 }

		
		sleEponProfileIgmpSnooping OBJECT-TYPE
			SYNTAX EnableFlag
			MAX-ACCESS read-only
			STATUS current
			DESCRIPTION
				"Description."
			::= { sleEponProfileEntry 17 }

		
		sleEponProfileSTPenable OBJECT-TYPE
			SYNTAX EnableFlag
			MAX-ACCESS read-only
			STATUS current
			DESCRIPTION
				"Description."
			::= { sleEponProfileEntry 18 }

		
		sleEponProfileSubscriberInfoCollection OBJECT-TYPE
			SYNTAX EnableFlag
			MAX-ACCESS read-only
			STATUS current
			DESCRIPTION
				"Description."
			::= { sleEponProfileEntry 19 }

		
		sleEponProfileLoopDetectStatus OBJECT-TYPE
			SYNTAX EnableFlag
			MAX-ACCESS read-only
			STATUS current
			DESCRIPTION
				"Description."
			::= { sleEponProfileEntry 20 }

		
		sleEponProfileLoopDetectBlockTimer OBJECT-TYPE
			SYNTAX INTEGER (0 | 10..86400)
			MAX-ACCESS read-only
			STATUS current
			DESCRIPTION
				"Description."
			::= { sleEponProfileEntry 21 }

		
		sleEponProfileLoopDetectSendingpacket OBJECT-TYPE
			SYNTAX INTEGER (0 | 1..60)
			MAX-ACCESS read-only
			STATUS current
			DESCRIPTION
				"Description."
			::= { sleEponProfileEntry 22 }

		
		sleEponProfileSipMgPort OBJECT-TYPE
			SYNTAX INTEGER
			MAX-ACCESS read-only
			STATUS current
			DESCRIPTION
				"Description."
			::= { sleEponProfileEntry 23 }

		
		sleEponProfileSipProxyServer OBJECT-TYPE
			SYNTAX OCTET STRING (SIZE (0..64))
			MAX-ACCESS read-only
			STATUS current
			DESCRIPTION
				"Description."
			::= { sleEponProfileEntry 24 }

		
		sleEponProfileSipProxyServerPort OBJECT-TYPE
			SYNTAX INTEGER
			MAX-ACCESS read-only
			STATUS current
			DESCRIPTION
				"Description."
			::= { sleEponProfileEntry 25 }

		
		sleEponProfileSipBackupProxyServer OBJECT-TYPE
			SYNTAX OCTET STRING (SIZE (0..64))
			MAX-ACCESS read-only
			STATUS current
			DESCRIPTION
				"Description."
			::= { sleEponProfileEntry 26 }

		
		sleEponProfileSipBackupProxyServerPort OBJECT-TYPE
			SYNTAX INTEGER
			MAX-ACCESS read-only
			STATUS current
			DESCRIPTION
				"Description."
			::= { sleEponProfileEntry 27 }

		
		sleEponProfileSipActiveServer OBJECT-TYPE
			SYNTAX OCTET STRING (SIZE (0..64))
			MAX-ACCESS read-only
			STATUS current
			DESCRIPTION
				"Description."
			::= { sleEponProfileEntry 28 }

		
		sleEponProfileSipRegisterServer OBJECT-TYPE
			SYNTAX OCTET STRING (SIZE (0..64))
			MAX-ACCESS read-only
			STATUS current
			DESCRIPTION
				"Description."
			::= { sleEponProfileEntry 29 }

		
		sleEponProfileSipRegisterServerPort OBJECT-TYPE
			SYNTAX INTEGER
			MAX-ACCESS read-only
			STATUS current
			DESCRIPTION
				"Description."
			::= { sleEponProfileEntry 30 }

		
		sleEponProfileSipBackupRegisterServer OBJECT-TYPE
			SYNTAX OCTET STRING (SIZE (0..64))
			MAX-ACCESS read-only
			STATUS current
			DESCRIPTION
				"Description."
			::= { sleEponProfileEntry 31 }

		
		sleEponProfileSipBackupRegisterServerPort OBJECT-TYPE
			SYNTAX INTEGER
			MAX-ACCESS read-only
			STATUS current
			DESCRIPTION
				"Description."
			::= { sleEponProfileEntry 32 }

		
		sleEponProfileSipOutBindServer OBJECT-TYPE
			SYNTAX OCTET STRING (SIZE (0..64))
			MAX-ACCESS read-only
			STATUS current
			DESCRIPTION
				"Description."
			::= { sleEponProfileEntry 33 }

		
		sleEponProfileSipOutBindServerPort OBJECT-TYPE
			SYNTAX INTEGER
			MAX-ACCESS read-only
			STATUS current
			DESCRIPTION
				"Description."
			::= { sleEponProfileEntry 34 }

		
		sleEponProfileSipRegisterInterval OBJECT-TYPE
			SYNTAX INTEGER
			MAX-ACCESS read-only
			STATUS current
			DESCRIPTION
				"Description."
			::= { sleEponProfileEntry 35 }

		
		sleEponProfileSipHeartBeatSwitch OBJECT-TYPE
			SYNTAX EnableFlag
			MAX-ACCESS read-only
			STATUS current
			DESCRIPTION
				"Description."
			::= { sleEponProfileEntry 36 }

		
		sleEponProfileSipHeartBeatCycle OBJECT-TYPE
			SYNTAX INTEGER
			MAX-ACCESS read-only
			STATUS current
			DESCRIPTION
				"Description."
			::= { sleEponProfileEntry 37 }

		
		sleEponProfileSipHeartBeatCount OBJECT-TYPE
			SYNTAX INTEGER
			MAX-ACCESS read-only
			STATUS current
			DESCRIPTION
				"Description."
			::= { sleEponProfileEntry 38 }

		
		sleEponProfileSipDNS1Server OBJECT-TYPE
			SYNTAX OCTET STRING (SIZE (0..64))
			MAX-ACCESS read-only
			STATUS current
			DESCRIPTION
				"Description."
			::= { sleEponProfileEntry 39 }

		
		sleEponProfileSipDNS2Server OBJECT-TYPE
			SYNTAX OCTET STRING (SIZE (0..64))
			MAX-ACCESS read-only
			STATUS current
			DESCRIPTION
				"Description."
			::= { sleEponProfileEntry 40 }

		
		sleEponProfileVoiceT38enable OBJECT-TYPE
			SYNTAX EnableFlag
			MAX-ACCESS read-only
			STATUS current
			DESCRIPTION
				"Description."
			::= { sleEponProfileEntry 41 }

		
		sleEponProfileModemControl OBJECT-TYPE
			SYNTAX EnableFlag
			MAX-ACCESS read-only
			STATUS current
			DESCRIPTION
				"Description."
			::= { sleEponProfileEntry 42 }

		
		sleEponProfileDHCPEnable OBJECT-TYPE
			SYNTAX Integer32
			MAX-ACCESS read-only
			STATUS current
			DESCRIPTION
				"dhcp enable"
			::= { sleEponProfileEntry 43 }

		
		sleEponProfileMacLearnStatus OBJECT-TYPE
			SYNTAX OCTET STRING
			MAX-ACCESS read-only
			STATUS current
			DESCRIPTION
				"mac learn status : enable or disable"
			::= { sleEponProfileEntry 44 }

		
		sleEponProfileMaxHostEnable OBJECT-TYPE
			SYNTAX Integer32
			MAX-ACCESS read-only
			STATUS current
			DESCRIPTION
				"Description."
			::= { sleEponProfileEntry 45 }

		
		sleEponProfileDbaProfile OBJECT-TYPE
			SYNTAX OCTET STRING
			MAX-ACCESS read-only
			STATUS current
			DESCRIPTION
				"Description."
			::= { sleEponProfileEntry 46 }

		
		sleEponProfileOnuListOltID OBJECT-TYPE
			SYNTAX Integer32
			MAX-ACCESS read-write
			STATUS current
			DESCRIPTION
				"Description."
			::= { sleEponProfileEntry 47 }

		
		sleEponProfileOnuListOnuID OBJECT-TYPE
			SYNTAX Integer32
			MAX-ACCESS read-write
			STATUS current
			DESCRIPTION
				"Description."
			::= { sleEponProfileEntry 48 }

		
		sleEponProfileStormControlEnable OBJECT-TYPE
			SYNTAX EnableFlag
			MAX-ACCESS read-only
			STATUS current
			DESCRIPTION
				"Onu strom status."
			::= { sleEponProfileEntry 49 }

		
		sleEponProfileStormControlBroadcast OBJECT-TYPE
			SYNTAX Integer32 (8..65535)
			MAX-ACCESS read-only
			STATUS current
			DESCRIPTION
				"Broadcast threshold (default 121 kbps)."
			::= { sleEponProfileEntry 50 }

		
		sleEponProfileStormControlMulticast OBJECT-TYPE
			SYNTAX Integer32 (8..65535)
			MAX-ACCESS read-only
			STATUS current
			DESCRIPTION
				"Multicast threshold (default 23 kbps)."
			::= { sleEponProfileEntry 51 }

		
		sleEponProfileStormControlUnknownUnicast OBJECT-TYPE
			SYNTAX Integer32 (8..65535)
			MAX-ACCESS read-only
			STATUS current
			DESCRIPTION
				"Unknown-Unicast threshold (default 23 kbps).."
			::= { sleEponProfileEntry 52 }

		
		sleEponProfileControl OBJECT IDENTIFIER ::= { sleEponProfileBase 2 }

		
		sleEponProfileControlRequest OBJECT-TYPE
			SYNTAX INTEGER
				{
				createProfile(1),
				modifyProfile(2),
				destroyProfile(3),
				modifyProfileMtu(4),
				modifyProfileIgmp(5),
				modifyProfileSTP(6),
				createDefaultProfile(7),
				modifyProfileSubscriber(8),
				modifyProfileLoopDetect(9),
				modifyProfileSipConfig(10),
				modifyProfileModemConfig(11),
				modifyProfileDHCP(12),
				modifyProfileMacLearn(13),
				destroyProfileAll(14),
				modifiyProfileSTPSpecified(15),
				modifyProfileLoopDetectSpecified(16),
				modifiyProfileDHCPSpecified(17),
				modifiyProfileMaxHost(18),
				modifiyProfileMaxHostSpecified(19),
				creatDbaProfile(20),
				destroyDbaProfile(21),
				creatDbaProfileSpecified(22),
				destroyDbaProfileSpecified(23),
				modifiyProfileStormControl(24),
				modifiyProfileStormControlDefault(25)
				}
			MAX-ACCESS read-write
			STATUS current
			DESCRIPTION
				"The request of a user command"
			::= { sleEponProfileControl 1 }

		
		sleEponProfileControlStatus OBJECT-TYPE
			SYNTAX SleControlStatusType
			MAX-ACCESS read-only
			STATUS current
			DESCRIPTION
				"The status of user command"
			::= { sleEponProfileControl 2 }

		
		sleEponProfileControlTimer OBJECT-TYPE
			SYNTAX Gauge32
			MAX-ACCESS read-write
			STATUS current
			DESCRIPTION
				"The maximum time for the manager for a long running user command"
			::= { sleEponProfileControl 3 }

		
		sleEponProfileControlTimeStamp OBJECT-TYPE
			SYNTAX TimeTicks
			MAX-ACCESS read-only
			STATUS current
			DESCRIPTION
				"The time stamp of the last command(end of command)"
			::= { sleEponProfileControl 4 }

		
		sleEponProfileControlReqResult OBJECT-TYPE
			SYNTAX SleControlRequestResultType
			MAX-ACCESS read-only
			STATUS current
			DESCRIPTION
				"The result of the last user command"
			::= { sleEponProfileControl 5 }

		
		sleEponProfileControlIndex OBJECT-TYPE
			SYNTAX INTEGER (1..32)
			MAX-ACCESS read-write
			STATUS current
			DESCRIPTION
				"Profile index"
			::= { sleEponProfileControl 6 }

		
		sleEponProfileControlName OBJECT-TYPE
			SYNTAX OCTET STRING (SIZE (1..64))
			MAX-ACCESS read-write
			STATUS current
			DESCRIPTION
				"Profile name"
			::= { sleEponProfileControl 7 }

		
		sleEponProfileControlDPDownMaxBandwidth OBJECT-TYPE
			SYNTAX INTEGER (0 | 1..1000000)
			UNITS "kbps"
			MAX-ACCESS read-write
			STATUS current
			DESCRIPTION
				"Download policy Down Max Bandwidth "
			::= { sleEponProfileControl 8 }

		
		sleEponProfileControlDPDownMaxBurstSize OBJECT-TYPE
			SYNTAX INTEGER (0 | 128..8388479)
			UNITS "byte"
			MAX-ACCESS read-write
			STATUS current
			DESCRIPTION
				"Download policy Down Max Burst Size"
			::= { sleEponProfileControl 9 }

		
		sleEponProfileControlDPP2pMaxBandwidth OBJECT-TYPE
			SYNTAX INTEGER (0 | 1..1000000)
			UNITS "kbps"
			MAX-ACCESS read-write
			STATUS current
			DESCRIPTION
				"Download policy P2P Max Bandwidth"
			::= { sleEponProfileControl 10 }

		
		sleEponProfileControlDPP2pMaxBurstSize OBJECT-TYPE
			SYNTAX INTEGER (0 | 128..8388479)
			UNITS "byte"
			MAX-ACCESS read-write
			STATUS current
			DESCRIPTION
				"Download policy P2P Max Burst Size "
			::= { sleEponProfileControl 11 }

		
		sleEponProfileControlSlaGuaranteedBandwidth OBJECT-TYPE
			SYNTAX INTEGER (43..65535)
			UNITS "TQ"
			MAX-ACCESS read-write
			STATUS current
			DESCRIPTION
				"SLA-internal Guranteed Bandwidth"
			DEFVAL { 85 }
			::= { sleEponProfileControl 12 }

		
		sleEponProfileControlSlaBestEffortBandwidth OBJECT-TYPE
			SYNTAX INTEGER (43..65535)
			UNITS "TQ"
			MAX-ACCESS read-write
			STATUS current
			DESCRIPTION
				"SLA-internal Best effort Bandwidth"
			DEFVAL { 85 }
			::= { sleEponProfileControl 13 }

		
		sleEponProfileControlSlaPlatoClass OBJECT-TYPE
			SYNTAX INTEGER (0..7)
			MAX-ACCESS read-write
			STATUS current
			DESCRIPTION
				"SLA-Plato Class"
			::= { sleEponProfileControl 14 }

		
		sleEponProfileControlSlaPlatoGuaranteedBandwidth1m OBJECT-TYPE
			SYNTAX INTEGER (1..1000)
			UNITS "Mbps"
			MAX-ACCESS read-write
			STATUS current
			DESCRIPTION
				"SLA-Plato Minimum Bandwidth_1m"
			DEFVAL { 1 }
			::= { sleEponProfileControl 15 }

		
		sleEponProfileControlSlaPlatoGuaranteedBandwdith64k OBJECT-TYPE
			SYNTAX INTEGER (0..1024)
			UNITS "64Kbps"
			MAX-ACCESS read-write
			STATUS current
			DESCRIPTION
				"SLA-plato Minimum Bandwidth_64k"
			DEFVAL { 0 }
			::= { sleEponProfileControl 16 }

		
		sleEponProfileControlSlaPlatoBestEffortBandwidth1m OBJECT-TYPE
			SYNTAX INTEGER (1..1000)
			UNITS "Mbps"
			MAX-ACCESS read-write
			STATUS current
			DESCRIPTION
				"SLA-plato Max bandwidth_1m"
			DEFVAL { 2 }
			::= { sleEponProfileControl 17 }

		
		sleEponProfileControlSlaPlatoBestEffortBandwidth64k OBJECT-TYPE
			SYNTAX INTEGER (0..1024)
			UNITS "64Kbps"
			MAX-ACCESS read-write
			STATUS current
			DESCRIPTION
				"SLA-plato Max bandwidth_64k"
			DEFVAL { 0 }
			::= { sleEponProfileControl 18 }

		
		sleEponProfileControlSlaPlatoDelayLevel OBJECT-TYPE
			SYNTAX INTEGER (1..2)
			MAX-ACCESS read-write
			STATUS current
			DESCRIPTION
				"SLA-plato Delay  level"
			DEFVAL { 1 }
			::= { sleEponProfileControl 19 }

		
		sleEponProfileControlExtendMtu OBJECT-TYPE
			SYNTAX EnableFlag
			MAX-ACCESS read-write
			STATUS current
			DESCRIPTION
				"Description."
			::= { sleEponProfileControl 20 }

		
		sleEponProfileControlIgmpFilter OBJECT-TYPE
			SYNTAX EnableFlag
			MAX-ACCESS read-write
			STATUS current
			DESCRIPTION
				"Description."
			::= { sleEponProfileControl 21 }

		
		sleEponProfileControlSnooping OBJECT-TYPE
			SYNTAX EnableFlag
			MAX-ACCESS read-write
			STATUS current
			DESCRIPTION
				"Description."
			::= { sleEponProfileControl 22 }

		
		sleEponProfileControlSTPenable OBJECT-TYPE
			SYNTAX EnableFlag
			MAX-ACCESS read-write
			STATUS current
			DESCRIPTION
				"Description."
			::= { sleEponProfileControl 23 }

		
		sleEponProfileControlSubscriberInfoCollection OBJECT-TYPE
			SYNTAX EnableFlag
			MAX-ACCESS read-write
			STATUS current
			DESCRIPTION
				"Description."
			::= { sleEponProfileControl 24 }

		
		sleEponProfileControlLoopDetectStatus OBJECT-TYPE
			SYNTAX EnableFlag
			MAX-ACCESS read-write
			STATUS current
			DESCRIPTION
				"Description."
			::= { sleEponProfileControl 25 }

		
		sleEponProfileControlLoopDetectBlockTimer OBJECT-TYPE
			SYNTAX INTEGER (0 | 10..86400)
			MAX-ACCESS read-write
			STATUS current
			DESCRIPTION
				"Description."
			::= { sleEponProfileControl 26 }

		
		sleEponProfileControlLoopDetectSendingpacket OBJECT-TYPE
			SYNTAX INTEGER (0 | 1..60)
			MAX-ACCESS read-write
			STATUS current
			DESCRIPTION
				"Description."
			::= { sleEponProfileControl 27 }

		
		sleEponProfileControlSipMgPort OBJECT-TYPE
			SYNTAX INTEGER
			MAX-ACCESS read-write
			STATUS current
			DESCRIPTION
				"Description."
			::= { sleEponProfileControl 28 }

		
		sleEponProfileControlSipProxyServer OBJECT-TYPE
			SYNTAX OCTET STRING (SIZE (0..64))
			MAX-ACCESS read-write
			STATUS current
			DESCRIPTION
				"Description."
			::= { sleEponProfileControl 29 }

		
		sleEponProfileControlSipProxyServerPort OBJECT-TYPE
			SYNTAX INTEGER
			MAX-ACCESS read-write
			STATUS current
			DESCRIPTION
				"Description."
			::= { sleEponProfileControl 30 }

		
		sleEponProfileControlSipBackupProxyServer OBJECT-TYPE
			SYNTAX OCTET STRING (SIZE (0..64))
			MAX-ACCESS read-write
			STATUS current
			DESCRIPTION
				"Description."
			::= { sleEponProfileControl 31 }

		
		sleEponProfileControlSipBackupProxyServerPort OBJECT-TYPE
			SYNTAX INTEGER
			MAX-ACCESS read-write
			STATUS current
			DESCRIPTION
				"Description."
			::= { sleEponProfileControl 32 }

		
		sleEponProfileControlSipActiveServer OBJECT-TYPE
			SYNTAX OCTET STRING (SIZE (0..64))
			MAX-ACCESS read-write
			STATUS current
			DESCRIPTION
				"Description."
			::= { sleEponProfileControl 33 }

		
		sleEponProfileControlSipRegisterServer OBJECT-TYPE
			SYNTAX OCTET STRING (SIZE (0..64))
			MAX-ACCESS read-write
			STATUS current
			DESCRIPTION
				"Description."
			::= { sleEponProfileControl 34 }

		
		sleEponProfileControlSipRegisterServerPort OBJECT-TYPE
			SYNTAX INTEGER
			MAX-ACCESS read-write
			STATUS current
			DESCRIPTION
				"Description."
			::= { sleEponProfileControl 35 }

		
		sleEponProfileControlSipBackupRegisterServer OBJECT-TYPE
			SYNTAX OCTET STRING (SIZE (0..64))
			MAX-ACCESS read-write
			STATUS current
			DESCRIPTION
				"Description."
			::= { sleEponProfileControl 36 }

		
		sleEponProfileControlSipBackupRegisterServerPort OBJECT-TYPE
			SYNTAX INTEGER
			MAX-ACCESS read-write
			STATUS current
			DESCRIPTION
				"Description."
			::= { sleEponProfileControl 37 }

		
		sleEponProfileControlSipOutBindServer OBJECT-TYPE
			SYNTAX OCTET STRING (SIZE (0..64))
			MAX-ACCESS read-write
			STATUS current
			DESCRIPTION
				"Description."
			::= { sleEponProfileControl 38 }

		
		sleEponProfileControlSipOutBindServerPort OBJECT-TYPE
			SYNTAX INTEGER
			MAX-ACCESS read-write
			STATUS current
			DESCRIPTION
				"Description."
			::= { sleEponProfileControl 39 }

		
		sleEponProfileControlSipRegisterInterval OBJECT-TYPE
			SYNTAX INTEGER
			MAX-ACCESS read-write
			STATUS current
			DESCRIPTION
				"Description."
			::= { sleEponProfileControl 40 }

		
		sleEponProfileControlSipHeartBeatSwitch OBJECT-TYPE
			SYNTAX EnableFlag
			MAX-ACCESS read-write
			STATUS current
			DESCRIPTION
				"Description."
			::= { sleEponProfileControl 41 }

		
		sleEponProfileControlSipHeartBeatCycle OBJECT-TYPE
			SYNTAX INTEGER
			MAX-ACCESS read-write
			STATUS current
			DESCRIPTION
				"Description."
			::= { sleEponProfileControl 42 }

		
		sleEponProfileControlSipHeartBeatCount OBJECT-TYPE
			SYNTAX INTEGER
			MAX-ACCESS read-write
			STATUS current
			DESCRIPTION
				"Description."
			::= { sleEponProfileControl 43 }

		
		sleEponProfileControlSipDNS1Server OBJECT-TYPE
			SYNTAX OCTET STRING (SIZE (0..64))
			MAX-ACCESS read-write
			STATUS current
			DESCRIPTION
				"Description."
			::= { sleEponProfileControl 44 }

		
		sleEponProfileControlSipDNS2Server OBJECT-TYPE
			SYNTAX OCTET STRING (SIZE (0..64))
			MAX-ACCESS read-write
			STATUS current
			DESCRIPTION
				"Description."
			::= { sleEponProfileControl 45 }

		
		sleEponProfileControlVoiceT38enable OBJECT-TYPE
			SYNTAX EnableFlag
			MAX-ACCESS read-write
			STATUS current
			DESCRIPTION
				"Description."
			::= { sleEponProfileControl 46 }

		
		sleEponProfileControlModemControl OBJECT-TYPE
			SYNTAX EnableFlag
			MAX-ACCESS read-write
			STATUS current
			DESCRIPTION
				"Description."
			::= { sleEponProfileControl 47 }

		
		sleEponProfileControlDHCPEnable OBJECT-TYPE
			SYNTAX Integer32
			MAX-ACCESS read-write
			STATUS current
			DESCRIPTION
				"dhcp enable"
			::= { sleEponProfileControl 48 }

		
		sleEponProfileControlMacLearnStatus OBJECT-TYPE
			SYNTAX EnableFlag
			MAX-ACCESS read-write
			STATUS current
			DESCRIPTION
				"mac learn : enbale 1 , diable 2"
			DEFVAL { enable }
			::= { sleEponProfileControl 49 }

		
		sleEponProfileControlMaxHostEnable OBJECT-TYPE
			SYNTAX Integer32
			MAX-ACCESS read-write
			STATUS current
			DESCRIPTION
				"Description."
			::= { sleEponProfileControl 50 }

		
		sleEponProfileControlDbaName OBJECT-TYPE
			SYNTAX OCTET STRING
			MAX-ACCESS read-write
			STATUS current
			DESCRIPTION
				"Description."
			::= { sleEponProfileControl 51 }

		
		sleEponProfileControlStormControlEnable OBJECT-TYPE
			SYNTAX EnableFlag
			MAX-ACCESS read-write
			STATUS current
			DESCRIPTION
				"Onu strom status."
			::= { sleEponProfileControl 52 }

		
		sleEponProfileControlStormControlBroadcast OBJECT-TYPE
			SYNTAX Integer32 (8..65535)
			MAX-ACCESS read-write
			STATUS current
			DESCRIPTION
				"Broadcast threshold (default 121 kbps)."
			::= { sleEponProfileControl 53 }

		
		sleEponProfileControlStormControlMulticast OBJECT-TYPE
			SYNTAX Integer32 (8..65535)
			MAX-ACCESS read-write
			STATUS current
			DESCRIPTION
				"Multicast threshold (default 23 kbps)."
			::= { sleEponProfileControl 54 }

		
		sleEponProfileControlStormControlUnknownUnicast OBJECT-TYPE
			SYNTAX Integer32 (8..65535)
			MAX-ACCESS read-write
			STATUS current
			DESCRIPTION
				"Unknown-Unicast threshold (default 23 kbps)."
			::= { sleEponProfileControl 55 }

		
		sleEponProfileNotification OBJECT IDENTIFIER ::= { sleEponProfileBase 3 }

		
		sleEponProfileCreated NOTIFICATION-TYPE
			OBJECTS { sleEponProfileControlRequest, sleEponProfileControlTimeStamp, sleEponProfileControlReqResult, sleEponProfileControlIndex, sleEponProfileControlName
				 }
			STATUS current
			DESCRIPTION 
				"Description."
			::= { sleEponProfileNotification 1 }

		
		sleEponProfileModified NOTIFICATION-TYPE
			OBJECTS { sleEponProfileControlRequest, sleEponProfileControlTimeStamp, sleEponProfileControlReqResult, sleEponProfileControlIndex, sleEponProfileControlName
				 }
			STATUS current
			DESCRIPTION 
				"Description."
			::= { sleEponProfileNotification 2 }

		
		sleEponProfileDestroyed NOTIFICATION-TYPE
			OBJECTS { sleEponProfileControlRequest, sleEponProfileControlTimeStamp, sleEponProfileControlReqResult, sleEponProfileControlIndex, sleEponProfileControlName
				 }
			STATUS current
			DESCRIPTION 
				"Description."
			::= { sleEponProfileNotification 3 }

		
		sleEponProfileExtendMtuChanged NOTIFICATION-TYPE
			OBJECTS { sleEponProfileControlRequest, sleEponProfileControlTimeStamp, sleEponProfileControlReqResult, sleEponProfileControlIndex, sleEponProfileControlName, 
				sleEponProfileControlExtendMtu }
			STATUS current
			DESCRIPTION 
				"Description."
			::= { sleEponProfileNotification 4 }

		
		sleEponProfileIgmpChanged NOTIFICATION-TYPE
			OBJECTS { sleEponProfileControlRequest, sleEponProfileControlTimeStamp, sleEponProfileControlReqResult, sleEponProfileControlIndex, sleEponProfileControlName, 
				sleEponProfileControlIgmpFilter, sleEponProfileControlSnooping }
			STATUS current
			DESCRIPTION 
				"Description."
			::= { sleEponProfileNotification 5 }

		
		sleEponProfileSTPChanged NOTIFICATION-TYPE
			OBJECTS { sleEponProfileControlRequest, sleEponProfileControlTimeStamp, sleEponProfileControlReqResult, sleEponProfileControlIndex, sleEponProfileControlName, 
				sleEponProfileControlSTPenable }
			STATUS current
			DESCRIPTION 
				"Description."
			::= { sleEponProfileNotification 6 }

		
		sleEponProfileDefaultProfileCreated NOTIFICATION-TYPE
			OBJECTS { sleEponProfileQueueControlRequest, sleEponProfileQueueControlTimeStamp, sleEponProfileQueueControlReqResult }
			STATUS current
			DESCRIPTION 
				"Description."
			::= { sleEponProfileNotification 7 }

		
		sleEponProfileSubscriberChanged NOTIFICATION-TYPE
			OBJECTS { sleEponProfileControlRequest, sleEponProfileControlTimeStamp, sleEponProfileControlReqResult, sleEponProfileControlIndex, sleEponProfileControlName, 
				sleEponProfileControlSubscriberInfoCollection }
			STATUS current
			DESCRIPTION 
				"Description."
			::= { sleEponProfileNotification 8 }

		
		sleEponProfileLoopDetectChanged NOTIFICATION-TYPE
			OBJECTS { sleEponProfileControlRequest, sleEponProfileControlTimeStamp, sleEponProfileControlReqResult, sleEponProfileControlIndex, sleEponProfileControlName, 
				sleEponProfileControlLoopDetectStatus, sleEponProfileControlLoopDetectBlockTimer, sleEponProfileControlLoopDetectSendingpacket }
			STATUS current
			DESCRIPTION 
				"Description."
			::= { sleEponProfileNotification 9 }

		
		sleEponProfileSipConfigChanged NOTIFICATION-TYPE
			OBJECTS { sleEponProfileControlRequest, sleEponProfileControlTimeStamp, sleEponProfileControlReqResult, sleEponProfileControlIndex, sleEponProfileControlName, 
				sleEponProfileControlSipMgPort, sleEponProfileControlSipProxyServer, sleEponProfileControlSipProxyServerPort, sleEponProfileControlSipBackupProxyServer, sleEponProfileControlSipBackupProxyServerPort, 
				sleEponProfileControlSipActiveServer, sleEponProfileControlSipRegisterServer, sleEponProfileControlSipRegisterServerPort, sleEponProfileControlSipBackupRegisterServer, sleEponProfileControlSipBackupRegisterServerPort, 
				sleEponProfileControlSipOutBindServer, sleEponProfileControlSipOutBindServerPort, sleEponProfileControlSipRegisterInterval, sleEponProfileControlSipHeartBeatSwitch, sleEponProfileControlSipHeartBeatCycle, 
				sleEponProfileControlSipHeartBeatCount, sleEponProfileControlSipDNS1Server, sleEponProfileControlSipDNS2Server }
			STATUS current
			DESCRIPTION 
				"Description."
			::= { sleEponProfileNotification 10 }

		
		sleEponProfileModemConfigChanged NOTIFICATION-TYPE
			OBJECTS { sleEponProfileControlRequest, sleEponProfileControlTimeStamp, sleEponProfileControlReqResult, sleEponProfileControlIndex, sleEponProfileControlName, 
				sleEponProfileControlVoiceT38enable, sleEponProfileControlModemControl }
			STATUS current
			DESCRIPTION 
				"Description."
			::= { sleEponProfileNotification 11 }

		
		sleEponProfileDHCPChanged NOTIFICATION-TYPE
			STATUS current
			DESCRIPTION 
				"Description."
			::= { sleEponProfileNotification 12 }

		
		sleEponProfileModemMacLearnChanged NOTIFICATION-TYPE
			OBJECTS { sleEponProfileControlRequest, sleEponProfileControlTimeStamp, sleEponProfileControlReqResult, sleEponProfileControlMacLearnStatus }
			STATUS current
			DESCRIPTION 
				"mac learn status changed trap"
			::= { sleEponProfileNotification 13 }

		
		sleEponProfileMaxHostChanged NOTIFICATION-TYPE
			OBJECTS { sleEponProfileControlIndex, sleEponProfileControlName, sleEponProfileControlMaxHostEnable, sleEponProfileControlRequest, sleEponProfileControlStatus, 
				sleEponProfileControlTimer, sleEponProfileControlReqResult, sleEponProfileControlTimeStamp }
			STATUS current
			DESCRIPTION 
				"Description."
			::= { sleEponProfileNotification 14 }

		
		sleEponProfileDBAChanged NOTIFICATION-TYPE
			OBJECTS { sleEponProfileControlRequest, sleEponProfileControlStatus, sleEponProfileControlTimer, sleEponProfileControlTimeStamp, sleEponProfileControlReqResult, 
				sleEponProfileControlIndex, sleEponProfileControlDPDownMaxBandwidth, sleEponProfileControlDbaName }
			STATUS current
			DESCRIPTION 
				"Description."
			::= { sleEponProfileNotification 15 }

		
		sleEponProfileStormControlChanged NOTIFICATION-TYPE
			OBJECTS { sleEponProfileControlRequest, sleEponProfileControlTimeStamp, sleEponProfileControlReqResult, sleEponProfileControlIndex }
			STATUS current
			DESCRIPTION 
				"Description."
			::= { sleEponProfileNotification 16 }

		
		sleEponProfileIgmpSnoopingTable OBJECT-TYPE
			SYNTAX SEQUENCE OF SleEponProfileIgmpSnoopingEntry
			MAX-ACCESS not-accessible
			STATUS current
			DESCRIPTION
				"Description."
			::= { sleEponProfileBase 4 }

		
		sleEponProfileIgmpSnoopingEntry OBJECT-TYPE
			SYNTAX SleEponProfileIgmpSnoopingEntry
			MAX-ACCESS not-accessible
			STATUS current
			DESCRIPTION
				"Description."
			INDEX { sleEponProfileIndex, sleEponProfileIgmpSnoopingIndex }
			::= { sleEponProfileIgmpSnoopingTable 1 }

		
		SleEponProfileIgmpSnoopingEntry ::=
			SEQUENCE { 
				sleEponProfileIgmpSnoopingIndex
					Integer32,
				sleEponProfileIgmpSnoopingState
					EnableFlag,
				sleEponProfileIgmpSnoopingMaxch
					Integer32,
				sleEponProfileIgmpSnoopingTagVlan
					Integer32
			 }

		sleEponProfileIgmpSnoopingIndex OBJECT-TYPE
			SYNTAX Integer32 (1..5)
			MAX-ACCESS read-only
			STATUS current
			DESCRIPTION
				"Igmp snooping count."
			::= { sleEponProfileIgmpSnoopingEntry 1 }

		
		sleEponProfileIgmpSnoopingState OBJECT-TYPE
			SYNTAX EnableFlag
			MAX-ACCESS read-only
			STATUS current
			DESCRIPTION
				"Description."
			::= { sleEponProfileIgmpSnoopingEntry 2 }

		
		sleEponProfileIgmpSnoopingMaxch OBJECT-TYPE
			SYNTAX Integer32 (1..255)
			MAX-ACCESS read-only
			STATUS current
			DESCRIPTION
				"Maximum number of channels."
			::= { sleEponProfileIgmpSnoopingEntry 3 }

		
		sleEponProfileIgmpSnoopingTagVlan OBJECT-TYPE
			SYNTAX Integer32 (1..4096)
			MAX-ACCESS read-write
			STATUS current
			DESCRIPTION
				"Igmp snooping tag vlan id."
			::= { sleEponProfileIgmpSnoopingEntry 4 }

		
		sleEponProfileIgmpSnoopingControl OBJECT IDENTIFIER ::= { sleEponProfileBase 5 }

		
		sleEponProfileIgmpSnoopingControlRequest OBJECT-TYPE
			SYNTAX INTEGER
				{
				modifyProfileIgmpSnooping(1),
				modifyProfileIgmpSnoopingSpecified(2)
				}
			MAX-ACCESS read-write
			STATUS current
			DESCRIPTION
				"The request of a user command"
			::= { sleEponProfileIgmpSnoopingControl 1 }

		
		sleEponProfileIgmpSnoopingControlStatus OBJECT-TYPE
			SYNTAX SleControlStatusType
			MAX-ACCESS read-only
			STATUS current
			DESCRIPTION
				"The status of user command"
			::= { sleEponProfileIgmpSnoopingControl 2 }

		
		sleEponProfileIgmpSnoopingControlTimer OBJECT-TYPE
			SYNTAX Gauge32
			MAX-ACCESS read-write
			STATUS current
			DESCRIPTION
				"The maximum time for the manager for a long running user command"
			::= { sleEponProfileIgmpSnoopingControl 3 }

		
		sleEponProfileIgmpSnoopingControlTimeStamp OBJECT-TYPE
			SYNTAX TimeTicks
			MAX-ACCESS read-only
			STATUS current
			DESCRIPTION
				"The time stamp of the last command(end of command)"
			::= { sleEponProfileIgmpSnoopingControl 4 }

		
		sleEponProfileIgmpSnoopingControlReqResult OBJECT-TYPE
			SYNTAX SleControlRequestResultType
			MAX-ACCESS read-only
			STATUS current
			DESCRIPTION
				"The result of the last user command"
			::= { sleEponProfileIgmpSnoopingControl 5 }

		
		sleEponProfileIgmpSnoopingControlProfileIndex OBJECT-TYPE
			SYNTAX INTEGER (1..32)
			MAX-ACCESS read-write
			STATUS current
			DESCRIPTION
				"Profile index"
			::= { sleEponProfileIgmpSnoopingControl 6 }

		
		sleEponProfileIgmpSnoopingControlState OBJECT-TYPE
			SYNTAX EnableFlag
			MAX-ACCESS read-write
			STATUS current
			DESCRIPTION
				"enable(1), disable(2)."
			::= { sleEponProfileIgmpSnoopingControl 7 }

		
		sleEponProfileIgmpSnoopingControlMaxch OBJECT-TYPE
			SYNTAX Integer32 (1..255)
			MAX-ACCESS read-write
			STATUS current
			DESCRIPTION
				"Maximum number of channels."
			DEFVAL { 255 }
			::= { sleEponProfileIgmpSnoopingControl 8 }

		
		sleEponProfileIgmpSnoopingControlTagVlan OBJECT-TYPE
			SYNTAX Integer32 (1..4096)
			MAX-ACCESS read-write
			STATUS current
			DESCRIPTION
				"Igmp snooping tag vlan id."
			::= { sleEponProfileIgmpSnoopingControl 9 }

		
		sleEponProfileIgmpSnoopingNotification OBJECT IDENTIFIER ::= { sleEponProfileBase 6 }

		
		sleEponProfileIgmpSnoopingChanged NOTIFICATION-TYPE
			OBJECTS { sleEponProfileIgmpSnoopingControlRequest, sleEponProfileIgmpSnoopingControlTimeStamp, sleEponProfileIgmpSnoopingControlReqResult, sleEponProfileIgmpSnoopingControlProfileName, sleEponProfileIgmpSnoopingControlState, 
				sleEponProfileIgmpSnoopingControlMaxch, sleEponProfileIgmpSnoopingControlTagVlan }
			STATUS current
			DESCRIPTION 
				"Description."
			::= { sleEponProfileIgmpSnoopingNotification 1 }

		
		sleEponProfileOnuRuleTable OBJECT-TYPE
			SYNTAX SEQUENCE OF SleEponProfileOnuRuleEntry
			MAX-ACCESS not-accessible
			STATUS current
			DESCRIPTION
				"Description."
			::= { sleEponProfileBase 7 }

		
		sleEponProfileOnuRuleEntry OBJECT-TYPE
			SYNTAX SleEponProfileOnuRuleEntry
			MAX-ACCESS not-accessible
			STATUS current
			DESCRIPTION
				"Profile Onu rule table."
			INDEX { sleEponProfileIndex, sleEponOnuProfileOnuRuleIndex }
			::= { sleEponProfileOnuRuleTable 1 }

		
		SleEponProfileOnuRuleEntry ::=
			SEQUENCE { 
				sleEponOnuProfileOnuRuleIndex
					INTEGER,
				sleEponProfileOnuRuleName
					OCTET STRING
			 }

		sleEponOnuProfileOnuRuleIndex OBJECT-TYPE
			SYNTAX INTEGER (0..24)
			MAX-ACCESS read-only
			STATUS current
			DESCRIPTION
				"Onu rule index."
			::= { sleEponProfileOnuRuleEntry 1 }

		
		sleEponProfileOnuRuleName OBJECT-TYPE
			SYNTAX OCTET STRING
			MAX-ACCESS read-only
			STATUS current
			DESCRIPTION
				"Rule name."
			::= { sleEponProfileOnuRuleEntry 2 }

		
		sleEponProfileOnuRuleControl OBJECT IDENTIFIER ::= { sleEponProfileBase 8 }

		
		sleEponProfileOnuRuleControlRequest OBJECT-TYPE
			SYNTAX INTEGER
				{
				applyProfileOnuRule(1),
				noApplyProfileOnuRule(2),
				applyProfileOnuRuleSpecified(3),
				noApplyProfileOnuRuleSpecified(4)
				}
			MAX-ACCESS read-write
			STATUS current
			DESCRIPTION
				"The request of a user command"
			::= { sleEponProfileOnuRuleControl 1 }

		
		sleEponProfileOnuRuleControlStatus OBJECT-TYPE
			SYNTAX SleControlStatusType
			MAX-ACCESS read-only
			STATUS current
			DESCRIPTION
				"The status of user command"
			::= { sleEponProfileOnuRuleControl 2 }

		
		sleEponProfileOnuRuleControlTimer OBJECT-TYPE
			SYNTAX Gauge32
			MAX-ACCESS read-write
			STATUS current
			DESCRIPTION
				"The maximum time for the manager for a long running user command"
			::= { sleEponProfileOnuRuleControl 3 }

		
		sleEponProfileOnuRuleControlTimeStamp OBJECT-TYPE
			SYNTAX TimeTicks
			MAX-ACCESS read-only
			STATUS current
			DESCRIPTION
				"The time stamp of the last command(end of command)"
			::= { sleEponProfileOnuRuleControl 4 }

		
		sleEponProfleOnuRuleControlReqResult OBJECT-TYPE
			SYNTAX SleControlRequestResultType
			MAX-ACCESS read-write
			STATUS current
			DESCRIPTION
				"The result of the last user command"
			::= { sleEponProfileOnuRuleControl 5 }

		
		sleEponProfileOnuRuleControlProfileIndex OBJECT-TYPE
			SYNTAX INTEGER (1..32)
			MAX-ACCESS read-write
			STATUS current
			DESCRIPTION
				"Profile Index"
			::= { sleEponProfileOnuRuleControl 6 }

		
		sleEponProfileOnuRuleControlName OBJECT-TYPE
			SYNTAX OCTET STRING
			MAX-ACCESS read-write
			STATUS current
			DESCRIPTION
				"Rule name."
			::= { sleEponProfileOnuRuleControl 7 }

		
		sleEponProfileOnuRuleNotification OBJECT IDENTIFIER ::= { sleEponProfileBase 9 }

		
		sleEponProfileOnuRuleChanged NOTIFICATION-TYPE
			OBJECTS { sleEponProfileOnuRuleControlRequest, sleEponProfileOnuRuleControlTimeStamp, sleEponProfleOnuRuleControlReqResult, sleEponProfileOnuRuleControlName }
			STATUS current
			DESCRIPTION 
				"Create or delete rule."
			::= { sleEponProfileOnuRuleNotification 1 }

		
		sleEponProfileQueue OBJECT IDENTIFIER ::= { sleEponProfile 2 }

		
		sleEponProfileQueueTable OBJECT-TYPE
			SYNTAX SEQUENCE OF SleEponProfileQueueEntry
			MAX-ACCESS not-accessible
			STATUS current
			DESCRIPTION
				"Description."
			::= { sleEponProfileQueue 1 }

		
		sleEponProfileQueueEntry OBJECT-TYPE
			SYNTAX SleEponProfileQueueEntry
			MAX-ACCESS not-accessible
			STATUS current
			DESCRIPTION
				"Description."
			INDEX { sleEponProfileIndex, sleEponProfileQueueIndex }
			::= { sleEponProfileQueueTable 1 }

		
		SleEponProfileQueueEntry ::=
			SEQUENCE { 
				sleEponProfileQueueIndex
					INTEGER,
				sleEponProfileQueueQPUpQueue
					INTEGER,
				sleEponProfileQueueQPUpMaxBandwidth
					INTEGER,
				sleEponProfileQueueQPUpMAxBurstSize
					INTEGER,
				sleEponProfileQueueQPDownQueue
					INTEGER,
				sleEponProfileQueueQPDownMaxBandwidth
					INTEGER,
				sleEponProfileQueueQPDownMAxBurstSize
					INTEGER,
				sleEponProfileQueueQLimitUpBlockSize
					INTEGER,
				sleEponProfileQueueQLimitDownBlockSize
					INTEGER
			 }

		sleEponProfileQueueIndex OBJECT-TYPE
			SYNTAX INTEGER (1..8)
			MAX-ACCESS read-only
			STATUS current
			DESCRIPTION
				"Profile Queue index "
			::= { sleEponProfileQueueEntry 1 }

		
		sleEponProfileQueueQPUpQueue OBJECT-TYPE
			SYNTAX INTEGER (0..7)
			MAX-ACCESS read-only
			STATUS current
			DESCRIPTION
				"Upstream queue number"
			::= { sleEponProfileQueueEntry 2 }

		
		sleEponProfileQueueQPUpMaxBandwidth OBJECT-TYPE
			SYNTAX INTEGER (0 | 100..1000000)
			UNITS "kbps"
			MAX-ACCESS read-only
			STATUS current
			DESCRIPTION
				"Upstream queue max bandwidth"
			::= { sleEponProfileQueueEntry 3 }

		
		sleEponProfileQueueQPUpMAxBurstSize OBJECT-TYPE
			SYNTAX INTEGER (0 | 2..16777214)
			UNITS "byte"
			MAX-ACCESS read-only
			STATUS current
			DESCRIPTION
				"Upstream queue max burst size"
			::= { sleEponProfileQueueEntry 4 }

		
		sleEponProfileQueueQPDownQueue OBJECT-TYPE
			SYNTAX INTEGER (0..7)
			MAX-ACCESS read-only
			STATUS current
			DESCRIPTION
				"Downstream queue number"
			::= { sleEponProfileQueueEntry 5 }

		
		sleEponProfileQueueQPDownMaxBandwidth OBJECT-TYPE
			SYNTAX INTEGER (0 | 100..1000000)
			UNITS "kbps"
			MAX-ACCESS read-only
			STATUS current
			DESCRIPTION
				"Downtream queue max bandwidth"
			::= { sleEponProfileQueueEntry 6 }

		
		sleEponProfileQueueQPDownMAxBurstSize OBJECT-TYPE
			SYNTAX INTEGER (0 | 2..16777214)
			UNITS "byte"
			MAX-ACCESS read-only
			STATUS current
			DESCRIPTION
				"Downtream queue max burst size"
			::= { sleEponProfileQueueEntry 7 }

		
		sleEponProfileQueueQLimitUpBlockSize OBJECT-TYPE
			SYNTAX INTEGER (-1 | 0..9215)
			MAX-ACCESS read-only
			STATUS current
			DESCRIPTION
				"Description."
			::= { sleEponProfileQueueEntry 8 }

		
		sleEponProfileQueueQLimitDownBlockSize OBJECT-TYPE
			SYNTAX INTEGER (-1 | 0..9215)
			MAX-ACCESS read-only
			STATUS current
			DESCRIPTION
				"Description."
			::= { sleEponProfileQueueEntry 9 }

		
		sleEponProfileQueueControl OBJECT IDENTIFIER ::= { sleEponProfileQueue 2 }

		
		sleEponProfileQueueControlRequest OBJECT-TYPE
			SYNTAX INTEGER
				{
				modifyProfileQuuePolicyUp(1),
				modifyProfileQuuePolicyDown(2),
				modifyProfileQueueLimit(3)
				}
			MAX-ACCESS read-write
			STATUS current
			DESCRIPTION
				"The request of a user command"
			::= { sleEponProfileQueueControl 1 }

		
		sleEponProfileQueueControlStatus OBJECT-TYPE
			SYNTAX SleControlStatusType
			MAX-ACCESS read-only
			STATUS current
			DESCRIPTION
				"The status of user command"
			::= { sleEponProfileQueueControl 2 }

		
		sleEponProfileQueueControlTimer OBJECT-TYPE
			SYNTAX Gauge32
			MAX-ACCESS read-write
			STATUS current
			DESCRIPTION
				"The maximum time for the manager for a long running user command"
			::= { sleEponProfileQueueControl 3 }

		
		sleEponProfileQueueControlTimeStamp OBJECT-TYPE
			SYNTAX TimeTicks
			MAX-ACCESS read-only
			STATUS current
			DESCRIPTION
				"The time stamp of the last command(end of command)"
			::= { sleEponProfileQueueControl 4 }

		
		sleEponProfileQueueControlReqResult OBJECT-TYPE
			SYNTAX SleControlRequestResultType
			MAX-ACCESS read-only
			STATUS current
			DESCRIPTION
				"The result of the last user command"
			::= { sleEponProfileQueueControl 5 }

		
		sleEponProfileQueueControlProfileIndex OBJECT-TYPE
			SYNTAX INTEGER (1..32)
			MAX-ACCESS read-write
			STATUS current
			DESCRIPTION
				"Profile Index"
			::= { sleEponProfileQueueControl 6 }

		
		sleEponProfileQueueControlQueueIndex OBJECT-TYPE
			SYNTAX INTEGER (1..8)
			MAX-ACCESS read-write
			STATUS current
			DESCRIPTION
				"Profile Queue index "
			::= { sleEponProfileQueueControl 7 }

		
		sleEponProfileQueueControlQPUpQueue OBJECT-TYPE
			SYNTAX INTEGER (0..7)
			MAX-ACCESS read-write
			STATUS current
			DESCRIPTION
				"Upstream queue number"
			::= { sleEponProfileQueueControl 8 }

		
		sleEponProfileQueueControlQPUpMaxBandwidth OBJECT-TYPE
			SYNTAX INTEGER (0 | 100..1000000)
			UNITS "kbps"
			MAX-ACCESS read-write
			STATUS current
			DESCRIPTION
				"Upstream queue max bandwidth"
			::= { sleEponProfileQueueControl 9 }

		
		sleEponProfileQueueControlQPUpMAxBurstSize OBJECT-TYPE
			SYNTAX INTEGER (0 | 2..16777214)
			UNITS "byte"
			MAX-ACCESS read-write
			STATUS current
			DESCRIPTION
				"Upstream queue max burst size"
			::= { sleEponProfileQueueControl 10 }

		
		sleEponProfileQueueControlQPDownQueue OBJECT-TYPE
			SYNTAX INTEGER (0..7)
			MAX-ACCESS read-write
			STATUS current
			DESCRIPTION
				"Downstream queue number"
			::= { sleEponProfileQueueControl 11 }

		
		sleEponProfileQueueControlQPDownMaxBandwidth OBJECT-TYPE
			SYNTAX INTEGER (0 | 100..1000000)
			UNITS "kbps"
			MAX-ACCESS read-write
			STATUS current
			DESCRIPTION
				"Downtream queue max bandwidth"
			::= { sleEponProfileQueueControl 12 }

		
		sleEponProfileQueueControlQPDownMAxBurstSize OBJECT-TYPE
			SYNTAX INTEGER (0 | 2..16777214)
			UNITS "byte"
			MAX-ACCESS read-write
			STATUS current
			DESCRIPTION
				"Downtream queue max burst size"
			::= { sleEponProfileQueueControl 13 }

		
		sleEponProfileQueueControlLimitFlag OBJECT-TYPE
			SYNTAX INTEGER
				{
				up(1),
				down(2)
				}
			MAX-ACCESS read-write
			STATUS current
			DESCRIPTION
				"Description."
			::= { sleEponProfileQueueControl 14 }

		
		sleEponProfileQueueControlBlockSize0 OBJECT-TYPE
			SYNTAX INTEGER (-1 | 0..9215)
			MAX-ACCESS read-write
			STATUS current
			DESCRIPTION
				"Description."
			::= { sleEponProfileQueueControl 15 }

		
		sleEponProfileQueueControlBlockSize1 OBJECT-TYPE
			SYNTAX INTEGER (-1 | 0..9215)
			MAX-ACCESS read-write
			STATUS current
			DESCRIPTION
				"Description."
			::= { sleEponProfileQueueControl 16 }

		
		sleEponProfileQueueControlBlockSize2 OBJECT-TYPE
			SYNTAX INTEGER (-1 | 0..9215)
			MAX-ACCESS read-write
			STATUS current
			DESCRIPTION
				"Description."
			::= { sleEponProfileQueueControl 17 }

		
		sleEponProfileQueueControlBlockSize3 OBJECT-TYPE
			SYNTAX INTEGER (-1 | 0..9215)
			MAX-ACCESS read-write
			STATUS current
			DESCRIPTION
				"Description."
			::= { sleEponProfileQueueControl 18 }

		
		sleEponProfileQueueControlBlockSize4 OBJECT-TYPE
			SYNTAX INTEGER (-1 | 0..9152)
			MAX-ACCESS read-write
			STATUS current
			DESCRIPTION
				"Description."
			::= { sleEponProfileQueueControl 19 }

		
		sleEponProfileQueueControlBlockSize5 OBJECT-TYPE
			SYNTAX INTEGER (-1 | 0..9152)
			MAX-ACCESS read-write
			STATUS current
			DESCRIPTION
				"Description."
			::= { sleEponProfileQueueControl 20 }

		
		sleEponProfileQueueControlBlockSize6 OBJECT-TYPE
			SYNTAX INTEGER (-1 | 0..9152)
			MAX-ACCESS read-write
			STATUS current
			DESCRIPTION
				"Description."
			::= { sleEponProfileQueueControl 21 }

		
		sleEponProfileQueueControlBlockSize7 OBJECT-TYPE
			SYNTAX INTEGER (-1 | 0..9152)
			MAX-ACCESS read-write
			STATUS current
			DESCRIPTION
				"Description."
			::= { sleEponProfileQueueControl 22 }

		
		sleEponProfileQueueNotification OBJECT IDENTIFIER ::= { sleEponProfileQueue 3 }

		
		sleEponProfileQueueModifyQueuePolicy NOTIFICATION-TYPE
			OBJECTS { sleEponProfileQueueControlRequest, sleEponProfileQueueControlTimeStamp, sleEponProfileQueueControlReqResult, sleEponProfileQueueControlProfileIndex, sleEponProfileQueueControlQueueIndex
				 }
			STATUS current
			DESCRIPTION 
				"Description."
			::= { sleEponProfileQueueNotification 1 }

		
		sleEponProfileQueueModifyQueueLimit NOTIFICATION-TYPE
			OBJECTS { sleEponProfileQueueControlRequest, sleEponProfileQueueControlTimeStamp, sleEponProfileQueueControlReqResult, sleEponProfileQueueControlProfileIndex, sleEponProfileQueueControlLimitFlag, 
				sleEponProfileQueueControlBlockSize0, sleEponProfileQueueControlBlockSize1, sleEponProfileQueueControlBlockSize2, sleEponProfileQueueControlBlockSize3, sleEponProfileQueueControlBlockSize4, 
				sleEponProfileQueueControlBlockSize5, sleEponProfileQueueControlBlockSize6, sleEponProfileQueueControlBlockSize7 }
			STATUS current
			DESCRIPTION 
				"Description."
			::= { sleEponProfileQueueNotification 2 }

		
		sleEponProfileVlan OBJECT IDENTIFIER ::= { sleEponProfile 3 }

		
		sleEponProfileVlanTable OBJECT-TYPE
			SYNTAX SEQUENCE OF SleEponProfileVlanEntry
			MAX-ACCESS not-accessible
			STATUS current
			DESCRIPTION
				"Description."
			::= { sleEponProfileVlan 1 }

		
		sleEponProfileVlanEntry OBJECT-TYPE
			SYNTAX SleEponProfileVlanEntry
			MAX-ACCESS not-accessible
			STATUS current
			DESCRIPTION
				"Description."
			INDEX { sleEponProfileIndex, sleEponProfileVlanIndex }
			::= { sleEponProfileVlanTable 1 }

		
		SleEponProfileVlanEntry ::=
			SEQUENCE { 
				sleEponProfileVlanIndex
					VlanIndex,
				sleEponProfileVlanEgressPorts
					PortList,
				sleEponProfileVlanUntaggedPorts
					PortList
			 }

		sleEponProfileVlanIndex OBJECT-TYPE
			SYNTAX VlanIndex (1..4094)
			MAX-ACCESS read-only
			STATUS current
			DESCRIPTION
				"The index of ONU VLAN"
			::= { sleEponProfileVlanEntry 1 }

		
		sleEponProfileVlanEgressPorts OBJECT-TYPE
			SYNTAX PortList
			MAX-ACCESS read-only
			STATUS current
			DESCRIPTION
				"The set of ports which are transmitting traffic for this ONU VLAN as either tagged or untagged frames."
			::= { sleEponProfileVlanEntry 2 }

		
		sleEponProfileVlanUntaggedPorts OBJECT-TYPE
			SYNTAX PortList
			MAX-ACCESS read-only
			STATUS current
			DESCRIPTION
				"The set of ports which are transmitting traffic for this VLAN as untagged frames"
			::= { sleEponProfileVlanEntry 3 }

		
		sleEponProfileVlanControl OBJECT IDENTIFIER ::= { sleEponProfileVlan 2 }

		
		sleEponProfileVlanControlRequest OBJECT-TYPE
			SYNTAX INTEGER
				{
				createVlan(1),
				destroyVlan(2),
				setAddVlanProfile(3),
				setDelVlanProfile(4),
				setPvidVlanProfile(5)
				}
			MAX-ACCESS read-write
			STATUS current
			DESCRIPTION
				"The request of a user command"
			::= { sleEponProfileVlanControl 1 }

		
		sleEponProfileVlanControlStatus OBJECT-TYPE
			SYNTAX SleControlStatusType
			MAX-ACCESS read-only
			STATUS current
			DESCRIPTION
				"The status of user command"
			::= { sleEponProfileVlanControl 2 }

		
		sleEponProfileVlanControlTimer OBJECT-TYPE
			SYNTAX Gauge32
			MAX-ACCESS read-write
			STATUS current
			DESCRIPTION
				"The maximum time for the manager for a long running user command"
			::= { sleEponProfileVlanControl 3 }

		
		sleEponProfileVlanControlTimeStamp OBJECT-TYPE
			SYNTAX TimeTicks
			MAX-ACCESS read-only
			STATUS current
			DESCRIPTION
				"The time stamp of the last command(end of command)"
			::= { sleEponProfileVlanControl 4 }

		
		sleEponProfileVlanControlReqResult OBJECT-TYPE
			SYNTAX SleControlRequestResultType
			MAX-ACCESS read-only
			STATUS current
			DESCRIPTION
				"The result of the last user command"
			::= { sleEponProfileVlanControl 5 }

		
		sleEponProfileVlanControlProfileIndex OBJECT-TYPE
			SYNTAX INTEGER (1..32)
			MAX-ACCESS read-write
			STATUS current
			DESCRIPTION
				"Description."
			::= { sleEponProfileVlanControl 6 }

		
		sleEponProfileVlanControlVlanIndex OBJECT-TYPE
			SYNTAX VlanIndex
			MAX-ACCESS read-write
			STATUS current
			DESCRIPTION
				"The index of ONU VLAN"
			::= { sleEponProfileVlanControl 7 }

		
		sleEponProfileVlanControlVlanEgressPorts OBJECT-TYPE
			SYNTAX PortList
			MAX-ACCESS read-write
			STATUS current
			DESCRIPTION
				"The set of ports which are transmitting traffic for this ONU VLAN as either tagged or untagged frames."
			::= { sleEponProfileVlanControl 8 }

		
		sleEponProfileVlanControlVlanUntaggedPorts OBJECT-TYPE
			SYNTAX PortList
			MAX-ACCESS read-write
			STATUS current
			DESCRIPTION
				"The set of ports which are transmitting traffic for this VLAN as untagged frames"
			::= { sleEponProfileVlanControl 9 }

		
		sleEponProfileVlanControlVlanPort OBJECT-TYPE
			SYNTAX Integer32
			MAX-ACCESS read-write
			STATUS current
			DESCRIPTION
				"Description."
			::= { sleEponProfileVlanControl 10 }

		
		sleEponProfileVlanControlVlanTagged OBJECT-TYPE
			SYNTAX INTEGER
				{
				tagged(1),
				untagged(2)
				}
			MAX-ACCESS read-write
			STATUS current
			DESCRIPTION
				"Description."
			::= { sleEponProfileVlanControl 11 }

		
		sleEponProfileVlanControlVlanPvid OBJECT-TYPE
			SYNTAX Integer32
			MAX-ACCESS read-write
			STATUS current
			DESCRIPTION
				"Description."
			::= { sleEponProfileVlanControl 12 }

		
		sleEponProfileVlanNotification OBJECT IDENTIFIER ::= { sleEponProfileVlan 3 }

		
		sleEponProfileVlanCreated NOTIFICATION-TYPE
			OBJECTS { sleEponProfileVlanControlRequest, sleEponProfileVlanControlTimeStamp, sleEponProfileVlanControlReqResult, sleEponProfileControlIndex, sleEponProfileControlName, 
				sleEponProfileVlanControlVlanIndex }
			STATUS current
			DESCRIPTION 
				"Description."
			::= { sleEponProfileVlanNotification 1 }

		
		sleEponProfileVlanDestroyed NOTIFICATION-TYPE
			OBJECTS { sleEponProfileVlanControlRequest, sleEponProfileVlanControlTimeStamp, sleEponProfileVlanControlReqResult, sleEponProfileControlIndex, sleEponProfileControlName, 
				sleEponProfileVlanControlVlanIndex }
			STATUS current
			DESCRIPTION 
				"Description."
			::= { sleEponProfileVlanNotification 2 }

		
		sleEponProfileVlanProfileChanged NOTIFICATION-TYPE
			OBJECTS { sleEponProfileVlanControlRequest, sleEponProfileVlanControlTimeStamp, sleEponProfileVlanControlReqResult, sleEponProfileControlIndex, sleEponProfileControlName, 
				sleEponProfileVlanControlVlanIndex, sleEponProfileVlanControlVlanEgressPorts, sleEponProfileVlanControlVlanUntaggedPorts }
			STATUS current
			DESCRIPTION 
				"Description."
			::= { sleEponProfileVlanNotification 3 }

		
		sleEponProfilePort OBJECT IDENTIFIER ::= { sleEponProfile 4 }

		
		sleEponProfilePortTable OBJECT-TYPE
			SYNTAX SEQUENCE OF SleEponProfilePortEntry
			MAX-ACCESS not-accessible
			STATUS current
			DESCRIPTION
				"Description."
			::= { sleEponProfilePort 1 }

		
		sleEponProfilePortEntry OBJECT-TYPE
			SYNTAX SleEponProfilePortEntry
			MAX-ACCESS not-accessible
			STATUS current
			DESCRIPTION
				"Description."
			INDEX { sleEponProfileIndex, sleEponProfilePortIndex }
			::= { sleEponProfilePortTable 1 }

		
		SleEponProfilePortEntry ::=
			SEQUENCE { 
				sleEponProfilePortIndex
					INTEGER,
				sleEponProfilePortAdminStatus
					INTEGER,
				sleEponProfilePortNego
					INTEGER,
				sleEponProfilePortSpeed
					INTEGER,
				sleEponProfilePortduplex
					INTEGER,
				sleEponProfilePortMaxHost
					Integer32,
				sleEponProfilePortPvid
					VlanIndex,
				sleEponProfilePortIngressRateLimitMode
					INTEGER,
				sleEponProfilePortIngressRateLimit
					INTEGER,
				sleEponProfilePortEgressRateLimit
					INTEGER,
				sleEponProfilePortFlowControl
					INTEGER,
				sleEponProfilePortIsolationStatus
					EnableFlag,
				sleEponProfilePortMaxHostAgingTime
					INTEGER,
				sleEponProfilePortEgressRateLimitMode
					INTEGER
			 }

		sleEponProfilePortIndex OBJECT-TYPE
			SYNTAX INTEGER (1..256)
			MAX-ACCESS read-only
			STATUS current
			DESCRIPTION
				"The index of the ONU port"
			::= { sleEponProfilePortEntry 1 }

		
		sleEponProfilePortAdminStatus OBJECT-TYPE
			SYNTAX INTEGER
				{
				enable(1),
				disable(2)
				}
			MAX-ACCESS read-only
			STATUS current
			DESCRIPTION
				"The desired state of the ONU port"
			::= { sleEponProfilePortEntry 2 }

		
		sleEponProfilePortNego OBJECT-TYPE
			SYNTAX INTEGER
				{
				on(1),
				off(2)
				}
			MAX-ACCESS read-only
			STATUS current
			DESCRIPTION
				"The current operational state of the ONU port"
			::= { sleEponProfilePortEntry 3 }

		
		sleEponProfilePortSpeed OBJECT-TYPE
			SYNTAX INTEGER (10 | 100 | 1000)
			UNITS "Mbits/sec"
			MAX-ACCESS read-only
			STATUS current
			DESCRIPTION
				"It's auto-negotiation for a port, automatically to match the transmission speed and the duplex mode of the attached device"
			::= { sleEponProfilePortEntry 4 }

		
		sleEponProfilePortduplex OBJECT-TYPE
			SYNTAX INTEGER
				{
				full(1),
				half(2)
				}
			MAX-ACCESS read-only
			STATUS current
			DESCRIPTION
				"It express port speed that configure transmit rate of each port."
			::= { sleEponProfilePortEntry 5 }

		
		sleEponProfilePortMaxHost OBJECT-TYPE
			SYNTAX Integer32
			MAX-ACCESS read-only
			STATUS current
			DESCRIPTION
				"It express half duplex or full duplex mode. Only unidirectional communication is possible on half duplex mode and bi-directional communication is possible on full duplex mode to transmit packet for two ways."
			::= { sleEponProfilePortEntry 6 }

		
		sleEponProfilePortPvid OBJECT-TYPE
			SYNTAX VlanIndex
			MAX-ACCESS read-only
			STATUS current
			DESCRIPTION
				"It is PVID that configure in ONU port"
			::= { sleEponProfilePortEntry 7 }

		
		sleEponProfilePortIngressRateLimitMode OBJECT-TYPE
			SYNTAX INTEGER
				{
				all(0),
				multiBroadUnicast(1),
				multiBroadcast(2),
				broadcast(3)
				}
			MAX-ACCESS read-only
			STATUS current
			DESCRIPTION
				"It is rate limit mode in Ingress
				0  Limit all frames
				 1  Limit multicast, broadcast and flooded unicast frame
				 2  Limit multicast, broadcast frame
				 3  Limit broadcast frame only"
			::= { sleEponProfilePortEntry 8 }

		
		sleEponProfilePortIngressRateLimit OBJECT-TYPE
			SYNTAX INTEGER (0 | 62..100000)
			MAX-ACCESS read-only
			STATUS current
			DESCRIPTION
				"It is configurable port rate limit in Ingress
				The value of 0 is unlimit
				"
			DEFVAL { 0 }
			::= { sleEponProfilePortEntry 9 }

		
		sleEponProfilePortEgressRateLimit OBJECT-TYPE
			SYNTAX INTEGER (0 | 62..100000)
			MAX-ACCESS read-only
			STATUS current
			DESCRIPTION
				"It is configurable port rate limit in Egress
				The value of 0 is unlimit
				"
			DEFVAL { 0 }
			::= { sleEponProfilePortEntry 10 }

		
		sleEponProfilePortFlowControl OBJECT-TYPE
			SYNTAX INTEGER
				{
				on(1),
				off(2)
				}
			MAX-ACCESS read-only
			STATUS current
			DESCRIPTION
				"Description."
			::= { sleEponProfilePortEntry 11 }

		
		sleEponProfilePortIsolationStatus OBJECT-TYPE
			SYNTAX EnableFlag
			MAX-ACCESS read-only
			STATUS current
			DESCRIPTION
				"Description."
			::= { sleEponProfilePortEntry 12 }

		
		sleEponProfilePortMaxHostAgingTime OBJECT-TYPE
			SYNTAX INTEGER (10..300)
			MAX-ACCESS read-write
			STATUS current
			DESCRIPTION
				"Max Host Aging Time."
			::= { sleEponProfilePortEntry 13 }

		
		sleEponProfilePortEgressRateLimitMode OBJECT-TYPE
			SYNTAX INTEGER
				{
				all(0),
				multiBroadUnicast(1),
				multiBroadcast(2),
				broadcast(3)
				}
			MAX-ACCESS read-only
			STATUS current
			DESCRIPTION
				"Description."
			::= { sleEponProfilePortEntry 14 }

		
		sleEponProfilePortControl OBJECT IDENTIFIER ::= { sleEponProfilePort 2 }

		
		sleEponProfilePortControlRequest OBJECT-TYPE
			SYNTAX INTEGER
				{
				setPortAdminStatus(1),
				setPortNego(2),
				setPortSpeed(3),
				setPortDuplex(4),
				setPortMaxHost(5),
				setPortPvid(6),
				setPortRateLimit(7),
				setPortFlowControl(8),
				setPortIsolation(9),
				setPortMaxHostAgingTime(10),
				noMaxHost(11),
				unsetPortRateLimit(12)
				}
			MAX-ACCESS read-write
			STATUS current
			DESCRIPTION
				"The request of a user command"
			::= { sleEponProfilePortControl 1 }

		
		sleEponProfilePortControlStatus OBJECT-TYPE
			SYNTAX SleControlStatusType
			MAX-ACCESS read-only
			STATUS current
			DESCRIPTION
				"The status of user command"
			::= { sleEponProfilePortControl 2 }

		
		sleEponProfilePortControlTimer OBJECT-TYPE
			SYNTAX Gauge32
			MAX-ACCESS read-write
			STATUS current
			DESCRIPTION
				"The maximum time for the manager for a long running user command"
			::= { sleEponProfilePortControl 3 }

		
		sleEponProfilePortControlTimeStamp OBJECT-TYPE
			SYNTAX TimeTicks
			MAX-ACCESS read-only
			STATUS current
			DESCRIPTION
				"The time stamp of the last command(end of command)"
			::= { sleEponProfilePortControl 4 }

		
		sleEponProfilePortControlReqResult OBJECT-TYPE
			SYNTAX SleControlRequestResultType
			MAX-ACCESS read-only
			STATUS current
			DESCRIPTION
				"The result of the last user command"
			::= { sleEponProfilePortControl 5 }

		
		sleEponProfilePortControlProfileIndex OBJECT-TYPE
			SYNTAX INTEGER (1..32)
			MAX-ACCESS read-write
			STATUS current
			DESCRIPTION
				"Description."
			::= { sleEponProfilePortControl 6 }

		
		sleEponProfilePortControlPortIndex OBJECT-TYPE
			SYNTAX INTEGER (1..256)
			MAX-ACCESS read-write
			STATUS current
			DESCRIPTION
				"Description."
			::= { sleEponProfilePortControl 7 }

		
		sleEponProfilePortControlAdminStatus OBJECT-TYPE
			SYNTAX INTEGER
				{
				enable(1),
				disable(2)
				}
			MAX-ACCESS read-write
			STATUS current
			DESCRIPTION
				"Description."
			DEFVAL { 0 }
			::= { sleEponProfilePortControl 8 }

		
		sleEponProfilePortControlNego OBJECT-TYPE
			SYNTAX INTEGER
				{
				on(1),
				off(2)
				}
			MAX-ACCESS read-write
			STATUS current
			DESCRIPTION
				"Description."
			DEFVAL { 1 }
			::= { sleEponProfilePortControl 9 }

		
		sleEponProfilePortControlSpeed OBJECT-TYPE
			SYNTAX INTEGER (10 | 100 | 1000)
			UNITS "Mbits/sec"
			MAX-ACCESS read-write
			STATUS current
			DESCRIPTION
				"Description."
			::= { sleEponProfilePortControl 10 }

		
		sleEponProfilePortControlDuplex OBJECT-TYPE
			SYNTAX INTEGER
				{
				full(1),
				half(2)
				}
			MAX-ACCESS read-write
			STATUS current
			DESCRIPTION
				"Description."
			DEFVAL { 1 }
			::= { sleEponProfilePortControl 11 }

		
		sleEponProfilePortControlMaxHost OBJECT-TYPE
			SYNTAX Integer32
			MAX-ACCESS read-write
			STATUS current
			DESCRIPTION
				"Description."
			::= { sleEponProfilePortControl 12 }

		
		sleEponProfilePortControlPvid OBJECT-TYPE
			SYNTAX VlanIndex
			MAX-ACCESS read-write
			STATUS current
			DESCRIPTION
				"It is PVID that configure in ONU port"
			DEFVAL { '1'b }
			::= { sleEponProfilePortControl 13 }

		
		sleEponProfilePortControlIngressRateLimitMode OBJECT-TYPE
			SYNTAX INTEGER
				{
				all(0),
				multiBroadUnicast(1),
				multiBroadcast(2),
				broadcast(3)
				}
			MAX-ACCESS read-write
			STATUS current
			DESCRIPTION
				"It is rate limit mode in Ingress 
				0  Limit all frames
				  1  Limit multicast, broadcast and flooded unicast frame
				  2  Limit multicast, broadcast frame
				  3  Limit broadcast frame only"
			DEFVAL { 0 }
			::= { sleEponProfilePortControl 14 }

		
		sleEponProfilePortControlIngressRateLimit OBJECT-TYPE
			SYNTAX INTEGER (62..100000)
			MAX-ACCESS read-write
			STATUS current
			DESCRIPTION
				"It is configurable port rate limit in Ingress
				The value of 0 is unlimit
				"
			DEFVAL { 0 }
			::= { sleEponProfilePortControl 15 }

		
		sleEponProfilePortControlEgressRateLimit OBJECT-TYPE
			SYNTAX INTEGER (62..100000)
			MAX-ACCESS read-write
			STATUS current
			DESCRIPTION
				"It is configurable port rate limit in Egress
				The value of 0 is unlimit
				"
			DEFVAL { 0 }
			::= { sleEponProfilePortControl 16 }

		
		sleEponProfilePortControlFlowControl OBJECT-TYPE
			SYNTAX INTEGER
				{
				on(1),
				off(2)
				}
			MAX-ACCESS read-write
			STATUS current
			DESCRIPTION
				"Description."
			::= { sleEponProfilePortControl 17 }

		
		sleEponProfilePortControlIsolationStatus OBJECT-TYPE
			SYNTAX EnableFlag
			MAX-ACCESS read-write
			STATUS current
			DESCRIPTION
				"Description."
			::= { sleEponProfilePortControl 18 }

		
		sleEponProfilePortControlMaxHostAgingTime OBJECT-TYPE
			SYNTAX INTEGER (10..300)
			MAX-ACCESS read-write
			STATUS current
			DESCRIPTION
				"Max Host Aging Time."
			::= { sleEponProfilePortControl 19 }

		
		sleEponProfilePortControlEgressRateLimitMode OBJECT-TYPE
			SYNTAX Integer32
			MAX-ACCESS read-write
			STATUS current
			DESCRIPTION
				"Description."
			::= { sleEponProfilePortControl 20 }

		
		sleEponProfilePortControlRateLimitDirection OBJECT-TYPE
			SYNTAX INTEGER
				{
				ingress(1),
				egress(2)
				}
			MAX-ACCESS read-write
			STATUS current
			DESCRIPTION
				"Description."
			::= { sleEponProfilePortControl 21 }

		
		sleEponProfilePortNotification OBJECT IDENTIFIER ::= { sleEponProfilePort 3 }

		
		sleEponProfilePortAdminStatusChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlAdminStatus }
			STATUS current
			DESCRIPTION 
				"Description."
			::= { sleEponProfilePortNotification 1 }

		
		sleEponProfilePortNegoChanged NOTIFICATION-TYPE
			OBJECTS { sleEponProfilePortControlRequest, sleEponProfilePortControlTimeStamp, sleEponProfilePortControlReqResult, sleEponProfilePortControlProfileIndex, sleEponProfilePortControlPortIndex, 
				sleEponProfilePortControlNego, sleEponProfileControlName }
			STATUS current
			DESCRIPTION 
				"Description."
			::= { sleEponProfilePortNotification 2 }

		
		sleEponProfilePortSpeedChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlSpeed }
			STATUS current
			DESCRIPTION 
				"Description."
			::= { sleEponProfilePortNotification 3 }

		
		sleEponProfilePortDuplexChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlDuplex }
			STATUS current
			DESCRIPTION 
				"Description."
			::= { sleEponProfilePortNotification 4 }

		
		sleEponProfilePortMaxHostChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlMaxHost }
			STATUS current
			DESCRIPTION 
				"Description."
			::= { sleEponProfilePortNotification 5 }

		
		sleEponProfilePortPvidChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlPvid }
			STATUS current
			DESCRIPTION 
				"Description."
			::= { sleEponProfilePortNotification 6 }

		
		sleEponProfilePortRateLimitChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlIngressRateLimitMode, sleEponProfilePortControlIngressRateLimit, sleEponProfilePortControlEgressRateLimit }
			STATUS current
			DESCRIPTION 
				"Description."
			::= { sleEponProfilePortNotification 7 }

		
		sleEponProfilePortFlowControlChanged NOTIFICATION-TYPE
			OBJECTS { sleEponProfilePortControlRequest, sleEponProfilePortControlTimeStamp, sleEponProfilePortControlReqResult, sleEponProfilePortControlProfileIndex, sleEponProfileControlName, 
				sleEponProfilePortControlPortIndex, sleEponProfilePortControlFlowControl }
			STATUS current
			DESCRIPTION 
				"Description."
			::= { sleEponProfilePortNotification 8 }

		
		sleEponProfilePortIsolationChanged NOTIFICATION-TYPE
			OBJECTS { sleEponProfilePortControlRequest, sleEponProfilePortControlTimeStamp, sleEponProfilePortControlReqResult, sleEponProfilePortControlProfileIndex, sleEponProfilePortControlPortIndex, 
				sleEponProfilePortControlIsolationStatus }
			STATUS current
			DESCRIPTION 
				"Description."
			::= { sleEponProfilePortNotification 9 }

		
		sleEponProfilePortUnsetRatelimitChanged NOTIFICATION-TYPE
			OBJECTS { sleEponProfilePortConfigControlRequest, sleEponProfilePortConfigControlStatus, sleEponProfilePortConfigControlTimer, sleEponProfilePortConfigControlTimeStamp, sleEponProfilePortConfigControlReqResult, 
				sleEponProfilePortConfigControlProfileIndex, sleEponProfilePortConfigControlState, sleEponProfilePortConfigControlPort, sleEponProfilePortControlReqResult, sleEponProfilePortControlProfileIndex, 
				sleEponProfilePortControlPortIndex, sleEponProfilePortControlRateLimitDirection }
			STATUS current
			DESCRIPTION 
				"Description."
			::= { sleEponProfilePortNotification 10 }

		
		sleEponProfileClassification OBJECT IDENTIFIER ::= { sleEponProfile 5 }

		
		sleEponProfileClassificationTable OBJECT-TYPE
			SYNTAX SEQUENCE OF SleEponProfileClassificationEntry
			MAX-ACCESS not-accessible
			STATUS current
			DESCRIPTION
				"Description."
			::= { sleEponProfileClassification 1 }

		
		sleEponProfileClassificationEntry OBJECT-TYPE
			SYNTAX SleEponProfileClassificationEntry
			MAX-ACCESS not-accessible
			STATUS current
			DESCRIPTION
				"Description."
			INDEX { sleEponProfileIndex, sleEponProfileClassificationIndex }
			::= { sleEponProfileClassificationTable 1 }

		
		SleEponProfileClassificationEntry ::=
			SEQUENCE { 
				sleEponProfileClassificationIndex
					INTEGER,
				sleEponProfileClassificationMatchAction
					INTEGER,
				sleEponProfileClassificationQueue
					INTEGER
			 }

		sleEponProfileClassificationIndex OBJECT-TYPE
			SYNTAX INTEGER (1..256)
			MAX-ACCESS read-only
			STATUS current
			DESCRIPTION
				"Description."
			::= { sleEponProfileClassificationEntry 1 }

		
		sleEponProfileClassificationMatchAction OBJECT-TYPE
			SYNTAX INTEGER
				{
				permit(1),
				deny(2),
				notUse(3)
				}
			MAX-ACCESS read-only
			STATUS current
			DESCRIPTION
				"Description."
			::= { sleEponProfileClassificationEntry 2 }

		
		sleEponProfileClassificationQueue OBJECT-TYPE
			SYNTAX INTEGER (-1 | 0..7)
			MAX-ACCESS read-only
			STATUS current
			DESCRIPTION
				"The value of -1 is all of the queue"
			::= { sleEponProfileClassificationEntry 3 }

		
		sleEponProfileClassificationControl OBJECT IDENTIFIER ::= { sleEponProfileClassification 2 }

		
		sleEponProfileClassificationControlRequest OBJECT-TYPE
			SYNTAX INTEGER
				{
				createClassification(1),
				destroyClassification(2)
				}
			MAX-ACCESS read-write
			STATUS current
			DESCRIPTION
				"Description."
			::= { sleEponProfileClassificationControl 1 }

		
		sleEponProfileClassificationControlStatus OBJECT-TYPE
			SYNTAX SleControlStatusType
			MAX-ACCESS read-only
			STATUS current
			DESCRIPTION
				"Description."
			::= { sleEponProfileClassificationControl 2 }

		
		sleEponProfileClassificationControlTimer OBJECT-TYPE
			SYNTAX Gauge32
			MAX-ACCESS read-write
			STATUS current
			DESCRIPTION
				"Description."
			::= { sleEponProfileClassificationControl 3 }

		
		sleEponProfileClassificationControlTimeStamp OBJECT-TYPE
			SYNTAX TimeTicks
			MAX-ACCESS read-only
			STATUS current
			DESCRIPTION
				"Description."
			::= { sleEponProfileClassificationControl 4 }

		
		sleEponProfileClassificationControlReqResult OBJECT-TYPE
			SYNTAX SleControlRequestResultType
			MAX-ACCESS read-only
			STATUS current
			DESCRIPTION
				"Description."
			::= { sleEponProfileClassificationControl 5 }

		
		sleEponProfileClassificationControlProfileIndex OBJECT-TYPE
			SYNTAX INTEGER (1..32)
			MAX-ACCESS read-write
			STATUS current
			DESCRIPTION
				"Description."
			::= { sleEponProfileClassificationControl 6 }

		
		sleEponProfileClassificationControlClassificationIndex OBJECT-TYPE
			SYNTAX INTEGER (1..256)
			MAX-ACCESS read-write
			STATUS current
			DESCRIPTION
				"Description."
			::= { sleEponProfileClassificationControl 7 }

		
		sleEponProfileClassificationControlMatchAction OBJECT-TYPE
			SYNTAX INTEGER
				{
				permit(1),
				deny(2),
				notUse(3)
				}
			MAX-ACCESS read-write
			STATUS current
			DESCRIPTION
				"Description."
			::= { sleEponProfileClassificationControl 8 }

		
		sleEponProfileClassificationControlQueue OBJECT-TYPE
			SYNTAX INTEGER (-1 | 0..7)
			MAX-ACCESS read-write
			STATUS current
			DESCRIPTION
				"Description."
			::= { sleEponProfileClassificationControl 9 }

		
		sleEponProfileClassificationNotification OBJECT IDENTIFIER ::= { sleEponProfileClassification 3 }

		
		sleEponProfileClassificationCreated NOTIFICATION-TYPE
			OBJECTS { sleEponProfileClassificationControlRequest, sleEponProfileClassificationControlTimeStamp, sleEponProfileClassificationControlReqResult, sleEponProfileClassificationControlProfileIndex, sleEponProfileClassificationControlClassificationIndex, 
				sleEponProfileClassificationControlMatchAction, sleEponProfileClassificationControlQueue }
			STATUS current
			DESCRIPTION 
				"Description."
			::= { sleEponProfileClassificationNotification 1 }

		
		sleEponProfileClassificationDestroyed NOTIFICATION-TYPE
			OBJECTS { sleEponProfileClassificationControlRequest, sleEponProfileClassificationControlTimeStamp, sleEponProfileClassificationControlReqResult, sleEponProfileClassificationControlProfileIndex, sleEponProfileControlName, 
				sleEponProfileClassificationControlClassificationIndex, sleEponOnuClassificationControlName }
			STATUS current
			DESCRIPTION 
				"Description."
			::= { sleEponProfileClassificationNotification 2 }

		
		sleEponProfileUNIQueue OBJECT IDENTIFIER ::= { sleEponProfile 6 }

		
		sleEponProfileUNIQueueTable OBJECT-TYPE
			SYNTAX SEQUENCE OF SleEponProfileUNIQueueEntry
			MAX-ACCESS not-accessible
			STATUS current
			DESCRIPTION
				"Description."
			::= { sleEponProfileUNIQueue 1 }

		
		sleEponProfileUNIQueueEntry OBJECT-TYPE
			SYNTAX SleEponProfileUNIQueueEntry
			MAX-ACCESS not-accessible
			STATUS current
			DESCRIPTION
				"Description."
			INDEX { sleEponProfileIndex }
			::= { sleEponProfileUNIQueueTable 1 }

		
		SleEponProfileUNIQueueEntry ::=
			SEQUENCE { 
				sleEponProfileUNIQueueUpMaxBandwidth
					INTEGER,
				sleEponProfileUNIQueueUpMaxBurstSize
					INTEGER,
				sleEponProfileUNIQueueDownMaxBandwidth
					INTEGER,
				sleEponProfileUNIQueueDownMaxBurstSize
					INTEGER
			 }

		sleEponProfileUNIQueueUpMaxBandwidth OBJECT-TYPE
			SYNTAX INTEGER (100..1000000)
			UNITS "kbps"
			MAX-ACCESS read-only
			STATUS current
			DESCRIPTION
				"Description."
			::= { sleEponProfileUNIQueueEntry 1 }

		
		sleEponProfileUNIQueueUpMaxBurstSize OBJECT-TYPE
			SYNTAX INTEGER (128..16777214)
			UNITS "byte"
			MAX-ACCESS read-only
			STATUS current
			DESCRIPTION
				"Description."
			::= { sleEponProfileUNIQueueEntry 2 }

		
		sleEponProfileUNIQueueDownMaxBandwidth OBJECT-TYPE
			SYNTAX INTEGER (100..1000000)
			UNITS "kbps"
			MAX-ACCESS read-only
			STATUS current
			DESCRIPTION
				"Description."
			::= { sleEponProfileUNIQueueEntry 3 }

		
		sleEponProfileUNIQueueDownMaxBurstSize OBJECT-TYPE
			SYNTAX INTEGER (128..16777214)
			MAX-ACCESS read-only
			STATUS current
			DESCRIPTION
				"Description."
			::= { sleEponProfileUNIQueueEntry 4 }

		
		sleEponProfileUNIQueueControl OBJECT IDENTIFIER ::= { sleEponProfileUNIQueue 2 }

		
		sleEponProfileUNIQueueControlRequest OBJECT-TYPE
			SYNTAX INTEGER
				{
				modifyProfileUNIQuuePolicyUp(1),
				modifyProfileUNIQuuePolicyDown(2)
				}
			MAX-ACCESS read-write
			STATUS current
			DESCRIPTION
				"Description."
			::= { sleEponProfileUNIQueueControl 1 }

		
		sleEponProfileUNIQueueControlStatus OBJECT-TYPE
			SYNTAX SleControlStatusType
			MAX-ACCESS read-only
			STATUS current
			DESCRIPTION
				"Description."
			::= { sleEponProfileUNIQueueControl 2 }

		
		sleEponProfileUNIQueueControlTimer OBJECT-TYPE
			SYNTAX Gauge32
			MAX-ACCESS read-write
			STATUS current
			DESCRIPTION
				"Description."
			::= { sleEponProfileUNIQueueControl 3 }

		
		sleEponProfileUNIQueueControlTimeStamp OBJECT-TYPE
			SYNTAX TimeTicks
			MAX-ACCESS read-only
			STATUS current
			DESCRIPTION
				"Description."
			::= { sleEponProfileUNIQueueControl 4 }

		
		sleEponProfileUNIQueueControlReqResult OBJECT-TYPE
			SYNTAX SleControlRequestResultType
			MAX-ACCESS read-only
			STATUS current
			DESCRIPTION
				"Description."
			::= { sleEponProfileUNIQueueControl 5 }

		
		sleEponProfileUNIQueueControlProfileIndex OBJECT-TYPE
			SYNTAX INTEGER (1..32)
			MAX-ACCESS read-write
			STATUS current
			DESCRIPTION
				"Description."
			::= { sleEponProfileUNIQueueControl 6 }

		
		sleEponProfileUNIQueueControlUpMaxBandwidth OBJECT-TYPE
			SYNTAX INTEGER (0 | 100..1000000)
			UNITS "kbps"
			MAX-ACCESS read-write
			STATUS current
			DESCRIPTION
				"Description."
			::= { sleEponProfileUNIQueueControl 7 }

		
		sleEponProfileUNIQueueControlUpMaxBurstSize OBJECT-TYPE
			SYNTAX INTEGER (0 | 128..16777214)
			UNITS "byte"
			MAX-ACCESS read-write
			STATUS current
			DESCRIPTION
				"Description."
			::= { sleEponProfileUNIQueueControl 8 }

		
		sleEponProfileUNIQueueControlDownMaxBandwidth OBJECT-TYPE
			SYNTAX INTEGER (0 | 100..1000000)
			UNITS "kbps"
			MAX-ACCESS read-write
			STATUS current
			DESCRIPTION
				"Description."
			::= { sleEponProfileUNIQueueControl 9 }

		
		sleEponProfileUNIQueueControlDownMaxBurstSize OBJECT-TYPE
			SYNTAX INTEGER (0 | 128..16777214)
			UNITS "byte"
			MAX-ACCESS read-write
			STATUS current
			DESCRIPTION
				"Description."
			::= { sleEponProfileUNIQueueControl 10 }

		
		sleEponProfileUNIQueueNotification OBJECT IDENTIFIER ::= { sleEponProfileUNIQueue 3 }

		
		sleEponProfileUNIQueueModifyQueuePolicy NOTIFICATION-TYPE
			OBJECTS { sleEponProfileUNIQueueControlRequest, sleEponProfileUNIQueueControlTimeStamp, sleEponProfileUNIQueueControlReqResult, sleEponProfileUNIQueueControlProfileIndex }
			STATUS current
			DESCRIPTION 
				"Description."
			::= { sleEponProfileUNIQueueNotification 1 }

		
		sleEponProfileOltService OBJECT IDENTIFIER ::= { sleEponProfile 7 }

		
		sleEponProfileOltServiceTable OBJECT-TYPE
			SYNTAX SEQUENCE OF SleEponProfileOltServiceEntry
			MAX-ACCESS not-accessible
			STATUS current
			DESCRIPTION
				"Description."
			::= { sleEponProfileOltService 1 }

		
		sleEponProfileOltServiceEntry OBJECT-TYPE
			SYNTAX SleEponProfileOltServiceEntry
			MAX-ACCESS not-accessible
			STATUS current
			DESCRIPTION
				"Description."
			INDEX { sleEponProfileOltServiceProfileName, sleEponProfileOltServiceModelName }
			::= { sleEponProfileOltServiceTable 1 }

		
		SleEponProfileOltServiceEntry ::=
			SEQUENCE { 
				sleEponProfileOltServiceProfileName
					OCTET STRING,
				sleEponProfileOltServiceModelName
					OCTET STRING
			 }

		sleEponProfileOltServiceProfileName OBJECT-TYPE
			SYNTAX OCTET STRING
			MAX-ACCESS read-only
			STATUS current
			DESCRIPTION
				"Description."
			::= { sleEponProfileOltServiceEntry 2 }

		
		sleEponProfileOltServiceModelName OBJECT-TYPE
			SYNTAX OCTET STRING
			MAX-ACCESS read-only
			STATUS current
			DESCRIPTION
				"Description."
			::= { sleEponProfileOltServiceEntry 3 }

		
		sleEponProfileOltServiceControl OBJECT IDENTIFIER ::= { sleEponProfileOltService 2 }

		
		sleEponProfileOltServiceRequest OBJECT-TYPE
			SYNTAX INTEGER
				{
				applyProfileOltServiceDefaule(1),
				applyProfileOltServiceModel(2),
				noapplyProfileOltServiceDefault(3),
				noapplyProfileOltServiceModel(4),
				noApplyProfileOltService(5)
				}
			MAX-ACCESS read-write
			STATUS current
			DESCRIPTION
				"Description."
			::= { sleEponProfileOltServiceControl 1 }

		
		sleEponProfileOltServiceStatus OBJECT-TYPE
			SYNTAX SleControlStatusType
			MAX-ACCESS read-only
			STATUS current
			DESCRIPTION
				"Description."
			::= { sleEponProfileOltServiceControl 2 }

		
		sleEponProfileOltServiceTimer OBJECT-TYPE
			SYNTAX Gauge32
			MAX-ACCESS read-write
			STATUS current
			DESCRIPTION
				"Description."
			::= { sleEponProfileOltServiceControl 3 }

		
		sleEponProfileOltServiceTimerStamp OBJECT-TYPE
			SYNTAX TimeTicks
			MAX-ACCESS read-only
			STATUS current
			DESCRIPTION
				"Description."
			::= { sleEponProfileOltServiceControl 4 }

		
		sleEponProfileOltServiceReqResult OBJECT-TYPE
			SYNTAX SleControlRequestResultType
			MAX-ACCESS read-only
			STATUS current
			DESCRIPTION
				"Description."
			::= { sleEponProfileOltServiceControl 5 }

		
		sleEponProfileOltServiceOnuModelName OBJECT-TYPE
			SYNTAX OCTET STRING
			MAX-ACCESS read-write
			STATUS current
			DESCRIPTION
				"Description."
			::= { sleEponProfileOltServiceControl 6 }

		
		sleEponProfileOltServiceOnuProfileName OBJECT-TYPE
			SYNTAX OCTET STRING
			MAX-ACCESS read-write
			STATUS current
			DESCRIPTION
				"Description."
			::= { sleEponProfileOltServiceControl 7 }

		
		sleEponProfileOltServiceNotification OBJECT IDENTIFIER ::= { sleEponProfileOltService 3 }

		
		sleEponProfileOltServiceDefaultChanged NOTIFICATION-TYPE
			STATUS current
			DESCRIPTION 
				"Description."
			::= { sleEponProfileOltServiceNotification 1 }

		
		sleEponProfileOltServiceModelChanged NOTIFICATION-TYPE
			STATUS current
			DESCRIPTION 
				"Description."
			::= { sleEponProfileOltServiceNotification 2 }

		
		sleEponAlarm OBJECT IDENTIFIER ::= { sleEpon 6 }

		
		sleEponAlarmTable OBJECT-TYPE
			SYNTAX SEQUENCE OF SleEponAlarmEntry
			MAX-ACCESS not-accessible
			STATUS current
			DESCRIPTION
				"Description."
			::= { sleEponAlarm 1 }

		
		sleEponAlarmEntry OBJECT-TYPE
			SYNTAX SleEponAlarmEntry
			MAX-ACCESS not-accessible
			STATUS current
			DESCRIPTION
				"Description."
			INDEX { sleEponOltIndex }
			::= { sleEponAlarmTable 1 }

		
		SleEponAlarmEntry ::=
			SEQUENCE { 
				sleEponAlarmBadEncryption
					EnableFlag,
				sleEponAlarmDyingGasp
					EnableFlag,
				sleEponAlarmLlidMismatch
					EnableFlag,
				sleEponAlarmOnuRegistrationError
					EnableFlag,
				sleEponAlarmTooManyOnuRegistration
					EnableFlag,
				sleEponAlarmOpticSignalError
					EnableFlag,
				sleEponAlarmStandardLinkFault
					EnableFlag,
				sleEponAlarmLossOfSignal
					EnableFlag,
				sleEponAlarmTransmitFail
					EnableFlag,
				sleEponAlarmMacLearningOverflow
					EnableFlag,
				sleEponAlarmLoopback
					EnableFlag,
				sleEponAlarmStandardDyingGasp
					EnableFlag,
				sleEponAlarmExternalDyingGasp
					EnableFlag,
				sleEponAlarmStandardCriticalEvent
					EnableFlag,
				sleEponAlarmExternalCriticalEvent
					EnableFlag,
				sleEponAlarmEponStandbyLos
					EnableFlag,
				sleEponAlarmOpitcalPower
					EnableFlag,
				sleEponAlarmOverVoltage
					EnableFlag
			 }

		sleEponAlarmBadEncryption OBJECT-TYPE
			SYNTAX EnableFlag
			MAX-ACCESS read-only
			STATUS current
			DESCRIPTION
				"alarm type: Bad encryption"
			DEFVAL { enable }
			::= { sleEponAlarmEntry 1 }

		
		sleEponAlarmDyingGasp OBJECT-TYPE
			SYNTAX EnableFlag
			MAX-ACCESS read-only
			STATUS current
			DESCRIPTION
				"alarm type: Dying gasp"
			DEFVAL { enable }
			::= { sleEponAlarmEntry 2 }

		
		sleEponAlarmLlidMismatch OBJECT-TYPE
			SYNTAX EnableFlag
			MAX-ACCESS read-only
			STATUS current
			DESCRIPTION
				"alarm type: llid mismatch"
			DEFVAL { enable }
			::= { sleEponAlarmEntry 3 }

		
		sleEponAlarmOnuRegistrationError OBJECT-TYPE
			SYNTAX EnableFlag
			MAX-ACCESS read-only
			STATUS current
			DESCRIPTION
				"alarm type: onu registration error"
			DEFVAL { enable }
			::= { sleEponAlarmEntry 4 }

		
		sleEponAlarmTooManyOnuRegistration OBJECT-TYPE
			SYNTAX EnableFlag
			MAX-ACCESS read-only
			STATUS current
			DESCRIPTION
				"alarm type: too many onu registration"
			DEFVAL { enable }
			::= { sleEponAlarmEntry 5 }

		
		sleEponAlarmOpticSignalError OBJECT-TYPE
			SYNTAX EnableFlag
			MAX-ACCESS read-only
			STATUS current
			DESCRIPTION
				"alarm type: onu optical signal error"
			DEFVAL { enable }
			::= { sleEponAlarmEntry 6 }

		
		sleEponAlarmStandardLinkFault OBJECT-TYPE
			SYNTAX EnableFlag
			MAX-ACCESS read-only
			STATUS current
			DESCRIPTION
				"alarm type: link falult"
			DEFVAL { enable }
			::= { sleEponAlarmEntry 7 }

		
		sleEponAlarmLossOfSignal OBJECT-TYPE
			SYNTAX EnableFlag
			MAX-ACCESS read-only
			STATUS current
			DESCRIPTION
				"alarm type:loss of signal."
			DEFVAL { enable }
			::= { sleEponAlarmEntry 8 }

		
		sleEponAlarmTransmitFail OBJECT-TYPE
			SYNTAX EnableFlag
			MAX-ACCESS read-only
			STATUS current
			DESCRIPTION
				"alarm type: transmit fail."
			DEFVAL { enable }
			::= { sleEponAlarmEntry 9 }

		
		sleEponAlarmMacLearningOverflow OBJECT-TYPE
			SYNTAX EnableFlag
			MAX-ACCESS read-only
			STATUS current
			DESCRIPTION
				"alarm type: mac learning overflow."
			DEFVAL { enable }
			::= { sleEponAlarmEntry 10 }

		
		sleEponAlarmLoopback OBJECT-TYPE
			SYNTAX EnableFlag
			MAX-ACCESS read-write
			STATUS current
			DESCRIPTION
				"alarm type: loopback."
			DEFVAL { enable }
			::= { sleEponAlarmEntry 11 }

		
		sleEponAlarmStandardDyingGasp OBJECT-TYPE
			SYNTAX EnableFlag
			MAX-ACCESS read-only
			STATUS current
			DESCRIPTION
				"alarm type:standard dying gasp."
			DEFVAL { enable }
			::= { sleEponAlarmEntry 12 }

		
		sleEponAlarmExternalDyingGasp OBJECT-TYPE
			SYNTAX EnableFlag
			MAX-ACCESS read-only
			STATUS current
			DESCRIPTION
				"alarm type :external dying gasp."
			DEFVAL { enable }
			::= { sleEponAlarmEntry 13 }

		
		sleEponAlarmStandardCriticalEvent OBJECT-TYPE
			SYNTAX EnableFlag
			MAX-ACCESS read-only
			STATUS current
			DESCRIPTION
				"alarm type:standard critical event.
				"
			DEFVAL { enable }
			::= { sleEponAlarmEntry 14 }

		
		sleEponAlarmExternalCriticalEvent OBJECT-TYPE
			SYNTAX EnableFlag
			MAX-ACCESS read-only
			STATUS current
			DESCRIPTION
				"alarm type:external critical event."
			DEFVAL { enable }
			::= { sleEponAlarmEntry 15 }

		
		sleEponAlarmEponStandbyLos OBJECT-TYPE
			SYNTAX EnableFlag
			MAX-ACCESS read-only
			STATUS current
			DESCRIPTION
				"alarm type: epon standby lose."
			DEFVAL { enable }
			::= { sleEponAlarmEntry 16 }

		
		sleEponAlarmOpitcalPower OBJECT-TYPE
			SYNTAX EnableFlag
			MAX-ACCESS read-only
			STATUS current
			DESCRIPTION
				"Description."
			DEFVAL { enable }
			::= { sleEponAlarmEntry 17 }

		
		sleEponAlarmOverVoltage OBJECT-TYPE
			SYNTAX EnableFlag
			MAX-ACCESS read-only
			STATUS current
			DESCRIPTION
				"Description."
			DEFVAL { enable }
			::= { sleEponAlarmEntry 18 }

		
		sleEponAlarmControl OBJECT IDENTIFIER ::= { sleEponAlarm 2 }

		
		sleEponAlarmControlRequest OBJECT-TYPE
			SYNTAX INTEGER
				{
				setEponAlarmProfile(1),
				setEponAlarm(2)
				}
			MAX-ACCESS read-write
			STATUS current
			DESCRIPTION
				"The request of a user command"
			::= { sleEponAlarmControl 1 }

		
		sleEponAlarmControlStatus OBJECT-TYPE
			SYNTAX SleControlStatusType
			MAX-ACCESS read-only
			STATUS current
			DESCRIPTION
				"The status of user command"
			::= { sleEponAlarmControl 2 }

		
		sleEponAlarmControlTimer OBJECT-TYPE
			SYNTAX Gauge32
			MAX-ACCESS read-write
			STATUS current
			DESCRIPTION
				"The maximum time for the manager for a long running user command"
			::= { sleEponAlarmControl 3 }

		
		sleEponAlarmControlTimeStamp OBJECT-TYPE
			SYNTAX TimeTicks
			MAX-ACCESS read-only
			STATUS current
			DESCRIPTION
				"The time stamp of the last command(end of command)"
			::= { sleEponAlarmControl 4 }

		
		sleEponAlarmControlReqResult OBJECT-TYPE
			SYNTAX SleControlRequestResultType
			MAX-ACCESS read-only
			STATUS current
			DESCRIPTION
				"The result of the last user command"
			::= { sleEponAlarmControl 5 }

		
		sleEponAlarmControlOltIndex OBJECT-TYPE
			SYNTAX Integer32
			MAX-ACCESS read-write
			STATUS current
			DESCRIPTION
				"OLT index"
			::= { sleEponAlarmControl 6 }

		
		sleEponAlarmControlBadEncryption OBJECT-TYPE
			SYNTAX EnableFlag
			MAX-ACCESS read-write
			STATUS current
			DESCRIPTION
				"disable(1), enable(2)"
			DEFVAL { enable }
			::= { sleEponAlarmControl 7 }

		
		sleEponAlarmControlDyingGasp OBJECT-TYPE
			SYNTAX EnableFlag
			MAX-ACCESS read-write
			STATUS current
			DESCRIPTION
				"disable(1), enable(2)"
			DEFVAL { enable }
			::= { sleEponAlarmControl 8 }

		
		sleEponAlarmControlLlidMismatch OBJECT-TYPE
			SYNTAX EnableFlag
			MAX-ACCESS read-write
			STATUS current
			DESCRIPTION
				"disable(1), enable(2)"
			DEFVAL { enable }
			::= { sleEponAlarmControl 9 }

		
		sleEponAlarmControlOnuRegistrationError OBJECT-TYPE
			SYNTAX EnableFlag
			MAX-ACCESS read-write
			STATUS current
			DESCRIPTION
				"disable(1), enable(2)"
			DEFVAL { enable }
			::= { sleEponAlarmControl 10 }

		
		sleEponAlarmControlTooManyOnuRegistration OBJECT-TYPE
			SYNTAX EnableFlag
			MAX-ACCESS read-write
			STATUS current
			DESCRIPTION
				"disable(1), enable(2)"
			DEFVAL { enable }
			::= { sleEponAlarmControl 11 }

		
		sleEponAlarmControlOpticSignalError OBJECT-TYPE
			SYNTAX EnableFlag
			MAX-ACCESS read-write
			STATUS current
			DESCRIPTION
				"disable(1), enable(2)"
			DEFVAL { enable }
			::= { sleEponAlarmControl 12 }

		
		sleEponAlarmControlStandardLinkFault OBJECT-TYPE
			SYNTAX EnableFlag
			MAX-ACCESS read-write
			STATUS current
			DESCRIPTION
				"disable(1), enable(2)"
			DEFVAL { enable }
			::= { sleEponAlarmControl 13 }

		
		sleEponAlarmControlLossOfSignal OBJECT-TYPE
			SYNTAX EnableFlag
			MAX-ACCESS read-write
			STATUS current
			DESCRIPTION
				"disable(1), enable(2)"
			DEFVAL { enable }
			::= { sleEponAlarmControl 14 }

		
		sleEponAlarmControlTransmitFail OBJECT-TYPE
			SYNTAX EnableFlag
			MAX-ACCESS read-write
			STATUS current
			DESCRIPTION
				"disable(1), enable(2)"
			DEFVAL { enable }
			::= { sleEponAlarmControl 15 }

		
		sleEponAlarmControlMacLearningOverflow OBJECT-TYPE
			SYNTAX EnableFlag
			MAX-ACCESS read-write
			STATUS current
			DESCRIPTION
				"disable(1), enable(2)"
			DEFVAL { enable }
			::= { sleEponAlarmControl 16 }

		
		sleEponAlarmControlLoopback OBJECT-TYPE
			SYNTAX EnableFlag
			MAX-ACCESS read-write
			STATUS current
			DESCRIPTION
				"disable(1), enable(2)"
			DEFVAL { enable }
			::= { sleEponAlarmControl 17 }

		
		sleEponAlarmControlStandardDyingGasp OBJECT-TYPE
			SYNTAX EnableFlag
			MAX-ACCESS read-write
			STATUS current
			DESCRIPTION
				"disable(1), enable(2)"
			DEFVAL { enable }
			::= { sleEponAlarmControl 18 }

		
		sleEponAlarmControlExternalDyingGasp OBJECT-TYPE
			SYNTAX EnableFlag
			MAX-ACCESS read-write
			STATUS current
			DESCRIPTION
				"disable(1), enable(2)"
			DEFVAL { enable }
			::= { sleEponAlarmControl 19 }

		
		sleEponAlarmControlStandardCriticalevent OBJECT-TYPE
			SYNTAX EnableFlag
			MAX-ACCESS read-write
			STATUS current
			DESCRIPTION
				"disable(1), enable(2)"
			DEFVAL { enable }
			::= { sleEponAlarmControl 20 }

		
		sleEponAlarmControlExternalCriticalEvent OBJECT-TYPE
			SYNTAX EnableFlag
			MAX-ACCESS read-write
			STATUS current
			DESCRIPTION
				"disable(1), enable(2)"
			DEFVAL { enable }
			::= { sleEponAlarmControl 21 }

		
		sleEponAlarmControlEponStandbyLos OBJECT-TYPE
			SYNTAX EnableFlag
			MAX-ACCESS read-write
			STATUS current
			DESCRIPTION
				"disable(1), enable(2)"
			DEFVAL { enable }
			::= { sleEponAlarmControl 22 }

		
		sleEponAlarmControlOpticalPower OBJECT-TYPE
			SYNTAX EnableFlag
			MAX-ACCESS read-write
			STATUS current
			DESCRIPTION
				"Description."
			DEFVAL { enable }
			::= { sleEponAlarmControl 23 }

		
		sleEponAlarmControlOverVoltage OBJECT-TYPE
			SYNTAX EnableFlag
			MAX-ACCESS read-write
			STATUS current
			DESCRIPTION
				"Description."
			DEFVAL { enable }
			::= { sleEponAlarmControl 24 }

		
		sleEponAlarmNotification OBJECT IDENTIFIER ::= { sleEponAlarm 3 }

		
		sleEponAlarmProfileChanged NOTIFICATION-TYPE
			OBJECTS { sleEponAlarmControlRequest, sleEponAlarmControlTimeStamp, sleEponAlarmControlReqResult, sleEponAlarmControlOltIndex }
			STATUS current
			DESCRIPTION 
				"alarm profile changed trap"
			::= { sleEponAlarmNotification 1 }

		
		sleEponAlarmChanged NOTIFICATION-TYPE
			OBJECTS { sleEponAlarmControlRequest, sleEponAlarmControlTimeStamp, sleEponAlarmControlReqResult }
			STATUS current
			DESCRIPTION 
				"alarm changed trap"
			::= { sleEponAlarmNotification 2 }

		
		sleEponStatistics OBJECT IDENTIFIER ::= { sleEpon 7 }

		
		sleEponOltStatistics OBJECT IDENTIFIER ::= { sleEponStatistics 1 }

		
		sleEponStatsOltTable OBJECT-TYPE
			SYNTAX SEQUENCE OF SleEponStatsOltEntry
			MAX-ACCESS not-accessible
			STATUS current
			DESCRIPTION
				"Description."
			::= { sleEponOltStatistics 1 }

		
		sleEponStatsOltEntry OBJECT-TYPE
			SYNTAX SleEponStatsOltEntry
			MAX-ACCESS not-accessible
			STATUS current
			DESCRIPTION
				"Description."
			INDEX { sleEponOltIndex }
			::= { sleEponStatsOltTable 1 }

		
		SleEponStatsOltEntry ::=
			SEQUENCE { 
				sleEponStatsOltInOctets
					Counter64,
				sleEponStatsOltInPkts
					Counter32,
				sleEponStatsOltInPause
					Counter32,
				sleEponStatsOltInErroredFrame
					Counter32,
				sleEponStatsOltInUnicastPkts
					Counter32,
				sleEponstatsOltInBroadcastPkts
					Counter32,
				sleEponStatsOltInMulticastPkts
					Counter32,
				sleEponStatsOltOutOctets
					Counter64,
				sleEponStatsOltOutPkts
					Counter32,
				sleEponStatsOltOutPause
					Counter32,
				sleEponStatsOltOutDropped
					Counter32,
				sleEponStatsOltOutUnicastPkts
					Counter32,
				sleEponstatsOltOutBroadcastPkts
					Counter32,
				sleEponStatsOltOutMulticastPkts
					Counter32,
				sleEponStatsOltHostFrame
					Counter32,
				sleEponStatsOltInTooLongFrame
					Counter32,
				sleEponStatsOltHostFrameDropped
					Counter32,
				sleEponStatsOltTxOkBytes64
					Counter64,
				sleEponStatsOltTxOkFrames64
					Counter64,
				sleEponStatsOltTxUniFrames64
					Counter64,
				sleEponStatsOltTxMulFrames64
					Counter64,
				sleEponStatsOltTxBroFrames64
					Counter64,
				sleEponStatsOltRxOkBytes64
					Counter64,
				sleEponStatsOltRxOkFrames64
					Counter64,
				sleEponStatsOltRxUniFrames64
					Counter64,
				sleEponStatsOltRxMulFrames64
					Counter64,
				sleEponStatsOltRxBroFrames64
					Counter64,
				sleEponStatsOltRxUnderSizeFrames64
					Counter64,
				sleEponStatsOltRxOverSizeFrames64
					Counter64
			 }

		sleEponStatsOltInOctets OBJECT-TYPE
			SYNTAX Counter64
			MAX-ACCESS read-only
			STATUS current
			DESCRIPTION
				"The total number of octets received on the switch side"
			::= { sleEponStatsOltEntry 1 }

		
		sleEponStatsOltInPkts OBJECT-TYPE
			SYNTAX Counter32
			MAX-ACCESS read-only
			STATUS current
			DESCRIPTION
				"The total number of packets received on the switch side"
			::= { sleEponStatsOltEntry 2 }

		
		sleEponStatsOltInPause OBJECT-TYPE
			SYNTAX Counter32
			MAX-ACCESS read-only
			STATUS current
			DESCRIPTION
				"The total number of paused packet received on the switch side"
			::= { sleEponStatsOltEntry 3 }

		
		sleEponStatsOltInErroredFrame OBJECT-TYPE
			SYNTAX Counter32
			MAX-ACCESS read-only
			STATUS current
			DESCRIPTION
				"The total number of errored frame received on the switch side"
			::= { sleEponStatsOltEntry 4 }

		
		sleEponStatsOltInUnicastPkts OBJECT-TYPE
			SYNTAX Counter32
			MAX-ACCESS read-only
			STATUS current
			DESCRIPTION
				"The total number of unicast packets received on the switch side"
			::= { sleEponStatsOltEntry 5 }

		
		sleEponstatsOltInBroadcastPkts OBJECT-TYPE
			SYNTAX Counter32
			MAX-ACCESS read-only
			STATUS current
			DESCRIPTION
				"The total number of broadcast packets received on the switch side"
			::= { sleEponStatsOltEntry 6 }

		
		sleEponStatsOltInMulticastPkts OBJECT-TYPE
			SYNTAX Counter32
			MAX-ACCESS read-only
			STATUS current
			DESCRIPTION
				"The total number of multicast packets received on the switch side"
			::= { sleEponStatsOltEntry 7 }

		
		sleEponStatsOltOutOctets OBJECT-TYPE
			SYNTAX Counter64
			MAX-ACCESS read-only
			STATUS current
			DESCRIPTION
				"The total number of octets transmitted out of the switch side"
			::= { sleEponStatsOltEntry 8 }

		
		sleEponStatsOltOutPkts OBJECT-TYPE
			SYNTAX Counter32
			MAX-ACCESS read-only
			STATUS current
			DESCRIPTION
				"The total number of packets transmitted out of the switch side"
			::= { sleEponStatsOltEntry 9 }

		
		sleEponStatsOltOutPause OBJECT-TYPE
			SYNTAX Counter32
			MAX-ACCESS read-only
			STATUS current
			DESCRIPTION
				"The total number of paused packets transmitted out of the switch side"
			::= { sleEponStatsOltEntry 10 }

		
		sleEponStatsOltOutDropped OBJECT-TYPE
			SYNTAX Counter32
			MAX-ACCESS read-only
			STATUS current
			DESCRIPTION
				"The total number of droped packets transmitted out of the switch side"
			::= { sleEponStatsOltEntry 11 }

		
		sleEponStatsOltOutUnicastPkts OBJECT-TYPE
			SYNTAX Counter32
			MAX-ACCESS read-only
			STATUS current
			DESCRIPTION
				"The total number of unicast packets transmitted out of the switch side"
			::= { sleEponStatsOltEntry 12 }

		
		sleEponstatsOltOutBroadcastPkts OBJECT-TYPE
			SYNTAX Counter32
			MAX-ACCESS read-only
			STATUS current
			DESCRIPTION
				"The total number of broadcast packets transmitted out of the switch side"
			::= { sleEponStatsOltEntry 13 }

		
		sleEponStatsOltOutMulticastPkts OBJECT-TYPE
			SYNTAX Counter32
			MAX-ACCESS read-only
			STATUS current
			DESCRIPTION
				"The total number of multicast packets transmitted out of the switch side"
			::= { sleEponStatsOltEntry 14 }

		
		sleEponStatsOltHostFrame OBJECT-TYPE
			SYNTAX Counter32
			MAX-ACCESS read-only
			STATUS current
			DESCRIPTION
				"The total number of host frame received on the switch side."
			::= { sleEponStatsOltEntry 15 }

		
		sleEponStatsOltInTooLongFrame OBJECT-TYPE
			SYNTAX Counter32
			MAX-ACCESS read-only
			STATUS current
			DESCRIPTION
				"The total number of too long frame received on the switch side."
			::= { sleEponStatsOltEntry 16 }

		
		sleEponStatsOltHostFrameDropped OBJECT-TYPE
			SYNTAX Counter32
			MAX-ACCESS read-write
			STATUS current
			DESCRIPTION
				"The total number of droped frame transmitted out of the switch side."
			::= { sleEponStatsOltEntry 17 }

		
		sleEponStatsOltTxOkBytes64 OBJECT-TYPE
			SYNTAX Counter64
			MAX-ACCESS read-only
			STATUS current
			DESCRIPTION
				" "
			::= { sleEponStatsOltEntry 18 }

		
		sleEponStatsOltTxOkFrames64 OBJECT-TYPE
			SYNTAX Counter64
			MAX-ACCESS read-only
			STATUS current
			DESCRIPTION
				" "
			::= { sleEponStatsOltEntry 19 }

		
		sleEponStatsOltTxUniFrames64 OBJECT-TYPE
			SYNTAX Counter64
			MAX-ACCESS read-only
			STATUS current
			DESCRIPTION
				" "
			::= { sleEponStatsOltEntry 20 }

		
		sleEponStatsOltTxMulFrames64 OBJECT-TYPE
			SYNTAX Counter64
			MAX-ACCESS read-only
			STATUS current
			DESCRIPTION
				" "
			::= { sleEponStatsOltEntry 21 }

		
		sleEponStatsOltTxBroFrames64 OBJECT-TYPE
			SYNTAX Counter64
			MAX-ACCESS read-only
			STATUS current
			DESCRIPTION
				" "
			::= { sleEponStatsOltEntry 22 }

		
		sleEponStatsOltRxOkBytes64 OBJECT-TYPE
			SYNTAX Counter64
			MAX-ACCESS read-only
			STATUS current
			DESCRIPTION
				" "
			::= { sleEponStatsOltEntry 23 }

		
		sleEponStatsOltRxOkFrames64 OBJECT-TYPE
			SYNTAX Counter64
			MAX-ACCESS read-only
			STATUS current
			DESCRIPTION
				" "
			::= { sleEponStatsOltEntry 24 }

		
		sleEponStatsOltRxUniFrames64 OBJECT-TYPE
			SYNTAX Counter64
			MAX-ACCESS read-only
			STATUS current
			DESCRIPTION
				" "
			::= { sleEponStatsOltEntry 25 }

		
		sleEponStatsOltRxMulFrames64 OBJECT-TYPE
			SYNTAX Counter64
			MAX-ACCESS read-only
			STATUS current
			DESCRIPTION
				" "
			::= { sleEponStatsOltEntry 26 }

		
		sleEponStatsOltRxBroFrames64 OBJECT-TYPE
			SYNTAX Counter64
			MAX-ACCESS read-only
			STATUS current
			DESCRIPTION
				" "
			::= { sleEponStatsOltEntry 27 }

		
		sleEponStatsOltRxUnderSizeFrames64 OBJECT-TYPE
			SYNTAX Counter64
			MAX-ACCESS read-only
			STATUS current
			DESCRIPTION
				" "
			::= { sleEponStatsOltEntry 28 }

		
		sleEponStatsOltRxOverSizeFrames64 OBJECT-TYPE
			SYNTAX Counter64
			MAX-ACCESS read-only
			STATUS current
			DESCRIPTION
				" "
			::= { sleEponStatsOltEntry 29 }

		
		sleEponStatsOltPonTable OBJECT-TYPE
			SYNTAX SEQUENCE OF SleEponStatsOltPonEntry
			MAX-ACCESS not-accessible
			STATUS current
			DESCRIPTION
				"Description."
			::= { sleEponOltStatistics 2 }

		
		sleEponStatsOltPonEntry OBJECT-TYPE
			SYNTAX SleEponStatsOltPonEntry
			MAX-ACCESS not-accessible
			STATUS current
			DESCRIPTION
				"Description."
			INDEX { sleEponOltIndex }
			::= { sleEponStatsOltPonTable 1 }

		
		SleEponStatsOltPonEntry ::=
			SEQUENCE { 
				sleEponStatsOltPonInOctets
					Counter64,
				sleEponStatsOltPonInPkts
					Counter32,
				sleEponStatsOltPonInPause
					Counter32,
				sleEponStatsOltPonInErroredFrame
					Counter32,
				sleEponStatsOltPonInUnicastPkts
					Counter32,
				sleEponstatsOltPonInBroadcastPkts
					Counter32,
				sleEponStatsOltPonInMulticastPkts
					Counter32,
				sleEponStatsOltPonOutOctets
					Counter64,
				sleEponStatsOltPonOutPkts
					Counter32,
				sleEponStatsOltPonOutPause
					Counter32,
				sleEponStatsOltPonOutDropped
					Counter32,
				sleEponStatsOltPonOutUnicastPkts
					Counter32,
				sleEponstatsOltPonOutBroadcastPkts
					Counter32,
				sleEponStatsOltPonOutMulticastPkts
					Counter32,
				sleEponStatsOltPonInHostFrame
					Counter32,
				sleEponStatsOltPonInTooLongFrame
					Counter32,
				sleEponStatsOltPonInHostFrameDropped
					Counter32,
				sleEponStatsOltPonInHECErrorFrame
					Counter32,
				sleEponStatsOltPonTxOkBytes64
					Counter64,
				sleEponStatsOltPonTxOkFrames64
					Counter64,
				sleEponStatsOltPonTxUniFrames64
					Counter64,
				sleEponStatsOltPonTxMulFrames64
					Counter64,
				sleEponStatsOltPonTxBroFrames64
					Counter64,
				sleEponStatsOltPonTxCrcGen64
					Counter64,
				sleEponStatsOltPonTxPauseFrames64
					Counter64,
				sleEponStatsOltPonTxErrBytes64
					Counter64,
				sleEponStatsOltPonRxOkBytes64
					Counter64,
				sleEponStatsOltPonRxOkFrames64
					Counter64,
				sleEponStatsOltPonRxUniFrames64
					Counter64,
				sleEponStatsOltPonRxMulFrames64
					Counter64,
				sleEponStatsOltPonRxBroFrames64
					Counter64,
				sleEponStatsOltPonRxUndersizeFrames64
					Counter64,
				sleEponStatsOltPonRxOverSizeFrames64
					Counter64,
				sleEponStatsOltPonRxPauseFrames64
					Counter64,
				sleEponStatsOltPonRxAlignErrFrames64
					Counter64,
				sleEponStatsOltPonRxErrBytes64
					Counter64,
				sleEponStatsOltPonRxCodeErr64
					Counter64
			 }

		sleEponStatsOltPonInOctets OBJECT-TYPE
			SYNTAX Counter64
			MAX-ACCESS read-only
			STATUS current
			DESCRIPTION
				"The total number of octets received on the OLT side"
			::= { sleEponStatsOltPonEntry 1 }

		
		sleEponStatsOltPonInPkts OBJECT-TYPE
			SYNTAX Counter32
			MAX-ACCESS read-only
			STATUS current
			DESCRIPTION
				"The total number of packets received on the OLT side"
			::= { sleEponStatsOltPonEntry 2 }

		
		sleEponStatsOltPonInPause OBJECT-TYPE
			SYNTAX Counter32
			MAX-ACCESS read-only
			STATUS current
			DESCRIPTION
				"The total number of paused packet received on the OLT side"
			::= { sleEponStatsOltPonEntry 3 }

		
		sleEponStatsOltPonInErroredFrame OBJECT-TYPE
			SYNTAX Counter32
			MAX-ACCESS read-only
			STATUS current
			DESCRIPTION
				"The total number of errored frame received on the OLT side"
			::= { sleEponStatsOltPonEntry 4 }

		
		sleEponStatsOltPonInUnicastPkts OBJECT-TYPE
			SYNTAX Counter32
			MAX-ACCESS read-only
			STATUS current
			DESCRIPTION
				"The total number of unicast packets received on the OLT side"
			::= { sleEponStatsOltPonEntry 5 }

		
		sleEponstatsOltPonInBroadcastPkts OBJECT-TYPE
			SYNTAX Counter32
			MAX-ACCESS read-only
			STATUS current
			DESCRIPTION
				"The total number of broadcast packets received on the OLT side"
			::= { sleEponStatsOltPonEntry 6 }

		
		sleEponStatsOltPonInMulticastPkts OBJECT-TYPE
			SYNTAX Counter32
			MAX-ACCESS read-only
			STATUS current
			DESCRIPTION
				"The total number of multicast packets received on the OLT side"
			::= { sleEponStatsOltPonEntry 7 }

		
		sleEponStatsOltPonOutOctets OBJECT-TYPE
			SYNTAX Counter64
			MAX-ACCESS read-only
			STATUS current
			DESCRIPTION
				"The total number of octets transmitted out of the OLT side"
			::= { sleEponStatsOltPonEntry 8 }

		
		sleEponStatsOltPonOutPkts OBJECT-TYPE
			SYNTAX Counter32
			MAX-ACCESS read-only
			STATUS current
			DESCRIPTION
				"The total number of packets transmitted out of the OLT side"
			::= { sleEponStatsOltPonEntry 9 }

		
		sleEponStatsOltPonOutPause OBJECT-TYPE
			SYNTAX Counter32
			MAX-ACCESS read-only
			STATUS current
			DESCRIPTION
				"The total number of paused packets transmitted out of the OLT side"
			::= { sleEponStatsOltPonEntry 10 }

		
		sleEponStatsOltPonOutDropped OBJECT-TYPE
			SYNTAX Counter32
			MAX-ACCESS read-only
			STATUS current
			DESCRIPTION
				"The total number of droped packets transmitted out of the OLT side"
			::= { sleEponStatsOltPonEntry 11 }

		
		sleEponStatsOltPonOutUnicastPkts OBJECT-TYPE
			SYNTAX Counter32
			MAX-ACCESS read-only
			STATUS current
			DESCRIPTION
				"The total number of unicast packets transmitted out of the OLT side"
			::= { sleEponStatsOltPonEntry 12 }

		
		sleEponstatsOltPonOutBroadcastPkts OBJECT-TYPE
			SYNTAX Counter32
			MAX-ACCESS read-only
			STATUS current
			DESCRIPTION
				"The total number of broadcast packets transmitted out of the OLT side"
			::= { sleEponStatsOltPonEntry 13 }

		
		sleEponStatsOltPonOutMulticastPkts OBJECT-TYPE
			SYNTAX Counter32
			MAX-ACCESS read-only
			STATUS current
			DESCRIPTION
				"The total number of multicast packets transmitted out of the OLT side"
			::= { sleEponStatsOltPonEntry 14 }

		
		sleEponStatsOltPonInHostFrame OBJECT-TYPE
			SYNTAX Counter32
			MAX-ACCESS read-only
			STATUS current
			DESCRIPTION
				"The total number of frame received on the OLT side."
			::= { sleEponStatsOltPonEntry 15 }

		
		sleEponStatsOltPonInTooLongFrame OBJECT-TYPE
			SYNTAX Counter32
			MAX-ACCESS read-only
			STATUS current
			DESCRIPTION
				"The total number of long frame received on the OLT side."
			::= { sleEponStatsOltPonEntry 16 }

		
		sleEponStatsOltPonInHostFrameDropped OBJECT-TYPE
			SYNTAX Counter32
			MAX-ACCESS read-only
			STATUS current
			DESCRIPTION
				"The total number of droped frame received on the OLT side."
			::= { sleEponStatsOltPonEntry 17 }

		
		sleEponStatsOltPonInHECErrorFrame OBJECT-TYPE
			SYNTAX Counter32
			MAX-ACCESS read-only
			STATUS current
			DESCRIPTION
				"The total number of HEC error frame received on the OLT side."
			::= { sleEponStatsOltPonEntry 18 }

		
		sleEponStatsOltPonTxOkBytes64 OBJECT-TYPE
			SYNTAX Counter64
			MAX-ACCESS read-only
			STATUS current
			DESCRIPTION
				" "
			::= { sleEponStatsOltPonEntry 19 }

		
		sleEponStatsOltPonTxOkFrames64 OBJECT-TYPE
			SYNTAX Counter64
			MAX-ACCESS read-only
			STATUS current
			DESCRIPTION
				" "
			::= { sleEponStatsOltPonEntry 20 }

		
		sleEponStatsOltPonTxUniFrames64 OBJECT-TYPE
			SYNTAX Counter64
			MAX-ACCESS read-only
			STATUS current
			DESCRIPTION
				" "
			::= { sleEponStatsOltPonEntry 21 }

		
		sleEponStatsOltPonTxMulFrames64 OBJECT-TYPE
			SYNTAX Counter64
			MAX-ACCESS read-only
			STATUS current
			DESCRIPTION
				" "
			::= { sleEponStatsOltPonEntry 22 }

		
		sleEponStatsOltPonTxBroFrames64 OBJECT-TYPE
			SYNTAX Counter64
			MAX-ACCESS read-only
			STATUS current
			DESCRIPTION
				" "
			::= { sleEponStatsOltPonEntry 23 }

		
		sleEponStatsOltPonTxCrcGen64 OBJECT-TYPE
			SYNTAX Counter64
			MAX-ACCESS read-only
			STATUS current
			DESCRIPTION
				" "
			::= { sleEponStatsOltPonEntry 24 }

		
		sleEponStatsOltPonTxPauseFrames64 OBJECT-TYPE
			SYNTAX Counter64
			MAX-ACCESS read-only
			STATUS current
			DESCRIPTION
				" "
			::= { sleEponStatsOltPonEntry 25 }

		
		sleEponStatsOltPonTxErrBytes64 OBJECT-TYPE
			SYNTAX Counter64
			MAX-ACCESS read-only
			STATUS current
			DESCRIPTION
				" "
			::= { sleEponStatsOltPonEntry 26 }

		
		sleEponStatsOltPonRxOkBytes64 OBJECT-TYPE
			SYNTAX Counter64
			MAX-ACCESS read-only
			STATUS current
			DESCRIPTION
				" "
			::= { sleEponStatsOltPonEntry 27 }

		
		sleEponStatsOltPonRxOkFrames64 OBJECT-TYPE
			SYNTAX Counter64
			MAX-ACCESS read-only
			STATUS current
			DESCRIPTION
				" "
			::= { sleEponStatsOltPonEntry 28 }

		
		sleEponStatsOltPonRxUniFrames64 OBJECT-TYPE
			SYNTAX Counter64
			MAX-ACCESS read-only
			STATUS current
			DESCRIPTION
				" "
			::= { sleEponStatsOltPonEntry 29 }

		
		sleEponStatsOltPonRxMulFrames64 OBJECT-TYPE
			SYNTAX Counter64
			MAX-ACCESS read-only
			STATUS current
			DESCRIPTION
				" "
			::= { sleEponStatsOltPonEntry 30 }

		
		sleEponStatsOltPonRxBroFrames64 OBJECT-TYPE
			SYNTAX Counter64
			MAX-ACCESS read-only
			STATUS current
			DESCRIPTION
				" "
			::= { sleEponStatsOltPonEntry 31 }

		
		sleEponStatsOltPonRxUndersizeFrames64 OBJECT-TYPE
			SYNTAX Counter64
			MAX-ACCESS read-only
			STATUS current
			DESCRIPTION
				" "
			::= { sleEponStatsOltPonEntry 32 }

		
		sleEponStatsOltPonRxOverSizeFrames64 OBJECT-TYPE
			SYNTAX Counter64
			MAX-ACCESS read-only
			STATUS current
			DESCRIPTION
				" "
			::= { sleEponStatsOltPonEntry 33 }

		
		sleEponStatsOltPonRxPauseFrames64 OBJECT-TYPE
			SYNTAX Counter64
			MAX-ACCESS read-only
			STATUS current
			DESCRIPTION
				" "
			::= { sleEponStatsOltPonEntry 34 }

		
		sleEponStatsOltPonRxAlignErrFrames64 OBJECT-TYPE
			SYNTAX Counter64
			MAX-ACCESS read-only
			STATUS current
			DESCRIPTION
				" "
			::= { sleEponStatsOltPonEntry 35 }

		
		sleEponStatsOltPonRxErrBytes64 OBJECT-TYPE
			SYNTAX Counter64
			MAX-ACCESS read-only
			STATUS current
			DESCRIPTION
				" "
			::= { sleEponStatsOltPonEntry 36 }

		
		sleEponStatsOltPonRxCodeErr64 OBJECT-TYPE
			SYNTAX Counter64
			MAX-ACCESS read-only
			STATUS current
			DESCRIPTION
				" "
			::= { sleEponStatsOltPonEntry 37 }

		
		sleEponStatsOltChannelTable OBJECT-TYPE
			SYNTAX SEQUENCE OF SleEponStatsOltChannelEntry
			MAX-ACCESS not-accessible
			STATUS current
			DESCRIPTION
				"Description."
			::= { sleEponOltStatistics 3 }

		
		sleEponStatsOltChannelEntry OBJECT-TYPE
			SYNTAX SleEponStatsOltChannelEntry
			MAX-ACCESS not-accessible
			STATUS current
			DESCRIPTION
				"Description."
			INDEX { sleEponOltIndex, sleEponOnuIndex }
			::= { sleEponStatsOltChannelTable 1 }

		
		SleEponStatsOltChannelEntry ::=
			SEQUENCE { 
				sleEponStatsOltChannelInOctets
					Counter64,
				sleEponStatsOltChannelInDataOctets
					Counter64,
				sleEponStatsOltChannelInPkts
					Counter32,
				sleEponStatsOltChannelInMulticastPkts
					Counter32,
				sleEponStatsOltChannelInBroadcastPkts
					Counter32,
				sleEponStatsOltChannelInErrorOctets
					Counter32,
				sleEponStatsOltChannelInErrorPkts
					Counter32,
				sleEponStatsOltChannelOutOctets
					Counter64,
				sleEponStatsOltChannelOutPkts
					Counter32,
				sleEponStatsOltChannelOutPolicerDroppedPkts
					Counter32,
				sleEponStatsOltChannelOutMismatchDroppedPkts
					Counter32,
				sleEponStatsOltChannelOutMulticastPkts
					Counter32,
				sleEponStatsOltChannelOutBroadcastPkts
					Counter32,
				sleEponStatsOltChannelFCS
					Counter32,
				sleEponStatsOltChannelInRangeLengthErrors
					Counter32,
				sleEponStatsOltChannelFrameTooLongErrors
					Counter32,
				sleEponStatsOltChannelInUnicastPkts
					Counter32,
				sleEponStatsOltChannelOutUnicastPkts
					Counter32
			 }

		sleEponStatsOltChannelInOctets OBJECT-TYPE
			SYNTAX Counter64
			MAX-ACCESS read-only
			STATUS current
			DESCRIPTION
				"The total number of octets received on the ONU side"
			::= { sleEponStatsOltChannelEntry 1 }

		
		sleEponStatsOltChannelInDataOctets OBJECT-TYPE
			SYNTAX Counter64
			MAX-ACCESS read-only
			STATUS current
			DESCRIPTION
				"The total number of  data octets received on the ONU side"
			::= { sleEponStatsOltChannelEntry 2 }

		
		sleEponStatsOltChannelInPkts OBJECT-TYPE
			SYNTAX Counter32
			MAX-ACCESS read-only
			STATUS current
			DESCRIPTION
				"The total number of packets transmitted out of the ONU side"
			::= { sleEponStatsOltChannelEntry 3 }

		
		sleEponStatsOltChannelInMulticastPkts OBJECT-TYPE
			SYNTAX Counter32
			MAX-ACCESS read-only
			STATUS current
			DESCRIPTION
				"The total number of multicast packets received on the ONU side"
			::= { sleEponStatsOltChannelEntry 4 }

		
		sleEponStatsOltChannelInBroadcastPkts OBJECT-TYPE
			SYNTAX Counter32
			MAX-ACCESS read-only
			STATUS current
			DESCRIPTION
				"The total number of broadcast packets received on the ONU side"
			::= { sleEponStatsOltChannelEntry 5 }

		
		sleEponStatsOltChannelInErrorOctets OBJECT-TYPE
			SYNTAX Counter32
			MAX-ACCESS read-only
			STATUS current
			DESCRIPTION
				"The total number of errored octets received on the ONU side"
			::= { sleEponStatsOltChannelEntry 6 }

		
		sleEponStatsOltChannelInErrorPkts OBJECT-TYPE
			SYNTAX Counter32
			MAX-ACCESS read-only
			STATUS current
			DESCRIPTION
				"The total number of errored packets received on the ONU side"
			::= { sleEponStatsOltChannelEntry 7 }

		
		sleEponStatsOltChannelOutOctets OBJECT-TYPE
			SYNTAX Counter64
			MAX-ACCESS read-only
			STATUS current
			DESCRIPTION
				"The total number of octets transmitted out of the ONU side"
			::= { sleEponStatsOltChannelEntry 8 }

		
		sleEponStatsOltChannelOutPkts OBJECT-TYPE
			SYNTAX Counter32
			MAX-ACCESS read-only
			STATUS current
			DESCRIPTION
				"The total number of packets transmitted out of the ONU side"
			::= { sleEponStatsOltChannelEntry 9 }

		
		sleEponStatsOltChannelOutPolicerDroppedPkts OBJECT-TYPE
			SYNTAX Counter32
			MAX-ACCESS read-only
			STATUS current
			DESCRIPTION
				"The total number of policer dropped transmitted out of the ONU side"
			::= { sleEponStatsOltChannelEntry 10 }

		
		sleEponStatsOltChannelOutMismatchDroppedPkts OBJECT-TYPE
			SYNTAX Counter32
			MAX-ACCESS read-only
			STATUS current
			DESCRIPTION
				"The total number of mismatch dropped packets transmitted out of the ONU side"
			::= { sleEponStatsOltChannelEntry 11 }

		
		sleEponStatsOltChannelOutMulticastPkts OBJECT-TYPE
			SYNTAX Counter32
			MAX-ACCESS read-only
			STATUS current
			DESCRIPTION
				"The total number of multicast packets transmitted out of the ONU side"
			::= { sleEponStatsOltChannelEntry 12 }

		
		sleEponStatsOltChannelOutBroadcastPkts OBJECT-TYPE
			SYNTAX Counter32
			MAX-ACCESS read-only
			STATUS current
			DESCRIPTION
				"The total number of broadcast packets transmitted out of the ONU side"
			::= { sleEponStatsOltChannelEntry 13 }

		
		sleEponStatsOltChannelFCS OBJECT-TYPE
			SYNTAX Counter32
			MAX-ACCESS read-only
			STATUS current
			DESCRIPTION
				"The total number of FCS transmitted out of the ONU side"
			::= { sleEponStatsOltChannelEntry 14 }

		
		sleEponStatsOltChannelInRangeLengthErrors OBJECT-TYPE
			SYNTAX Counter32
			MAX-ACCESS read-only
			STATUS current
			DESCRIPTION
				"The total number of range length errors received on th ONU side"
			::= { sleEponStatsOltChannelEntry 15 }

		
		sleEponStatsOltChannelFrameTooLongErrors OBJECT-TYPE
			SYNTAX Counter32
			MAX-ACCESS read-only
			STATUS current
			DESCRIPTION
				"The total number of frame to long errors on the ONU side"
			::= { sleEponStatsOltChannelEntry 16 }

		
		sleEponStatsOltChannelInUnicastPkts OBJECT-TYPE
			SYNTAX Counter32
			MAX-ACCESS read-only
			STATUS current
			DESCRIPTION
				"The total number of unicast packets received on the ONU side"
			::= { sleEponStatsOltChannelEntry 17 }

		
		sleEponStatsOltChannelOutUnicastPkts OBJECT-TYPE
			SYNTAX Counter32
			MAX-ACCESS read-only
			STATUS current
			DESCRIPTION
				"The total number of unicast packets transmitted out of the ONU side"
			::= { sleEponStatsOltChannelEntry 18 }

		
		sleEponStatsOltControl OBJECT IDENTIFIER ::= { sleEponOltStatistics 4 }

		
		sleEponStatsOltControlRequest OBJECT-TYPE
			SYNTAX INTEGER
				{
				clearEponStatsOlt(1),
				clearEponStatsOltChannel(2),
				clearEponStatsAll(3)
				}
			MAX-ACCESS read-write
			STATUS current
			DESCRIPTION
				"The request of a user command"
			::= { sleEponStatsOltControl 1 }

		
		sleEponStatsOltControlStatus OBJECT-TYPE
			SYNTAX SleControlStatusType
			MAX-ACCESS read-only
			STATUS current
			DESCRIPTION
				"The status of user command"
			::= { sleEponStatsOltControl 2 }

		
		sleEponStatsOltControlTimer OBJECT-TYPE
			SYNTAX Gauge32
			MAX-ACCESS read-write
			STATUS current
			DESCRIPTION
				"The maximum time for the manager for a long running user command"
			::= { sleEponStatsOltControl 3 }

		
		sleEponStatsOltControlTimeStamp OBJECT-TYPE
			SYNTAX TimeTicks
			MAX-ACCESS read-only
			STATUS current
			DESCRIPTION
				"The time stamp of the last command(end of command)"
			::= { sleEponStatsOltControl 4 }

		
		sleEponStatsOltControlReqResult OBJECT-TYPE
			SYNTAX SleControlRequestResultType
			MAX-ACCESS read-only
			STATUS current
			DESCRIPTION
				"The result of the last user command"
			::= { sleEponStatsOltControl 5 }

		
		sleEponStatsOltControlOltIndex OBJECT-TYPE
			SYNTAX INTEGER (1..512)
			MAX-ACCESS read-write
			STATUS current
			DESCRIPTION
				"OLT index"
			::= { sleEponStatsOltControl 6 }

		
		sleEponStatsOltControlChannelIndex OBJECT-TYPE
			SYNTAX INTEGER (1..32)
			MAX-ACCESS read-write
			STATUS current
			DESCRIPTION
				"ONU index"
			::= { sleEponStatsOltControl 7 }

		
		sleEponStatsOltNotification OBJECT IDENTIFIER ::= { sleEponOltStatistics 5 }

		
		sleEponstatsOltCleared NOTIFICATION-TYPE
			OBJECTS { sleEponStatsOltControlRequest, sleEponStatsOltControlTimeStamp, sleEponStatsOltControlReqResult, sleEponStatsOltControlOltIndex }
			STATUS current
			DESCRIPTION 
				"Description."
			::= { sleEponStatsOltNotification 1 }

		
		sleEponStatsOltChannelCleared NOTIFICATION-TYPE
			OBJECTS { sleEponStatsOltControlRequest, sleEponStatsOltControlTimeStamp, sleEponStatsOltControlReqResult, sleEponStatsOltControlOltIndex, sleEponStatsOltControlChannelIndex
				 }
			STATUS current
			DESCRIPTION 
				"Description."
			::= { sleEponStatsOltNotification 2 }

		
		sleEponStatsAllCleared NOTIFICATION-TYPE
			OBJECTS { sleEponStatsOltControlRequest, sleEponStatsOltControlTimeStamp, sleEponStatsOltControlReqResult, sleEponStatsOltControlOltIndex, sleEponStatsOltControlChannelIndex
				 }
			STATUS current
			DESCRIPTION 
				"Description."
			::= { sleEponStatsOltNotification 3 }

		
		sleEponStatsOltFromOnuTable OBJECT-TYPE
			SYNTAX SEQUENCE OF SleEponStatsOltFromOnuEntry
			MAX-ACCESS not-accessible
			STATUS current
			DESCRIPTION
				"Description."
			::= { sleEponOltStatistics 6 }

		
		sleEponStatsOltFromOnuEntry OBJECT-TYPE
			SYNTAX SleEponStatsOltFromOnuEntry
			MAX-ACCESS not-accessible
			STATUS current
			DESCRIPTION
				"Olt statistics: from onu."
			INDEX { sleEponOltIndex }
			::= { sleEponStatsOltFromOnuTable 1 }

		
		SleEponStatsOltFromOnuEntry ::=
			SEQUENCE { 
				sleEponStatsOltFromOnuInFrame
					Counter32,
				sleEponStatsOltFromOnuInErrorFrame
					Counter32,
				sleEponStatsOltFromOnuInMulticastFrame
					Counter32,
				sleEponStatsOltFromOnuInBroadcastFrame
					Counter32,
				sleEponStatsOltFromOnuInReportFrame
					Counter32,
				sleEponStatsOltFromOnuInCheckSeqErrorFrame
					Counter32,
				sleEponStatsOltFromOnuInRangeLenErrors
					Counter32,
				sleEponStatsOltFromOnuInTooLongFrame
					Counter32,
				sleEponStatsOltFromOnuOutFrame
					Counter32,
				sleEponStatsOltFromOnuOutFrameBytes
					Counter64,
				sleEponStatsOltFromOnuOutMulticastFrame
					Counter32,
				sleEponStatsOltFromOnuOutBroadcastFrame
					Counter32,
				sleEponStatsOltFromOnuOutDBAGrantFrame
					Counter32,
				sleEponStatsOltFromOnuOutControlGrantFrame
					Counter32,
				sleEponStatsOltFromOnuInUsedBytes
					Counter64,
				sleEponStatsOltFromOnuInGoodBytes
					Counter64,
				sleEponStatsOltFromOnuInHostFrame
					Counter32,
				sleEponStatsOltFromOnuInErrorBytes
					Counter32,
				sleEponStatsOltFromOnuInP2PFrame
					Counter32,
				sleEponStatsOltFromOnuOutUniFrame
					Counter32,
				sleEponStatsOltFromOnuOutPolicerDroppedFrame
					Counter32,
				sleEponStatsOltFromOnuOutMismatchDroppedFrame
					Counter32,
				sleEponStatsOltFromOnuOutHostFrame
					Counter32,
				sleEponStatsOltFromOnuPolicerDropP2PFrame
					Counter32,
				sleEponStatsOltFromOnuAccessCtrlDropP2PFrame
					Counter32,
				sleEponStatsOltFromOnuTxbuffFullDropP2PFrame
					Counter32
			 }

		sleEponStatsOltFromOnuInFrame OBJECT-TYPE
			SYNTAX Counter32
			MAX-ACCESS read-only
			STATUS current
			DESCRIPTION
				"The total number of Rx frame."
			::= { sleEponStatsOltFromOnuEntry 1 }

		
		sleEponStatsOltFromOnuInErrorFrame OBJECT-TYPE
			SYNTAX Counter32
			MAX-ACCESS read-only
			STATUS current
			DESCRIPTION
				"Rx error frame count."
			::= { sleEponStatsOltFromOnuEntry 2 }

		
		sleEponStatsOltFromOnuInMulticastFrame OBJECT-TYPE
			SYNTAX Counter32
			MAX-ACCESS read-only
			STATUS current
			DESCRIPTION
				"Rx multicast frame count."
			::= { sleEponStatsOltFromOnuEntry 3 }

		
		sleEponStatsOltFromOnuInBroadcastFrame OBJECT-TYPE
			SYNTAX Counter32
			MAX-ACCESS read-only
			STATUS current
			DESCRIPTION
				"Rx broadcast frame count."
			::= { sleEponStatsOltFromOnuEntry 4 }

		
		sleEponStatsOltFromOnuInReportFrame OBJECT-TYPE
			SYNTAX Counter32
			MAX-ACCESS read-only
			STATUS current
			DESCRIPTION
				"Rx report frame count."
			::= { sleEponStatsOltFromOnuEntry 5 }

		
		sleEponStatsOltFromOnuInCheckSeqErrorFrame OBJECT-TYPE
			SYNTAX Counter32
			MAX-ACCESS read-only
			STATUS current
			DESCRIPTION
				"Rx check sequenece error frame count."
			::= { sleEponStatsOltFromOnuEntry 6 }

		
		sleEponStatsOltFromOnuInRangeLenErrors OBJECT-TYPE
			SYNTAX Counter32
			MAX-ACCESS read-only
			STATUS current
			DESCRIPTION
				"Rx range of length error frame count."
			::= { sleEponStatsOltFromOnuEntry 7 }

		
		sleEponStatsOltFromOnuInTooLongFrame OBJECT-TYPE
			SYNTAX Counter32
			MAX-ACCESS read-only
			STATUS current
			DESCRIPTION
				"Rx too long frame counts."
			::= { sleEponStatsOltFromOnuEntry 8 }

		
		sleEponStatsOltFromOnuOutFrame OBJECT-TYPE
			SYNTAX Counter32
			MAX-ACCESS read-only
			STATUS current
			DESCRIPTION
				"Tx frame count."
			::= { sleEponStatsOltFromOnuEntry 9 }

		
		sleEponStatsOltFromOnuOutFrameBytes OBJECT-TYPE
			SYNTAX Counter64
			MAX-ACCESS read-only
			STATUS current
			DESCRIPTION
				"Tx frame bytes."
			::= { sleEponStatsOltFromOnuEntry 10 }

		
		sleEponStatsOltFromOnuOutMulticastFrame OBJECT-TYPE
			SYNTAX Counter32
			MAX-ACCESS read-only
			STATUS current
			DESCRIPTION
				"Tx multicast frame count."
			::= { sleEponStatsOltFromOnuEntry 11 }

		
		sleEponStatsOltFromOnuOutBroadcastFrame OBJECT-TYPE
			SYNTAX Counter32
			MAX-ACCESS read-only
			STATUS current
			DESCRIPTION
				"Tx broadcast frame count."
			::= { sleEponStatsOltFromOnuEntry 12 }

		
		sleEponStatsOltFromOnuOutDBAGrantFrame OBJECT-TYPE
			SYNTAX Counter32
			MAX-ACCESS read-only
			STATUS current
			DESCRIPTION
				"Tx grant DBA frame count."
			::= { sleEponStatsOltFromOnuEntry 13 }

		
		sleEponStatsOltFromOnuOutControlGrantFrame OBJECT-TYPE
			SYNTAX Counter32
			MAX-ACCESS read-only
			STATUS current
			DESCRIPTION
				"Tx grant frame count."
			::= { sleEponStatsOltFromOnuEntry 14 }

		
		sleEponStatsOltFromOnuInUsedBytes OBJECT-TYPE
			SYNTAX Counter64
			MAX-ACCESS read-only
			STATUS current
			DESCRIPTION
				"Rx Used Bytes(total data)."
			::= { sleEponStatsOltFromOnuEntry 15 }

		
		sleEponStatsOltFromOnuInGoodBytes OBJECT-TYPE
			SYNTAX Counter64
			MAX-ACCESS read-only
			STATUS current
			DESCRIPTION
				"Rx Good Bytes(total byte)."
			::= { sleEponStatsOltFromOnuEntry 16 }

		
		sleEponStatsOltFromOnuInHostFrame OBJECT-TYPE
			SYNTAX Counter32
			MAX-ACCESS read-only
			STATUS current
			DESCRIPTION
				"Rx OK Firmware(host frame)."
			::= { sleEponStatsOltFromOnuEntry 17 }

		
		sleEponStatsOltFromOnuInErrorBytes OBJECT-TYPE
			SYNTAX Counter32
			MAX-ACCESS read-only
			STATUS current
			DESCRIPTION
				"Rx Error Bytes."
			::= { sleEponStatsOltFromOnuEntry 18 }

		
		sleEponStatsOltFromOnuInP2PFrame OBJECT-TYPE
			SYNTAX Counter32
			MAX-ACCESS read-only
			STATUS current
			DESCRIPTION
				"Rx OK P2P Frames."
			::= { sleEponStatsOltFromOnuEntry 19 }

		
		sleEponStatsOltFromOnuOutUniFrame OBJECT-TYPE
			SYNTAX Counter32
			MAX-ACCESS read-only
			STATUS current
			DESCRIPTION
				"Tx OK Frames(SYSTEM)  ."
			::= { sleEponStatsOltFromOnuEntry 20 }

		
		sleEponStatsOltFromOnuOutPolicerDroppedFrame OBJECT-TYPE
			SYNTAX Counter32
			MAX-ACCESS read-only
			STATUS current
			DESCRIPTION
				"Tx Dropped Frames by Policer."
			::= { sleEponStatsOltFromOnuEntry 21 }

		
		sleEponStatsOltFromOnuOutMismatchDroppedFrame OBJECT-TYPE
			SYNTAX Counter32
			MAX-ACCESS read-only
			STATUS current
			DESCRIPTION
				"Tx Dropped Frames by Mismatch."
			::= { sleEponStatsOltFromOnuEntry 22 }

		
		sleEponStatsOltFromOnuOutHostFrame OBJECT-TYPE
			SYNTAX Counter32
			MAX-ACCESS read-only
			STATUS current
			DESCRIPTION
				"TX OK Host Frames(PON)."
			::= { sleEponStatsOltFromOnuEntry 23 }

		
		sleEponStatsOltFromOnuPolicerDropP2PFrame OBJECT-TYPE
			SYNTAX Counter32
			MAX-ACCESS read-only
			STATUS current
			DESCRIPTION
				"Drop P2P Frames by policer."
			::= { sleEponStatsOltFromOnuEntry 24 }

		
		sleEponStatsOltFromOnuAccessCtrlDropP2PFrame OBJECT-TYPE
			SYNTAX Counter32
			MAX-ACCESS read-only
			STATUS current
			DESCRIPTION
				"Drop P2P Frames by acess control."
			::= { sleEponStatsOltFromOnuEntry 25 }

		
		sleEponStatsOltFromOnuTxbuffFullDropP2PFrame OBJECT-TYPE
			SYNTAX Counter32
			MAX-ACCESS read-only
			STATUS current
			DESCRIPTION
				" Drop P2P Frames due to tx buffer full."
			::= { sleEponStatsOltFromOnuEntry 26 }

		
		sleEponOnuStatistics OBJECT IDENTIFIER ::= { sleEponStatistics 2 }

		
		sleEponStatsOnuPortTable OBJECT-TYPE
			SYNTAX SEQUENCE OF SleEponStatsOnuPortEntry
			MAX-ACCESS not-accessible
			STATUS current
			DESCRIPTION
				"Description."
			::= { sleEponOnuStatistics 1 }

		
		sleEponStatsOnuPortEntry OBJECT-TYPE
			SYNTAX SleEponStatsOnuPortEntry
			MAX-ACCESS not-accessible
			STATUS current
			DESCRIPTION
				"Description."
			INDEX { sleEponOltIndex, sleEponOnuIndex, sleEponOnuPortIndex }
			::= { sleEponStatsOnuPortTable 1 }

		
		SleEponStatsOnuPortEntry ::=
			SEQUENCE { 
				sleEponStatsOnuPortInOctets
					Counter64,
				sleEponStatsOnuPortInPkts
					Counter32,
				sleEponStatsOnuPortInUcastPkts
					Counter32,
				sleEponStatsOnuPortInBcastPkts
					Counter32,
				sleEponStatsOnuPortInMcastPkts
					Counter32,
				sleEponStatsOnuPortOutOctets
					Counter64,
				sleEponStatsOnuPortOutPkts
					Counter32,
				sleEponStatsOnuPortOutUcastPkts
					Counter32,
				sleEponStatsOnuPortOutBcastPkts
					Counter32,
				sleEponStatsOnuPortOutMcastPkts
					Counter32,
				sleEponStatsOnuPortInUndersize
					Counter32,
				sleEponStatsOnuPortInOversize
					Counter32,
				sleEponStatsOnuPortInJabber
					Counter32,
				sleEponStatsOnuPortInRxError
					Counter32,
				sleEponStatsOnuPortInRxFcsError
					Counter32,
				sleEponStatsOnuPortTxOkBytes64
					Counter64,
				sleEponStatsOnuPortTxOkFrames64
					Counter64,
				sleEponStatsOnuPortTxUniFrames64
					Counter64,
				sleEponStatsOnuPortTxMulFrames64
					Counter64,
				sleEponStatsOnuPortTxBroFrames64
					Counter64,
				sleEponStatsOnuPortTxPauseFrames64
					Counter64,
				sleEponStatsOnuPortTxDropBytes64
					Counter64,
				sleEponStatsOnuPortTxDropFrames64
					Counter64,
				sleEponStatsOnuPortRxOkBytes64
					Counter64,
				sleEponStatsOnuPortRxOkFrames64
					Counter64,
				sleEponStatsOnuPortRxUniFrames64
					Counter64,
				sleEponStatsOnuPortRxMulFrames64
					Counter64,
				sleEponStatsOnuPortRxBroFrames64
					Counter64,
				sleEponStatsOnuPortRxUndersizeFrames64
					Counter64,
				sleEponStatsOnuPortRxOverSizeFrames64
					Counter64,
				sleEponStatsOnuPortRxPauseFrames64
					Counter64,
				sleEponStatsOnuPortRxLengthErrFrames64
					Counter64,
				sleEponStatsOnuPortRxAlignErrFrames64
					Counter64,
				sleEponStatsOnuPortRxCrcErrFrames64
					Counter64
			 }

		sleEponStatsOnuPortInOctets OBJECT-TYPE
			SYNTAX Counter64
			MAX-ACCESS read-only
			STATUS current
			DESCRIPTION
				"Description."
			::= { sleEponStatsOnuPortEntry 1 }

		
		sleEponStatsOnuPortInPkts OBJECT-TYPE
			SYNTAX Counter32
			MAX-ACCESS read-only
			STATUS current
			DESCRIPTION
				"Description."
			::= { sleEponStatsOnuPortEntry 2 }

		
		sleEponStatsOnuPortInUcastPkts OBJECT-TYPE
			SYNTAX Counter32
			MAX-ACCESS read-only
			STATUS current
			DESCRIPTION
				"Description."
			::= { sleEponStatsOnuPortEntry 3 }

		
		sleEponStatsOnuPortInBcastPkts OBJECT-TYPE
			SYNTAX Counter32
			MAX-ACCESS read-only
			STATUS current
			DESCRIPTION
				"Description."
			::= { sleEponStatsOnuPortEntry 4 }

		
		sleEponStatsOnuPortInMcastPkts OBJECT-TYPE
			SYNTAX Counter32
			MAX-ACCESS read-only
			STATUS current
			DESCRIPTION
				"Description."
			::= { sleEponStatsOnuPortEntry 5 }

		
		sleEponStatsOnuPortOutOctets OBJECT-TYPE
			SYNTAX Counter64
			MAX-ACCESS read-only
			STATUS current
			DESCRIPTION
				"Description."
			::= { sleEponStatsOnuPortEntry 6 }

		
		sleEponStatsOnuPortOutPkts OBJECT-TYPE
			SYNTAX Counter32
			MAX-ACCESS read-only
			STATUS current
			DESCRIPTION
				"Description."
			::= { sleEponStatsOnuPortEntry 7 }

		
		sleEponStatsOnuPortOutUcastPkts OBJECT-TYPE
			SYNTAX Counter32
			MAX-ACCESS read-only
			STATUS current
			DESCRIPTION
				"Description."
			::= { sleEponStatsOnuPortEntry 8 }

		
		sleEponStatsOnuPortOutBcastPkts OBJECT-TYPE
			SYNTAX Counter32
			MAX-ACCESS read-only
			STATUS current
			DESCRIPTION
				"Description."
			::= { sleEponStatsOnuPortEntry 9 }

		
		sleEponStatsOnuPortOutMcastPkts OBJECT-TYPE
			SYNTAX Counter32
			MAX-ACCESS read-only
			STATUS current
			DESCRIPTION
				"Description."
			::= { sleEponStatsOnuPortEntry 10 }

		
		sleEponStatsOnuPortInUndersize OBJECT-TYPE
			SYNTAX Counter32
			MAX-ACCESS read-only
			STATUS current
			DESCRIPTION
				"Description."
			::= { sleEponStatsOnuPortEntry 11 }

		
		sleEponStatsOnuPortInOversize OBJECT-TYPE
			SYNTAX Counter32
			MAX-ACCESS read-only
			STATUS current
			DESCRIPTION
				"Description."
			::= { sleEponStatsOnuPortEntry 12 }

		
		sleEponStatsOnuPortInJabber OBJECT-TYPE
			SYNTAX Counter32
			MAX-ACCESS read-only
			STATUS current
			DESCRIPTION
				"Description."
			::= { sleEponStatsOnuPortEntry 13 }

		
		sleEponStatsOnuPortInRxError OBJECT-TYPE
			SYNTAX Counter32
			MAX-ACCESS read-only
			STATUS current
			DESCRIPTION
				"Description."
			::= { sleEponStatsOnuPortEntry 14 }

		
		sleEponStatsOnuPortInRxFcsError OBJECT-TYPE
			SYNTAX Counter32
			MAX-ACCESS read-only
			STATUS current
			DESCRIPTION
				"Description."
			::= { sleEponStatsOnuPortEntry 15 }

		
		sleEponStatsOnuPortTxOkBytes64 OBJECT-TYPE
			SYNTAX Counter64
			MAX-ACCESS read-only
			STATUS current
			DESCRIPTION
				" "
			::= { sleEponStatsOnuPortEntry 16 }

		
		sleEponStatsOnuPortTxOkFrames64 OBJECT-TYPE
			SYNTAX Counter64
			MAX-ACCESS read-only
			STATUS current
			DESCRIPTION
				" "
			::= { sleEponStatsOnuPortEntry 17 }

		
		sleEponStatsOnuPortTxUniFrames64 OBJECT-TYPE
			SYNTAX Counter64
			MAX-ACCESS read-only
			STATUS current
			DESCRIPTION
				" "
			::= { sleEponStatsOnuPortEntry 18 }

		
		sleEponStatsOnuPortTxMulFrames64 OBJECT-TYPE
			SYNTAX Counter64
			MAX-ACCESS read-only
			STATUS current
			DESCRIPTION
				" "
			::= { sleEponStatsOnuPortEntry 19 }

		
		sleEponStatsOnuPortTxBroFrames64 OBJECT-TYPE
			SYNTAX Counter64
			MAX-ACCESS read-only
			STATUS current
			DESCRIPTION
				" "
			::= { sleEponStatsOnuPortEntry 20 }

		
		sleEponStatsOnuPortTxPauseFrames64 OBJECT-TYPE
			SYNTAX Counter64
			MAX-ACCESS read-only
			STATUS current
			DESCRIPTION
				" "
			::= { sleEponStatsOnuPortEntry 21 }

		
		sleEponStatsOnuPortTxDropBytes64 OBJECT-TYPE
			SYNTAX Counter64
			MAX-ACCESS read-only
			STATUS current
			DESCRIPTION
				" "
			::= { sleEponStatsOnuPortEntry 22 }

		
		sleEponStatsOnuPortTxDropFrames64 OBJECT-TYPE
			SYNTAX Counter64
			MAX-ACCESS read-only
			STATUS current
			DESCRIPTION
				" "
			::= { sleEponStatsOnuPortEntry 23 }

		
		sleEponStatsOnuPortRxOkBytes64 OBJECT-TYPE
			SYNTAX Counter64
			MAX-ACCESS read-only
			STATUS current
			DESCRIPTION
				" "
			::= { sleEponStatsOnuPortEntry 24 }

		
		sleEponStatsOnuPortRxOkFrames64 OBJECT-TYPE
			SYNTAX Counter64
			MAX-ACCESS read-only
			STATUS current
			DESCRIPTION
				" "
			::= { sleEponStatsOnuPortEntry 25 }

		
		sleEponStatsOnuPortRxUniFrames64 OBJECT-TYPE
			SYNTAX Counter64
			MAX-ACCESS read-only
			STATUS current
			DESCRIPTION
				" "
			::= { sleEponStatsOnuPortEntry 26 }

		
		sleEponStatsOnuPortRxMulFrames64 OBJECT-TYPE
			SYNTAX Counter64
			MAX-ACCESS read-only
			STATUS current
			DESCRIPTION
				" "
			::= { sleEponStatsOnuPortEntry 27 }

		
		sleEponStatsOnuPortRxBroFrames64 OBJECT-TYPE
			SYNTAX Counter64
			MAX-ACCESS read-only
			STATUS current
			DESCRIPTION
				" "
			::= { sleEponStatsOnuPortEntry 28 }

		
		sleEponStatsOnuPortRxUndersizeFrames64 OBJECT-TYPE
			SYNTAX Counter64
			MAX-ACCESS read-only
			STATUS current
			DESCRIPTION
				" "
			::= { sleEponStatsOnuPortEntry 29 }

		
		sleEponStatsOnuPortRxOverSizeFrames64 OBJECT-TYPE
			SYNTAX Counter64
			MAX-ACCESS read-only
			STATUS current
			DESCRIPTION
				" "
			::= { sleEponStatsOnuPortEntry 30 }

		
		sleEponStatsOnuPortRxPauseFrames64 OBJECT-TYPE
			SYNTAX Counter64
			MAX-ACCESS read-only
			STATUS current
			DESCRIPTION
				" "
			::= { sleEponStatsOnuPortEntry 31 }

		
		sleEponStatsOnuPortRxLengthErrFrames64 OBJECT-TYPE
			SYNTAX Counter64
			MAX-ACCESS read-only
			STATUS current
			DESCRIPTION
				" "
			::= { sleEponStatsOnuPortEntry 32 }

		
		sleEponStatsOnuPortRxAlignErrFrames64 OBJECT-TYPE
			SYNTAX Counter64
			MAX-ACCESS read-only
			STATUS current
			DESCRIPTION
				" "
			::= { sleEponStatsOnuPortEntry 33 }

		
		sleEponStatsOnuPortRxCrcErrFrames64 OBJECT-TYPE
			SYNTAX Counter64
			MAX-ACCESS read-only
			STATUS current
			DESCRIPTION
				" "
			::= { sleEponStatsOnuPortEntry 34 }

		
		sleEponStatsOnuUniTable OBJECT-TYPE
			SYNTAX SEQUENCE OF SleEponStatsOnuUniEntry
			MAX-ACCESS not-accessible
			STATUS current
			DESCRIPTION
				"Description."
			::= { sleEponOnuStatistics 2 }

		
		sleEponStatsOnuUniEntry OBJECT-TYPE
			SYNTAX SleEponStatsOnuUniEntry
			MAX-ACCESS not-accessible
			STATUS current
			DESCRIPTION
				"Description."
			INDEX { sleEponOltIndex, sleEponOnuIndex }
			::= { sleEponStatsOnuUniTable 1 }

		
		SleEponStatsOnuUniEntry ::=
			SEQUENCE { 
				sleEponStatsOnuUniInPkts
					Counter32,
				sleEponStatsOnuUniInBytes
					Counter64,
				sleEponStatsOnuUniInErrPkts
					Counter32,
				sleEponStatsOnuUniInErrBytes
					Counter32,
				sleEponStatsOnuUniInPause
					Counter32,
				sleEponStatsOnuUniFrameLongError
					Counter32,
				sleEponStatsOnuUniOutPkts
					Counter32,
				sleEponStatsOnuUniOutBytes
					Counter64,
				sleEponStatsOnuUniOutPause
					Counter32,
				sleEponStatsOnuUniOutDropPkts
					Counter32,
				sleEponStatsOnuUnInMcastPkts
					Counter32,
				sleEponStatsOnuUnInBcastPkts
					Counter32,
				sleEponStatsOnuUniInDropPkts
					Counter32,
				sleEponStatsOnuUniOutMcastPkts
					Counter32,
				sleEponStatsOnuUniOutBcastPkts
					Counter32,
				sleEponStatsOnuUniTxOkBytes64
					Counter64,
				sleEponStatsOnuUniTxOkFrames64
					Counter64,
				sleEponStatsOnuUniTxUniFrames64
					Counter64,
				sleEponStatsOnuUniTxMulFrames64
					Counter64,
				sleEponStatsOnuUniTxBroFrames64
					Counter64,
				sleEponStatsOnuUniTxPauseFrames64
					Counter64,
				sleEponStatsOnuUniTxDropBytes64
					Counter64,
				sleEponStatsOnuUniTxDropFrames64
					Counter64,
				sleEponStatsOnuUniRxOkBytes64
					Counter64,
				sleEponStatsOnuUniRxOkFrames64
					Counter64,
				sleEponStatsOnuUniRxUniFrames64
					Counter64,
				sleEponStatsOnuUniRxMulFrames64
					Counter64,
				sleEponStatsOnuUniRxBroFrames64
					Counter64,
				sleEponStatsOnuUniRxUnderSizeFrames64
					Counter64,
				sleEponStatsOnuUniRxOverSizeFrames64
					Counter64,
				sleEponStatsOnuUniRxPauseFrames64
					Counter64,
				sleEponStatsOnuUniRxLengthErrFrames64
					Counter64,
				sleEponStatsOnuUniRxAlignErrFrames64
					Counter64,
				sleEponStatsOnuUniRxCrcErrFrames64
					Counter64
			 }

		sleEponStatsOnuUniInPkts OBJECT-TYPE
			SYNTAX Counter32
			MAX-ACCESS read-only
			STATUS current
			DESCRIPTION
				"Description."
			::= { sleEponStatsOnuUniEntry 1 }

		
		sleEponStatsOnuUniInBytes OBJECT-TYPE
			SYNTAX Counter64
			MAX-ACCESS read-only
			STATUS current
			DESCRIPTION
				"Description."
			::= { sleEponStatsOnuUniEntry 2 }

		
		sleEponStatsOnuUniInErrPkts OBJECT-TYPE
			SYNTAX Counter32
			MAX-ACCESS read-only
			STATUS current
			DESCRIPTION
				"Description."
			::= { sleEponStatsOnuUniEntry 3 }

		
		sleEponStatsOnuUniInErrBytes OBJECT-TYPE
			SYNTAX Counter32
			MAX-ACCESS read-only
			STATUS current
			DESCRIPTION
				"Description."
			::= { sleEponStatsOnuUniEntry 4 }

		
		sleEponStatsOnuUniInPause OBJECT-TYPE
			SYNTAX Counter32
			MAX-ACCESS read-only
			STATUS current
			DESCRIPTION
				"Description."
			::= { sleEponStatsOnuUniEntry 5 }

		
		sleEponStatsOnuUniFrameLongError OBJECT-TYPE
			SYNTAX Counter32
			MAX-ACCESS read-only
			STATUS current
			DESCRIPTION
				"Description."
			::= { sleEponStatsOnuUniEntry 6 }

		
		sleEponStatsOnuUniOutPkts OBJECT-TYPE
			SYNTAX Counter32
			MAX-ACCESS read-only
			STATUS current
			DESCRIPTION
				"Description."
			::= { sleEponStatsOnuUniEntry 7 }

		
		sleEponStatsOnuUniOutBytes OBJECT-TYPE
			SYNTAX Counter64
			MAX-ACCESS read-only
			STATUS current
			DESCRIPTION
				"Description."
			::= { sleEponStatsOnuUniEntry 8 }

		
		sleEponStatsOnuUniOutPause OBJECT-TYPE
			SYNTAX Counter32
			MAX-ACCESS read-only
			STATUS current
			DESCRIPTION
				"Description."
			::= { sleEponStatsOnuUniEntry 9 }

		
		sleEponStatsOnuUniOutDropPkts OBJECT-TYPE
			SYNTAX Counter32
			MAX-ACCESS read-only
			STATUS current
			DESCRIPTION
				"Description."
			::= { sleEponStatsOnuUniEntry 10 }

		
		sleEponStatsOnuUnInMcastPkts OBJECT-TYPE
			SYNTAX Counter32
			MAX-ACCESS read-only
			STATUS current
			DESCRIPTION
				"The total number of Rx multicast packets on the ONU Uni side."
			::= { sleEponStatsOnuUniEntry 11 }

		
		sleEponStatsOnuUnInBcastPkts OBJECT-TYPE
			SYNTAX Counter32
			MAX-ACCESS read-only
			STATUS current
			DESCRIPTION
				"The total number of Rx broadcast packets on the ONU Uni side."
			::= { sleEponStatsOnuUniEntry 12 }

		
		sleEponStatsOnuUniInDropPkts OBJECT-TYPE
			SYNTAX Counter32
			MAX-ACCESS read-only
			STATUS current
			DESCRIPTION
				"The total number of Rx dropped packets on the ONU Uni side."
			::= { sleEponStatsOnuUniEntry 13 }

		
		sleEponStatsOnuUniOutMcastPkts OBJECT-TYPE
			SYNTAX Counter32
			MAX-ACCESS read-only
			STATUS current
			DESCRIPTION
				"The total number of Tx multicast packets on the ONU Uni side."
			::= { sleEponStatsOnuUniEntry 14 }

		
		sleEponStatsOnuUniOutBcastPkts OBJECT-TYPE
			SYNTAX Counter32
			MAX-ACCESS read-only
			STATUS current
			DESCRIPTION
				"The total number of Tx braocast packets on the ONU Uni side."
			::= { sleEponStatsOnuUniEntry 15 }

		
		sleEponStatsOnuUniTxOkBytes64 OBJECT-TYPE
			SYNTAX Counter64
			MAX-ACCESS read-only
			STATUS current
			DESCRIPTION
				" "
			::= { sleEponStatsOnuUniEntry 16 }

		
		sleEponStatsOnuUniTxOkFrames64 OBJECT-TYPE
			SYNTAX Counter64
			MAX-ACCESS read-only
			STATUS current
			DESCRIPTION
				" "
			::= { sleEponStatsOnuUniEntry 17 }

		
		sleEponStatsOnuUniTxUniFrames64 OBJECT-TYPE
			SYNTAX Counter64
			MAX-ACCESS read-only
			STATUS current
			DESCRIPTION
				" "
			::= { sleEponStatsOnuUniEntry 18 }

		
		sleEponStatsOnuUniTxMulFrames64 OBJECT-TYPE
			SYNTAX Counter64
			MAX-ACCESS read-only
			STATUS current
			DESCRIPTION
				" "
			::= { sleEponStatsOnuUniEntry 19 }

		
		sleEponStatsOnuUniTxBroFrames64 OBJECT-TYPE
			SYNTAX Counter64
			MAX-ACCESS read-only
			STATUS current
			DESCRIPTION
				" "
			::= { sleEponStatsOnuUniEntry 20 }

		
		sleEponStatsOnuUniTxPauseFrames64 OBJECT-TYPE
			SYNTAX Counter64
			MAX-ACCESS read-only
			STATUS current
			DESCRIPTION
				" "
			::= { sleEponStatsOnuUniEntry 21 }

		
		sleEponStatsOnuUniTxDropBytes64 OBJECT-TYPE
			SYNTAX Counter64
			MAX-ACCESS read-only
			STATUS current
			DESCRIPTION
				" "
			::= { sleEponStatsOnuUniEntry 22 }

		
		sleEponStatsOnuUniTxDropFrames64 OBJECT-TYPE
			SYNTAX Counter64
			MAX-ACCESS read-only
			STATUS current
			DESCRIPTION
				" "
			::= { sleEponStatsOnuUniEntry 23 }

		
		sleEponStatsOnuUniRxOkBytes64 OBJECT-TYPE
			SYNTAX Counter64
			MAX-ACCESS read-only
			STATUS current
			DESCRIPTION
				" "
			::= { sleEponStatsOnuUniEntry 24 }

		
		sleEponStatsOnuUniRxOkFrames64 OBJECT-TYPE
			SYNTAX Counter64
			MAX-ACCESS read-only
			STATUS current
			DESCRIPTION
				" "
			::= { sleEponStatsOnuUniEntry 25 }

		
		sleEponStatsOnuUniRxUniFrames64 OBJECT-TYPE
			SYNTAX Counter64
			MAX-ACCESS read-only
			STATUS current
			DESCRIPTION
				" "
			::= { sleEponStatsOnuUniEntry 26 }

		
		sleEponStatsOnuUniRxMulFrames64 OBJECT-TYPE
			SYNTAX Counter64
			MAX-ACCESS read-only
			STATUS current
			DESCRIPTION
				" "
			::= { sleEponStatsOnuUniEntry 27 }

		
		sleEponStatsOnuUniRxBroFrames64 OBJECT-TYPE
			SYNTAX Counter64
			MAX-ACCESS read-only
			STATUS current
			DESCRIPTION
				" "
			::= { sleEponStatsOnuUniEntry 28 }

		
		sleEponStatsOnuUniRxUnderSizeFrames64 OBJECT-TYPE
			SYNTAX Counter64
			MAX-ACCESS read-only
			STATUS current
			DESCRIPTION
				" "
			::= { sleEponStatsOnuUniEntry 29 }

		
		sleEponStatsOnuUniRxOverSizeFrames64 OBJECT-TYPE
			SYNTAX Counter64
			MAX-ACCESS read-only
			STATUS current
			DESCRIPTION
				" "
			::= { sleEponStatsOnuUniEntry 30 }

		
		sleEponStatsOnuUniRxPauseFrames64 OBJECT-TYPE
			SYNTAX Counter64
			MAX-ACCESS read-only
			STATUS current
			DESCRIPTION
				" "
			::= { sleEponStatsOnuUniEntry 31 }

		
		sleEponStatsOnuUniRxLengthErrFrames64 OBJECT-TYPE
			SYNTAX Counter64
			MAX-ACCESS read-only
			STATUS current
			DESCRIPTION
				" "
			::= { sleEponStatsOnuUniEntry 32 }

		
		sleEponStatsOnuUniRxAlignErrFrames64 OBJECT-TYPE
			SYNTAX Counter64
			MAX-ACCESS read-only
			STATUS current
			DESCRIPTION
				" "
			::= { sleEponStatsOnuUniEntry 33 }

		
		sleEponStatsOnuUniRxCrcErrFrames64 OBJECT-TYPE
			SYNTAX Counter64
			MAX-ACCESS read-only
			STATUS current
			DESCRIPTION
				" "
			::= { sleEponStatsOnuUniEntry 34 }

		
		sleEponStatsOnuPonTable OBJECT-TYPE
			SYNTAX SEQUENCE OF SleEponStatsOnuPonEntry
			MAX-ACCESS not-accessible
			STATUS current
			DESCRIPTION
				"Description."
			::= { sleEponOnuStatistics 3 }

		
		sleEponStatsOnuPonEntry OBJECT-TYPE
			SYNTAX SleEponStatsOnuPonEntry
			MAX-ACCESS not-accessible
			STATUS current
			DESCRIPTION
				"Description."
			INDEX { sleEponOltIndex, sleEponOnuIndex }
			::= { sleEponStatsOnuPonTable 1 }

		
		SleEponStatsOnuPonEntry ::=
			SEQUENCE { 
				sleEponStatsOnuPonInPkts
					Counter32,
				sleEponStatsOnuPonInBytes
					Counter32,
				sleEponStatsOnuPonInMcastPkts
					Counter32,
				sleEponStatsOnuPonIntBcastPkts
					Counter32,
				sleEponStatsOnuPonInErrPkts
					Counter32,
				sleEponStatsOnuPonInErrBytes
					Counter32,
				sleEponStatsOnuPonInPause
					Counter32,
				sleEponStatsOnuPonInHostPkts
					Counter32,
				sleEponStatsOnuPonInDropHostPkts
					Counter32,
				sleEponStatsOnuPonFrameLongError
					Counter32,
				sleEponStatsOnuPonOutPkts
					Counter32,
				sleEponStatsOnuPonOutBytes
					Counter32,
				sleEponStatsOnuPonOutMcastPkts
					Counter32,
				sleEponStatsOnuPonOutBcastPkts
					Counter32,
				sleEponStatsOnuPonOutPause
					Counter32,
				sleEponStatsOnuPonOutDropPkts
					Counter32,
				sleEponStatsOnuPonOutHostPkts
					Counter32,
				sleEponStatsOnuPonOutChipErrPkts
					Counter32,
				sleEponStatsOnuPonInDropPkts
					Counter32,
				sleEponStatsOnuPonTxOkBytes64
					Counter64,
				sleEponStatsOnuPonTxOkFrames64
					Counter64,
				sleEponStatsOnuPonTxUniFrames64
					Counter64,
				sleEponStatsOnuPonTxMulFrames64
					Counter64,
				sleEponStatsOnuPonTxBroFrames64
					Counter64,
				sleEponStatsOnuPonTxDropBytes64
					Counter64,
				sleEponStatsOnuPonTxUnusedBytes64
					Counter64,
				sleEponStatsOnuPonTxLaserPower64
					Counter64,
				sleEponStatsOnuPonTxLaserVcc64
					Counter64,
				sleEponStatsOnuPonTxLaserBias64
					Counter64,
				sleEponStatsOnuPonTxLaserTemp64
					Counter64,
				sleEponStatsOnuPonRxOkBytes64
					Counter64,
				sleEponStatsOnuPonRxOkFrames64
					Counter64,
				sleEponStatsOnuPonRxUniFrames64
					Counter64,
				sleEponStatsOnuPonRxMulFrames64
					Counter64,
				sleEponStatsOnuPonRxBroFrames64
					Counter64,
				sleEponStatsOnuPonRxUnderSizeFrames64
					Counter64,
				sleEponStatsOnuPonFcsErrFrames64
					Counter64,
				sleEponStatsOnuPonRxCrc8ErrFrames64
					Counter64,
				sleEponStatsOnuPonRxDropFrames64
					Counter64,
				sleEponStatsOnuPonRxDelayedBytes64
					Counter64,
				sleEponStatsOnuPonRxDelayMax64
					Counter64,
				sleEponStatsOnuPonRxDelayThresh64
					Counter64,
				sleEponStatsOnuPonRxErrFrames64
					Counter64,
				sleEponStatsOnuPonRxLaserPower64
					Counter64
			 }

		sleEponStatsOnuPonInPkts OBJECT-TYPE
			SYNTAX Counter32
			MAX-ACCESS read-only
			STATUS current
			DESCRIPTION
				"Description."
			::= { sleEponStatsOnuPonEntry 1 }

		
		sleEponStatsOnuPonInBytes OBJECT-TYPE
			SYNTAX Counter32
			MAX-ACCESS read-only
			STATUS current
			DESCRIPTION
				"Description."
			::= { sleEponStatsOnuPonEntry 2 }

		
		sleEponStatsOnuPonInMcastPkts OBJECT-TYPE
			SYNTAX Counter32
			MAX-ACCESS read-only
			STATUS current
			DESCRIPTION
				"Description."
			::= { sleEponStatsOnuPonEntry 3 }

		
		sleEponStatsOnuPonIntBcastPkts OBJECT-TYPE
			SYNTAX Counter32
			MAX-ACCESS read-only
			STATUS current
			DESCRIPTION
				"Description."
			::= { sleEponStatsOnuPonEntry 4 }

		
		sleEponStatsOnuPonInErrPkts OBJECT-TYPE
			SYNTAX Counter32
			MAX-ACCESS read-only
			STATUS current
			DESCRIPTION
				"Description."
			::= { sleEponStatsOnuPonEntry 5 }

		
		sleEponStatsOnuPonInErrBytes OBJECT-TYPE
			SYNTAX Counter32
			MAX-ACCESS read-only
			STATUS current
			DESCRIPTION
				"Description."
			::= { sleEponStatsOnuPonEntry 6 }

		
		sleEponStatsOnuPonInPause OBJECT-TYPE
			SYNTAX Counter32
			MAX-ACCESS read-only
			STATUS current
			DESCRIPTION
				"Description."
			::= { sleEponStatsOnuPonEntry 7 }

		
		sleEponStatsOnuPonInHostPkts OBJECT-TYPE
			SYNTAX Counter32
			MAX-ACCESS read-only
			STATUS current
			DESCRIPTION
				"Description."
			::= { sleEponStatsOnuPonEntry 8 }

		
		sleEponStatsOnuPonInDropHostPkts OBJECT-TYPE
			SYNTAX Counter32
			MAX-ACCESS read-only
			STATUS current
			DESCRIPTION
				"Description."
			::= { sleEponStatsOnuPonEntry 9 }

		
		sleEponStatsOnuPonFrameLongError OBJECT-TYPE
			SYNTAX Counter32
			MAX-ACCESS read-only
			STATUS current
			DESCRIPTION
				"Description."
			::= { sleEponStatsOnuPonEntry 10 }

		
		sleEponStatsOnuPonOutPkts OBJECT-TYPE
			SYNTAX Counter32
			MAX-ACCESS read-only
			STATUS current
			DESCRIPTION
				"Description."
			::= { sleEponStatsOnuPonEntry 11 }

		
		sleEponStatsOnuPonOutBytes OBJECT-TYPE
			SYNTAX Counter32
			MAX-ACCESS read-only
			STATUS current
			DESCRIPTION
				"Description."
			::= { sleEponStatsOnuPonEntry 12 }

		
		sleEponStatsOnuPonOutMcastPkts OBJECT-TYPE
			SYNTAX Counter32
			MAX-ACCESS read-only
			STATUS current
			DESCRIPTION
				"Description."
			::= { sleEponStatsOnuPonEntry 13 }

		
		sleEponStatsOnuPonOutBcastPkts OBJECT-TYPE
			SYNTAX Counter32
			MAX-ACCESS read-only
			STATUS current
			DESCRIPTION
				"Description."
			::= { sleEponStatsOnuPonEntry 14 }

		
		sleEponStatsOnuPonOutPause OBJECT-TYPE
			SYNTAX Counter32
			MAX-ACCESS read-only
			STATUS current
			DESCRIPTION
				"Description."
			::= { sleEponStatsOnuPonEntry 15 }

		
		sleEponStatsOnuPonOutDropPkts OBJECT-TYPE
			SYNTAX Counter32
			MAX-ACCESS read-only
			STATUS current
			DESCRIPTION
				"Description."
			::= { sleEponStatsOnuPonEntry 16 }

		
		sleEponStatsOnuPonOutHostPkts OBJECT-TYPE
			SYNTAX Counter32
			MAX-ACCESS read-only
			STATUS current
			DESCRIPTION
				"Description."
			::= { sleEponStatsOnuPonEntry 17 }

		
		sleEponStatsOnuPonOutChipErrPkts OBJECT-TYPE
			SYNTAX Counter32
			MAX-ACCESS read-only
			STATUS current
			DESCRIPTION
				"Description."
			::= { sleEponStatsOnuPonEntry 18 }

		
		sleEponStatsOnuPonInDropPkts OBJECT-TYPE
			SYNTAX Counter32
			MAX-ACCESS read-only
			STATUS current
			DESCRIPTION
				"The total number of Rx droped packest received on the ONU Pon side."
			::= { sleEponStatsOnuPonEntry 19 }

		
		sleEponStatsOnuPonTxOkBytes64 OBJECT-TYPE
			SYNTAX Counter64
			MAX-ACCESS read-only
			STATUS current
			DESCRIPTION
				" "
			::= { sleEponStatsOnuPonEntry 20 }

		
		sleEponStatsOnuPonTxOkFrames64 OBJECT-TYPE
			SYNTAX Counter64
			MAX-ACCESS read-only
			STATUS current
			DESCRIPTION
				" "
			::= { sleEponStatsOnuPonEntry 21 }

		
		sleEponStatsOnuPonTxUniFrames64 OBJECT-TYPE
			SYNTAX Counter64
			MAX-ACCESS read-only
			STATUS current
			DESCRIPTION
				" "
			::= { sleEponStatsOnuPonEntry 22 }

		
		sleEponStatsOnuPonTxMulFrames64 OBJECT-TYPE
			SYNTAX Counter64
			MAX-ACCESS read-only
			STATUS current
			DESCRIPTION
				" "
			::= { sleEponStatsOnuPonEntry 23 }

		
		sleEponStatsOnuPonTxBroFrames64 OBJECT-TYPE
			SYNTAX Counter64
			MAX-ACCESS read-only
			STATUS current
			DESCRIPTION
				" "
			::= { sleEponStatsOnuPonEntry 24 }

		
		sleEponStatsOnuPonTxDropBytes64 OBJECT-TYPE
			SYNTAX Counter64
			MAX-ACCESS read-only
			STATUS current
			DESCRIPTION
				" "
			::= { sleEponStatsOnuPonEntry 25 }

		
		sleEponStatsOnuPonTxUnusedBytes64 OBJECT-TYPE
			SYNTAX Counter64
			MAX-ACCESS read-only
			STATUS current
			DESCRIPTION
				" "
			::= { sleEponStatsOnuPonEntry 26 }

		
		sleEponStatsOnuPonTxLaserPower64 OBJECT-TYPE
			SYNTAX Counter64
			MAX-ACCESS read-only
			STATUS current
			DESCRIPTION
				" "
			::= { sleEponStatsOnuPonEntry 27 }

		
		sleEponStatsOnuPonTxLaserVcc64 OBJECT-TYPE
			SYNTAX Counter64
			MAX-ACCESS read-only
			STATUS current
			DESCRIPTION
				" "
			::= { sleEponStatsOnuPonEntry 28 }

		
		sleEponStatsOnuPonTxLaserBias64 OBJECT-TYPE
			SYNTAX Counter64
			MAX-ACCESS read-only
			STATUS current
			DESCRIPTION
				" "
			::= { sleEponStatsOnuPonEntry 29 }

		
		sleEponStatsOnuPonTxLaserTemp64 OBJECT-TYPE
			SYNTAX Counter64
			MAX-ACCESS read-only
			STATUS current
			DESCRIPTION
				" "
			::= { sleEponStatsOnuPonEntry 30 }

		
		sleEponStatsOnuPonRxOkBytes64 OBJECT-TYPE
			SYNTAX Counter64
			MAX-ACCESS read-only
			STATUS current
			DESCRIPTION
				" "
			::= { sleEponStatsOnuPonEntry 31 }

		
		sleEponStatsOnuPonRxOkFrames64 OBJECT-TYPE
			SYNTAX Counter64
			MAX-ACCESS read-only
			STATUS current
			DESCRIPTION
				" "
			::= { sleEponStatsOnuPonEntry 32 }

		
		sleEponStatsOnuPonRxUniFrames64 OBJECT-TYPE
			SYNTAX Counter64
			MAX-ACCESS read-only
			STATUS current
			DESCRIPTION
				" "
			::= { sleEponStatsOnuPonEntry 33 }

		
		sleEponStatsOnuPonRxMulFrames64 OBJECT-TYPE
			SYNTAX Counter64
			MAX-ACCESS read-only
			STATUS current
			DESCRIPTION
				" "
			::= { sleEponStatsOnuPonEntry 34 }

		
		sleEponStatsOnuPonRxBroFrames64 OBJECT-TYPE
			SYNTAX Counter64
			MAX-ACCESS read-only
			STATUS current
			DESCRIPTION
				" "
			::= { sleEponStatsOnuPonEntry 35 }

		
		sleEponStatsOnuPonRxUnderSizeFrames64 OBJECT-TYPE
			SYNTAX Counter64
			MAX-ACCESS read-only
			STATUS current
			DESCRIPTION
				" "
			::= { sleEponStatsOnuPonEntry 36 }

		
		sleEponStatsOnuPonFcsErrFrames64 OBJECT-TYPE
			SYNTAX Counter64
			MAX-ACCESS read-only
			STATUS current
			DESCRIPTION
				" "
			::= { sleEponStatsOnuPonEntry 37 }

		
		sleEponStatsOnuPonRxCrc8ErrFrames64 OBJECT-TYPE
			SYNTAX Counter64
			MAX-ACCESS read-only
			STATUS current
			DESCRIPTION
				" "
			::= { sleEponStatsOnuPonEntry 38 }

		
		sleEponStatsOnuPonRxDropFrames64 OBJECT-TYPE
			SYNTAX Counter64
			MAX-ACCESS read-only
			STATUS current
			DESCRIPTION
				" "
			::= { sleEponStatsOnuPonEntry 39 }

		
		sleEponStatsOnuPonRxDelayedBytes64 OBJECT-TYPE
			SYNTAX Counter64
			MAX-ACCESS read-only
			STATUS current
			DESCRIPTION
				" "
			::= { sleEponStatsOnuPonEntry 40 }

		
		sleEponStatsOnuPonRxDelayMax64 OBJECT-TYPE
			SYNTAX Counter64
			MAX-ACCESS read-only
			STATUS current
			DESCRIPTION
				" "
			::= { sleEponStatsOnuPonEntry 41 }

		
		sleEponStatsOnuPonRxDelayThresh64 OBJECT-TYPE
			SYNTAX Counter64
			MAX-ACCESS read-only
			STATUS current
			DESCRIPTION
				" "
			::= { sleEponStatsOnuPonEntry 42 }

		
		sleEponStatsOnuPonRxErrFrames64 OBJECT-TYPE
			SYNTAX Counter64
			MAX-ACCESS read-only
			STATUS current
			DESCRIPTION
				" "
			::= { sleEponStatsOnuPonEntry 43 }

		
		sleEponStatsOnuPonRxLaserPower64 OBJECT-TYPE
			SYNTAX Counter64
			MAX-ACCESS read-only
			STATUS current
			DESCRIPTION
				" "
			::= { sleEponStatsOnuPonEntry 44 }

		
		sleEponStatsOnuPortSumTable OBJECT-TYPE
			SYNTAX SEQUENCE OF SleEponStatsOnuPortSumEntry
			MAX-ACCESS not-accessible
			STATUS current
			DESCRIPTION
				"Description."
			::= { sleEponOnuStatistics 4 }

		
		sleEponStatsOnuPortSumEntry OBJECT-TYPE
			SYNTAX SleEponStatsOnuPortSumEntry
			MAX-ACCESS not-accessible
			STATUS current
			DESCRIPTION
				"Description."
			INDEX { sleEponOltIndex, sleEponIopOnuIndex, sleEponOnuPortIndex }
			::= { sleEponStatsOnuPortSumTable 1 }

		
		SleEponStatsOnuPortSumEntry ::=
			SEQUENCE { 
				sleEponStatsOnuPortSumTxOkBytes64
					Counter64,
				sleEponStatsOnuPortSumTxUniFrames64
					Counter64,
				sleEponStatsOnuPortSumTxMulFrames64
					Counter64,
				sleEponStatsOnuPortSumTxBroFrames64
					Counter64,
				sleEponStatsOnuPortSumRxOkBytes64
					Counter64,
				sleEponStatsOnuPortSumRxUniFrames64
					Counter64,
				sleEponStatsOnuPortSumRxMulFrames64
					Counter64,
				sleEponStatsOnuPortSumRxBroFrames64
					Counter64
			 }

		sleEponStatsOnuPortSumTxOkBytes64 OBJECT-TYPE
			SYNTAX Counter64
			MAX-ACCESS read-only
			STATUS current
			DESCRIPTION
				"The summation bytes of transmitted out of the onu port1-port4.
				"
			::= { sleEponStatsOnuPortSumEntry 1 }

		
		sleEponStatsOnuPortSumTxUniFrames64 OBJECT-TYPE
			SYNTAX Counter64
			MAX-ACCESS read-only
			STATUS current
			DESCRIPTION
				"The summation unicast packets of transmitted out of the onu port1-port4.
				"
			::= { sleEponStatsOnuPortSumEntry 2 }

		
		sleEponStatsOnuPortSumTxMulFrames64 OBJECT-TYPE
			SYNTAX Counter64
			MAX-ACCESS read-only
			STATUS current
			DESCRIPTION
				"The summation multicast packets of transmitted out of the onu port1-port4."
			::= { sleEponStatsOnuPortSumEntry 3 }

		
		sleEponStatsOnuPortSumTxBroFrames64 OBJECT-TYPE
			SYNTAX Counter64
			MAX-ACCESS read-only
			STATUS current
			DESCRIPTION
				"The summation broadcast packets of transmitted out of the onu port1-port4."
			::= { sleEponStatsOnuPortSumEntry 4 }

		
		sleEponStatsOnuPortSumRxOkBytes64 OBJECT-TYPE
			SYNTAX Counter64
			MAX-ACCESS read-only
			STATUS current
			DESCRIPTION
				"The summation bytes of received on of the onu port1-port4.
				"
			::= { sleEponStatsOnuPortSumEntry 5 }

		
		sleEponStatsOnuPortSumRxUniFrames64 OBJECT-TYPE
			SYNTAX Counter64
			MAX-ACCESS read-only
			STATUS current
			DESCRIPTION
				" The summation unicast packets of received on of the onu port1-port4.
				"
			::= { sleEponStatsOnuPortSumEntry 6 }

		
		sleEponStatsOnuPortSumRxMulFrames64 OBJECT-TYPE
			SYNTAX Counter64
			MAX-ACCESS read-only
			STATUS current
			DESCRIPTION
				" The summation multicast packets of received on of the onu port1-port4."
			::= { sleEponStatsOnuPortSumEntry 7 }

		
		sleEponStatsOnuPortSumRxBroFrames64 OBJECT-TYPE
			SYNTAX Counter64
			MAX-ACCESS read-only
			STATUS current
			DESCRIPTION
				" The summation broadcast packets of received on of the onu port1-port4."
			::= { sleEponStatsOnuPortSumEntry 8 }

		
		sleEponStatsOnuLlidTable OBJECT-TYPE
			SYNTAX SEQUENCE OF SleEponStatsOnuLlidEntry
			MAX-ACCESS not-accessible
			STATUS current
			DESCRIPTION
				"Description."
			::= { sleEponOnuStatistics 5 }

		
		sleEponStatsOnuLlidEntry OBJECT-TYPE
			SYNTAX SleEponStatsOnuLlidEntry
			MAX-ACCESS not-accessible
			STATUS current
			DESCRIPTION
				"Description."
			INDEX { sleEponOltIndex, sleEponOnuIndex, sleEponStatsOnuLlidIndex }
			::= { sleEponStatsOnuLlidTable 1 }

		
		SleEponStatsOnuLlidEntry ::=
			SEQUENCE { 
				sleEponStatsOnuLlidIndex
					Integer32,
				sleEponStatsOnuLlidTxOkBytes64
					Counter64,
				sleEponStatsOnuLlidTxOkFrames64
					Counter64,
				sleEponStatsOnuLlidTxUniFrames64
					Counter64,
				sleEponStatsOnuLlidTxMulFrames64
					Counter64,
				sleEponStatsOnuLlidTxBroFrames64
					Counter64,
				sleEponStatsOnuLlidTxTx64Byte64
					Counter64,
				sleEponStatsOnuLlidTxTx65To127Byte64
					Counter64,
				sleEponStatsOnuLlidTxTx128To255Byte64
					Counter64,
				sleEponStatsOnuLlidTxTx256To511Byte64
					Counter64,
				sleEponStatsOnuLlidTxTx512To1023Byte64
					Counter64,
				sleEponStatsOnuLlidTxTx1024To1518Byte64
					Counter64,
				sleEponStatsOnuLlidTxGreater1518Byte64
					Counter64,
				sleEponStatsOnuLlidTxDropBytes64
					Counter64,
				sleEponStatsOnuLlidTxDropFrames64
					Counter64,
				sleEponStatsOnuLlidTxDelayedBytes64
					Counter64,
				sleEponStatsOnuLlidTxDelayMax64
					Counter64,
				sleEponStatsOnuLlidTxDelayThresh64
					Counter64,
				sleEponStatsOnuLlidTxUnusedBytes64
					Counter64,
				sleEponStatsOnuLlidTxOamFrames64
					Counter64,
				sleEponStatsOnuLlidTxErrFrames64
					Counter64,
				sleEponStatsOnuLlidTxMpcpReports64
					Counter64,
				sleEponStatsOnuLlidTxMpcpRequests64
					Counter64,
				sleEponStatsOnuLlidTxMpcpRegAck64
					Counter64,
				sleEponStatsOnuLlidRxOkBytes64
					Counter64,
				sleEponStatsOnuLlidRxOkFrames64
					Counter64,
				sleEponStatsOnuLlidRxUniFrames64
					Counter64,
				sleEponStatsOnuLlidRxMulFrames64
					Counter64,
				sleEponStatsOnuLlidRxBroFrames64
					Counter64,
				sleEponStatsOnuLlidRxRx64Byte64
					Counter64,
				sleEponStatsOnuLlidRxRx65To127Byte64
					Counter64,
				sleEponStatsOnuLlidRxRx128To255Byte64
					Counter64,
				sleEponStatsOnuLlidRxRx256To511Byte64
					Counter64,
				sleEponStatsOnuLlidRxRx512To1023Byte64
					Counter64,
				sleEponStatsOnuLlidRxRx1024To1518Byte64
					Counter64,
				sleEponStatsOnuLlidRxGreater1518Byte64
					Counter64,
				sleEponStatsOnuLlidRxUnderSizeFrames64
					Counter64,
				sleEponStatsOnuLlidRxFcsErrFrames64
					Counter64,
				sleEponStatsOnuLlidRxDropBytes64
					Counter64,
				sleEponStatsOnuLlidRxDropFrames64
					Counter64,
				sleEponStatsOnuLlidRxDelayedBytes64
					Counter64,
				sleEponStatsOnuLlidRxDelayMax64
					Counter64,
				sleEponStatsOnuLlidRxDelayThresh64
					Counter64,
				sleEponStatsOnuLlidRxOamFrames64
					Counter64,
				sleEponStatsOnuLlidRxErrFrames64
					Counter64,
				sleEponStatsOnuLlidRxErrFramePeriod64
					Counter64,
				sleEponStatsOnuLlidRxErrFrameSummary64
					Counter64,
				sleEponStatsOnuLlidRxMpcpGates64
					Counter64,
				sleEponStatsOnuLlidRxMpcpRegister64
					Counter64,
				sleEponStatsOnuLlidRxLineCodeErr64
					Counter64
			 }

		sleEponStatsOnuLlidIndex OBJECT-TYPE
			SYNTAX Integer32 (1..65535)
			MAX-ACCESS read-only
			STATUS current
			DESCRIPTION
				"Description."
			::= { sleEponStatsOnuLlidEntry 1 }

		
		sleEponStatsOnuLlidTxOkBytes64 OBJECT-TYPE
			SYNTAX Counter64
			MAX-ACCESS read-only
			STATUS current
			DESCRIPTION
				"Description."
			::= { sleEponStatsOnuLlidEntry 2 }

		
		sleEponStatsOnuLlidTxOkFrames64 OBJECT-TYPE
			SYNTAX Counter64
			MAX-ACCESS read-only
			STATUS current
			DESCRIPTION
				"Description.
				"
			::= { sleEponStatsOnuLlidEntry 3 }

		
		sleEponStatsOnuLlidTxUniFrames64 OBJECT-TYPE
			SYNTAX Counter64
			MAX-ACCESS read-only
			STATUS current
			DESCRIPTION
				"Description."
			::= { sleEponStatsOnuLlidEntry 4 }

		
		sleEponStatsOnuLlidTxMulFrames64 OBJECT-TYPE
			SYNTAX Counter64
			MAX-ACCESS read-only
			STATUS current
			DESCRIPTION
				"Description."
			::= { sleEponStatsOnuLlidEntry 5 }

		
		sleEponStatsOnuLlidTxBroFrames64 OBJECT-TYPE
			SYNTAX Counter64
			MAX-ACCESS read-only
			STATUS current
			DESCRIPTION
				"Description.
				"
			::= { sleEponStatsOnuLlidEntry 6 }

		
		sleEponStatsOnuLlidTxTx64Byte64 OBJECT-TYPE
			SYNTAX Counter64
			MAX-ACCESS read-only
			STATUS current
			DESCRIPTION
				"Description."
			::= { sleEponStatsOnuLlidEntry 7 }

		
		sleEponStatsOnuLlidTxTx65To127Byte64 OBJECT-TYPE
			SYNTAX Counter64
			MAX-ACCESS read-only
			STATUS current
			DESCRIPTION
				"Description."
			::= { sleEponStatsOnuLlidEntry 8 }

		
		sleEponStatsOnuLlidTxTx128To255Byte64 OBJECT-TYPE
			SYNTAX Counter64
			MAX-ACCESS read-only
			STATUS current
			DESCRIPTION
				"Description."
			::= { sleEponStatsOnuLlidEntry 9 }

		
		sleEponStatsOnuLlidTxTx256To511Byte64 OBJECT-TYPE
			SYNTAX Counter64
			MAX-ACCESS read-only
			STATUS current
			DESCRIPTION
				"Description."
			::= { sleEponStatsOnuLlidEntry 10 }

		
		sleEponStatsOnuLlidTxTx512To1023Byte64 OBJECT-TYPE
			SYNTAX Counter64
			MAX-ACCESS read-only
			STATUS current
			DESCRIPTION
				"Description.
				"
			::= { sleEponStatsOnuLlidEntry 11 }

		
		sleEponStatsOnuLlidTxTx1024To1518Byte64 OBJECT-TYPE
			SYNTAX Counter64
			MAX-ACCESS read-only
			STATUS current
			DESCRIPTION
				"Description."
			::= { sleEponStatsOnuLlidEntry 12 }

		
		sleEponStatsOnuLlidTxGreater1518Byte64 OBJECT-TYPE
			SYNTAX Counter64
			MAX-ACCESS read-only
			STATUS current
			DESCRIPTION
				"Description.
				"
			::= { sleEponStatsOnuLlidEntry 13 }

		
		sleEponStatsOnuLlidTxDropBytes64 OBJECT-TYPE
			SYNTAX Counter64
			MAX-ACCESS read-only
			STATUS current
			DESCRIPTION
				"Description."
			::= { sleEponStatsOnuLlidEntry 14 }

		
		sleEponStatsOnuLlidTxDropFrames64 OBJECT-TYPE
			SYNTAX Counter64
			MAX-ACCESS read-only
			STATUS current
			DESCRIPTION
				"Description."
			::= { sleEponStatsOnuLlidEntry 15 }

		
		sleEponStatsOnuLlidTxDelayedBytes64 OBJECT-TYPE
			SYNTAX Counter64
			MAX-ACCESS read-only
			STATUS current
			DESCRIPTION
				"Description."
			::= { sleEponStatsOnuLlidEntry 16 }

		
		sleEponStatsOnuLlidTxDelayMax64 OBJECT-TYPE
			SYNTAX Counter64
			MAX-ACCESS read-only
			STATUS current
			DESCRIPTION
				"Description."
			::= { sleEponStatsOnuLlidEntry 17 }

		
		sleEponStatsOnuLlidTxDelayThresh64 OBJECT-TYPE
			SYNTAX Counter64
			MAX-ACCESS read-only
			STATUS current
			DESCRIPTION
				"Description."
			::= { sleEponStatsOnuLlidEntry 18 }

		
		sleEponStatsOnuLlidTxUnusedBytes64 OBJECT-TYPE
			SYNTAX Counter64
			MAX-ACCESS read-only
			STATUS current
			DESCRIPTION
				"Description."
			::= { sleEponStatsOnuLlidEntry 19 }

		
		sleEponStatsOnuLlidTxOamFrames64 OBJECT-TYPE
			SYNTAX Counter64
			MAX-ACCESS read-only
			STATUS current
			DESCRIPTION
				"Description.
				"
			::= { sleEponStatsOnuLlidEntry 20 }

		
		sleEponStatsOnuLlidTxErrFrames64 OBJECT-TYPE
			SYNTAX Counter64
			MAX-ACCESS read-only
			STATUS current
			DESCRIPTION
				"Description."
			::= { sleEponStatsOnuLlidEntry 21 }

		
		sleEponStatsOnuLlidTxMpcpReports64 OBJECT-TYPE
			SYNTAX Counter64
			MAX-ACCESS read-only
			STATUS current
			DESCRIPTION
				"Description."
			::= { sleEponStatsOnuLlidEntry 22 }

		
		sleEponStatsOnuLlidTxMpcpRequests64 OBJECT-TYPE
			SYNTAX Counter64
			MAX-ACCESS read-only
			STATUS current
			DESCRIPTION
				"Description."
			::= { sleEponStatsOnuLlidEntry 23 }

		
		sleEponStatsOnuLlidTxMpcpRegAck64 OBJECT-TYPE
			SYNTAX Counter64
			MAX-ACCESS read-only
			STATUS current
			DESCRIPTION
				"Description."
			::= { sleEponStatsOnuLlidEntry 24 }

		
		sleEponStatsOnuLlidRxOkBytes64 OBJECT-TYPE
			SYNTAX Counter64
			MAX-ACCESS read-only
			STATUS current
			DESCRIPTION
				"Description."
			::= { sleEponStatsOnuLlidEntry 25 }

		
		sleEponStatsOnuLlidRxOkFrames64 OBJECT-TYPE
			SYNTAX Counter64
			MAX-ACCESS read-only
			STATUS current
			DESCRIPTION
				"Description.
				"
			::= { sleEponStatsOnuLlidEntry 26 }

		
		sleEponStatsOnuLlidRxUniFrames64 OBJECT-TYPE
			SYNTAX Counter64
			MAX-ACCESS read-only
			STATUS current
			DESCRIPTION
				"Description."
			::= { sleEponStatsOnuLlidEntry 27 }

		
		sleEponStatsOnuLlidRxMulFrames64 OBJECT-TYPE
			SYNTAX Counter64
			MAX-ACCESS read-only
			STATUS current
			DESCRIPTION
				"Description."
			::= { sleEponStatsOnuLlidEntry 28 }

		
		sleEponStatsOnuLlidRxBroFrames64 OBJECT-TYPE
			SYNTAX Counter64
			MAX-ACCESS read-only
			STATUS current
			DESCRIPTION
				"Description.
				"
			::= { sleEponStatsOnuLlidEntry 29 }

		
		sleEponStatsOnuLlidRxRx64Byte64 OBJECT-TYPE
			SYNTAX Counter64
			MAX-ACCESS read-only
			STATUS current
			DESCRIPTION
				"Description."
			::= { sleEponStatsOnuLlidEntry 30 }

		
		sleEponStatsOnuLlidRxRx65To127Byte64 OBJECT-TYPE
			SYNTAX Counter64
			MAX-ACCESS read-only
			STATUS current
			DESCRIPTION
				"Description.
				"
			::= { sleEponStatsOnuLlidEntry 31 }

		
		sleEponStatsOnuLlidRxRx128To255Byte64 OBJECT-TYPE
			SYNTAX Counter64
			MAX-ACCESS read-only
			STATUS current
			DESCRIPTION
				"Description."
			::= { sleEponStatsOnuLlidEntry 32 }

		
		sleEponStatsOnuLlidRxRx256To511Byte64 OBJECT-TYPE
			SYNTAX Counter64
			MAX-ACCESS read-only
			STATUS current
			DESCRIPTION
				"Description.
				"
			::= { sleEponStatsOnuLlidEntry 33 }

		
		sleEponStatsOnuLlidRxRx512To1023Byte64 OBJECT-TYPE
			SYNTAX Counter64
			MAX-ACCESS read-only
			STATUS current
			DESCRIPTION
				"Description."
			::= { sleEponStatsOnuLlidEntry 34 }

		
		sleEponStatsOnuLlidRxRx1024To1518Byte64 OBJECT-TYPE
			SYNTAX Counter64
			MAX-ACCESS read-only
			STATUS current
			DESCRIPTION
				"Description.
				"
			::= { sleEponStatsOnuLlidEntry 35 }

		
		sleEponStatsOnuLlidRxGreater1518Byte64 OBJECT-TYPE
			SYNTAX Counter64
			MAX-ACCESS read-only
			STATUS current
			DESCRIPTION
				"Description."
			::= { sleEponStatsOnuLlidEntry 36 }

		
		sleEponStatsOnuLlidRxUnderSizeFrames64 OBJECT-TYPE
			SYNTAX Counter64
			MAX-ACCESS read-only
			STATUS current
			DESCRIPTION
				"Description."
			::= { sleEponStatsOnuLlidEntry 37 }

		
		sleEponStatsOnuLlidRxFcsErrFrames64 OBJECT-TYPE
			SYNTAX Counter64
			MAX-ACCESS read-only
			STATUS current
			DESCRIPTION
				"Description.
				"
			::= { sleEponStatsOnuLlidEntry 38 }

		
		sleEponStatsOnuLlidRxDropBytes64 OBJECT-TYPE
			SYNTAX Counter64
			MAX-ACCESS read-only
			STATUS current
			DESCRIPTION
				"Description."
			::= { sleEponStatsOnuLlidEntry 39 }

		
		sleEponStatsOnuLlidRxDropFrames64 OBJECT-TYPE
			SYNTAX Counter64
			MAX-ACCESS read-only
			STATUS current
			DESCRIPTION
				"Description."
			::= { sleEponStatsOnuLlidEntry 40 }

		
		sleEponStatsOnuLlidRxDelayedBytes64 OBJECT-TYPE
			SYNTAX Counter64
			MAX-ACCESS read-only
			STATUS current
			DESCRIPTION
				"Description."
			::= { sleEponStatsOnuLlidEntry 41 }

		
		sleEponStatsOnuLlidRxDelayMax64 OBJECT-TYPE
			SYNTAX Counter64
			MAX-ACCESS read-only
			STATUS current
			DESCRIPTION
				"Description.
				"
			::= { sleEponStatsOnuLlidEntry 42 }

		
		sleEponStatsOnuLlidRxDelayThresh64 OBJECT-TYPE
			SYNTAX Counter64
			MAX-ACCESS read-only
			STATUS current
			DESCRIPTION
				"Description."
			::= { sleEponStatsOnuLlidEntry 43 }

		
		sleEponStatsOnuLlidRxOamFrames64 OBJECT-TYPE
			SYNTAX Counter64
			MAX-ACCESS read-only
			STATUS current
			DESCRIPTION
				"Description.
				"
			::= { sleEponStatsOnuLlidEntry 44 }

		
		sleEponStatsOnuLlidRxErrFrames64 OBJECT-TYPE
			SYNTAX Counter64
			MAX-ACCESS read-only
			STATUS current
			DESCRIPTION
				"Description.
				"
			::= { sleEponStatsOnuLlidEntry 45 }

		
		sleEponStatsOnuLlidRxErrFramePeriod64 OBJECT-TYPE
			SYNTAX Counter64
			MAX-ACCESS read-only
			STATUS current
			DESCRIPTION
				"Description."
			::= { sleEponStatsOnuLlidEntry 46 }

		
		sleEponStatsOnuLlidRxErrFrameSummary64 OBJECT-TYPE
			SYNTAX Counter64
			MAX-ACCESS read-only
			STATUS current
			DESCRIPTION
				"Description."
			::= { sleEponStatsOnuLlidEntry 47 }

		
		sleEponStatsOnuLlidRxMpcpGates64 OBJECT-TYPE
			SYNTAX Counter64
			MAX-ACCESS read-only
			STATUS current
			DESCRIPTION
				"Description."
			::= { sleEponStatsOnuLlidEntry 48 }

		
		sleEponStatsOnuLlidRxMpcpRegister64 OBJECT-TYPE
			SYNTAX Counter64
			MAX-ACCESS read-only
			STATUS current
			DESCRIPTION
				"Description."
			::= { sleEponStatsOnuLlidEntry 49 }

		
		sleEponStatsOnuLlidRxLineCodeErr64 OBJECT-TYPE
			SYNTAX Counter64
			MAX-ACCESS read-only
			STATUS current
			DESCRIPTION
				"Description."
			::= { sleEponStatsOnuLlidEntry 50 }

		
		sleEponPerTimeStatistics OBJECT IDENTIFIER ::= { sleEponStatistics 3 }

		
		sleEponPTimeStatsPortTable OBJECT-TYPE
			SYNTAX SEQUENCE OF SleEponPTimeStatsPortEntry
			MAX-ACCESS not-accessible
			STATUS current
			DESCRIPTION
				"Description."
			::= { sleEponPerTimeStatistics 1 }

		
		sleEponPTimeStatsPortEntry OBJECT-TYPE
			SYNTAX SleEponPTimeStatsPortEntry
			MAX-ACCESS not-accessible
			STATUS current
			DESCRIPTION
				"Description."
			INDEX { ifIndex }
			::= { sleEponPTimeStatsPortTable 1 }

		
		SleEponPTimeStatsPortEntry ::=
			SEQUENCE { 
				sleEponPTimeStatsPortSaveTime
					Gauge32,
				sleEponPTimeStatsPortHourInOctets
					Counter64,
				sleEponPTimeStatsPortHourOutOctets
					Counter64,
				sleEponPTimeStatsPortDayInOctets
					Counter64,
				sleEponPTimeStatsPortDayOutOctets
					Counter64
			 }

		sleEponPTimeStatsPortSaveTime OBJECT-TYPE
			SYNTAX Gauge32
			MAX-ACCESS read-only
			STATUS current
			DESCRIPTION
				"Description."
			::= { sleEponPTimeStatsPortEntry 1 }

		
		sleEponPTimeStatsPortHourInOctets OBJECT-TYPE
			SYNTAX Counter64
			MAX-ACCESS read-only
			STATUS current
			DESCRIPTION
				"Description."
			::= { sleEponPTimeStatsPortEntry 2 }

		
		sleEponPTimeStatsPortHourOutOctets OBJECT-TYPE
			SYNTAX Counter64
			MAX-ACCESS read-only
			STATUS current
			DESCRIPTION
				"Description."
			::= { sleEponPTimeStatsPortEntry 3 }

		
		sleEponPTimeStatsPortDayInOctets OBJECT-TYPE
			SYNTAX Counter64
			MAX-ACCESS read-only
			STATUS current
			DESCRIPTION
				"Description."
			::= { sleEponPTimeStatsPortEntry 4 }

		
		sleEponPTimeStatsPortDayOutOctets OBJECT-TYPE
			SYNTAX Counter64
			MAX-ACCESS read-only
			STATUS current
			DESCRIPTION
				"Description."
			::= { sleEponPTimeStatsPortEntry 5 }

		
		sleEponPTimeStatsOltTable OBJECT-TYPE
			SYNTAX SEQUENCE OF SleEponPTimeStatsOltEntry
			MAX-ACCESS not-accessible
			STATUS current
			DESCRIPTION
				"Description."
			::= { sleEponPerTimeStatistics 2 }

		
		sleEponPTimeStatsOltEntry OBJECT-TYPE
			SYNTAX SleEponPTimeStatsOltEntry
			MAX-ACCESS not-accessible
			STATUS current
			DESCRIPTION
				"Description."
			INDEX { sleEponOltIndex }
			::= { sleEponPTimeStatsOltTable 1 }

		
		SleEponPTimeStatsOltEntry ::=
			SEQUENCE { 
				sleEponPTimeStatsOltSaveTime
					Gauge32,
				sleEponPTimeStatsOltHourInOctets
					Counter64,
				sleEponPTimeStatsOltHourOutOctets
					Counter64,
				sleEponPTimeStatsOltDayInOctets
					Counter64,
				sleEponPTimeStatsOltDayOutOctets
					Counter64
			 }

		sleEponPTimeStatsOltSaveTime OBJECT-TYPE
			SYNTAX Gauge32
			MAX-ACCESS read-only
			STATUS current
			DESCRIPTION
				"Description."
			::= { sleEponPTimeStatsOltEntry 1 }

		
		sleEponPTimeStatsOltHourInOctets OBJECT-TYPE
			SYNTAX Counter64
			MAX-ACCESS read-only
			STATUS current
			DESCRIPTION
				"Description."
			::= { sleEponPTimeStatsOltEntry 2 }

		
		sleEponPTimeStatsOltHourOutOctets OBJECT-TYPE
			SYNTAX Counter64
			MAX-ACCESS read-only
			STATUS current
			DESCRIPTION
				"Description."
			::= { sleEponPTimeStatsOltEntry 3 }

		
		sleEponPTimeStatsOltDayInOctets OBJECT-TYPE
			SYNTAX Counter64
			MAX-ACCESS read-only
			STATUS current
			DESCRIPTION
				"Description."
			::= { sleEponPTimeStatsOltEntry 4 }

		
		sleEponPTimeStatsOltDayOutOctets OBJECT-TYPE
			SYNTAX Counter64
			MAX-ACCESS read-only
			STATUS current
			DESCRIPTION
				"Description."
			::= { sleEponPTimeStatsOltEntry 5 }

		
		sleEponPTimeStatsOnuTable OBJECT-TYPE
			SYNTAX SEQUENCE OF SleEponPTimeStatsOnuEntry
			MAX-ACCESS not-accessible
			STATUS current
			DESCRIPTION
				"Description."
			::= { sleEponPerTimeStatistics 3 }

		
		sleEponPTimeStatsOnuEntry OBJECT-TYPE
			SYNTAX SleEponPTimeStatsOnuEntry
			MAX-ACCESS not-accessible
			STATUS current
			DESCRIPTION
				"Description."
			INDEX { sleEponOltIndex, sleEponOnuIndex }
			::= { sleEponPTimeStatsOnuTable 1 }

		
		SleEponPTimeStatsOnuEntry ::=
			SEQUENCE { 
				sleEponPTimeStatsOnuSaveTime
					Gauge32,
				sleEponPTimeStatsOnuHourInOctets
					Counter64,
				sleEponPTimeStatsOnuHourOutOctets
					Counter64,
				sleEponPTimeStatsOnuDayInOctets
					Counter64,
				sleEponPTimeStatsOnuDayOutOctets
					Counter64
			 }

		sleEponPTimeStatsOnuSaveTime OBJECT-TYPE
			SYNTAX Gauge32
			MAX-ACCESS read-only
			STATUS current
			DESCRIPTION
				"Description."
			::= { sleEponPTimeStatsOnuEntry 1 }

		
		sleEponPTimeStatsOnuHourInOctets OBJECT-TYPE
			SYNTAX Counter64
			MAX-ACCESS read-only
			STATUS current
			DESCRIPTION
				"Description."
			::= { sleEponPTimeStatsOnuEntry 2 }

		
		sleEponPTimeStatsOnuHourOutOctets OBJECT-TYPE
			SYNTAX Counter64
			MAX-ACCESS read-only
			STATUS current
			DESCRIPTION
				"Description."
			::= { sleEponPTimeStatsOnuEntry 3 }

		
		sleEponPTimeStatsOnuDayInOctets OBJECT-TYPE
			SYNTAX Counter64
			MAX-ACCESS read-only
			STATUS current
			DESCRIPTION
				"Description."
			::= { sleEponPTimeStatsOnuEntry 4 }

		
		sleEponPTimeStatsOnuDayOutOctets OBJECT-TYPE
			SYNTAX Counter64
			MAX-ACCESS read-only
			STATUS current
			DESCRIPTION
				"Description."
			::= { sleEponPTimeStatsOnuEntry 5 }

		
		sleEponPTimeStatsInfo OBJECT IDENTIFIER ::= { sleEponPerTimeStatistics 4 }

		
		sleEponPTimeStatsBase OBJECT IDENTIFIER ::= { sleEponPTimeStatsInfo 1 }

		
		sleEponPTimeStatsServiceActivity OBJECT-TYPE
			SYNTAX EnableFlag
			MAX-ACCESS read-only
			STATUS current
			DESCRIPTION
				"Description."
			::= { sleEponPTimeStatsBase 1 }

		
		sleEponPTimeStatsControl OBJECT IDENTIFIER ::= { sleEponPTimeStatsInfo 2 }

		
		sleEponPTimeStatsControlRequest OBJECT-TYPE
			SYNTAX INTEGER
				{
				setEponPerTimeStatisticsServiceActivity(1),
				clearEponPerTimeStatistics(2)
				}
			MAX-ACCESS read-write
			STATUS current
			DESCRIPTION
				"Description."
			::= { sleEponPTimeStatsControl 1 }

		
		sleEponPTimeStatsControlStatus OBJECT-TYPE
			SYNTAX SleControlStatusType
			MAX-ACCESS read-only
			STATUS current
			DESCRIPTION
				"Description."
			::= { sleEponPTimeStatsControl 2 }

		
		sleEponPTimeStatsControlTimer OBJECT-TYPE
			SYNTAX Gauge32
			MAX-ACCESS read-write
			STATUS current
			DESCRIPTION
				"Description."
			::= { sleEponPTimeStatsControl 3 }

		
		sleEponPTimeStatsControlTimeStamp OBJECT-TYPE
			SYNTAX TimeTicks
			MAX-ACCESS read-only
			STATUS current
			DESCRIPTION
				"Description."
			::= { sleEponPTimeStatsControl 4 }

		
		sleEponPTimeStatsControlReqResult OBJECT-TYPE
			SYNTAX SleControlRequestResultType
			MAX-ACCESS read-only
			STATUS current
			DESCRIPTION
				"Description."
			::= { sleEponPTimeStatsControl 5 }

		
		sleEponPTimeStatsControlServiceActivity OBJECT-TYPE
			SYNTAX EnableFlag
			MAX-ACCESS read-write
			STATUS current
			DESCRIPTION
				"Description."
			::= { sleEponPTimeStatsControl 6 }

		
		sleEponPTimeStatsNotification OBJECT IDENTIFIER ::= { sleEponPTimeStatsInfo 3 }

		
		sleEponPTimeStatsServiceActivityChanged NOTIFICATION-TYPE
			OBJECTS { sleEponPTimeStatsControlRequest, sleEponPTimeStatsControlTimeStamp, sleEponPTimeStatsControlReqResult, sleEponPTimeStatsControlServiceActivity }
			STATUS current
			DESCRIPTION 
				"Description."
			::= { sleEponPTimeStatsNotification 1 }

		
		sleEponPTimeStatsCleared NOTIFICATION-TYPE
			OBJECTS { sleEponPTimeStatsControlRequest, sleEponPTimeStatsControlTimeStamp, sleEponPTimeStatsControlReqResult }
			STATUS current
			DESCRIPTION 
				"Description."
			::= { sleEponPTimeStatsNotification 2 }

		
		sleEponOnuClassification OBJECT IDENTIFIER ::= { sleEpon 8 }

		
		sleEponOnuClassificationTable OBJECT-TYPE
			SYNTAX SEQUENCE OF SleEponOnuClassificationEntry
			MAX-ACCESS not-accessible
			STATUS current
			DESCRIPTION
				"Description."
			::= { sleEponOnuClassification 1 }

		
		sleEponOnuClassificationEntry OBJECT-TYPE
			SYNTAX SleEponOnuClassificationEntry
			MAX-ACCESS not-accessible
			STATUS current
			DESCRIPTION
				"Description."
			INDEX { sleEponOnuClassificationIndex }
			::= { sleEponOnuClassificationTable 1 }

		
		SleEponOnuClassificationEntry ::=
			SEQUENCE { 
				sleEponOnuClassificationIndex
					INTEGER,
				sleEponOnuClassificationName
					OCTET STRING,
				sleEponOnuClassificationTrafficDirection
					INTEGER,
				sleEponOnuClassificationLayer
					INTEGER,
				sleEponOnuClassificationEtherType
					Integer32,
				sleEponOnuClassificationProtoTypeNum
					INTEGER,
				sleEponOnuClassificationL3Addr
					IpAddress,
				sleEponOnuClassificationL4Num
					Integer32,
				sleEponOnuClassificationL3Mask
					Integer32,
				sleEponOnuClassificationCos
					Integer32,
				sleEponOnuClassificationVid
					Integer32
			 }

		sleEponOnuClassificationIndex OBJECT-TYPE
			SYNTAX INTEGER (1..256)
			MAX-ACCESS read-only
			STATUS current
			DESCRIPTION
				"Description."
			::= { sleEponOnuClassificationEntry 1 }

		
		sleEponOnuClassificationName OBJECT-TYPE
			SYNTAX OCTET STRING (SIZE (1..32))
			MAX-ACCESS read-only
			STATUS current
			DESCRIPTION
				"Description."
			::= { sleEponOnuClassificationEntry 2 }

		
		sleEponOnuClassificationTrafficDirection OBJECT-TYPE
			SYNTAX INTEGER
				{
				downstream(1),
				upstream(2)
				}
			MAX-ACCESS read-only
			STATUS current
			DESCRIPTION
				"Description."
			::= { sleEponOnuClassificationEntry 3 }

		
		sleEponOnuClassificationLayer OBJECT-TYPE
			SYNTAX INTEGER
				{
				etherType(1),
				protoType(2),
				layer3Destination(3),
				layer3Source(4),
				layer4Tcp(5),
				layer4Udp(6),
				layer2Cos(7),
				layer2vid(8)
				}
			MAX-ACCESS read-only
			STATUS current
			DESCRIPTION
				"Description."
			::= { sleEponOnuClassificationEntry 4 }

		
		sleEponOnuClassificationEtherType OBJECT-TYPE
			SYNTAX Integer32
			MAX-ACCESS read-only
			STATUS current
			DESCRIPTION
				"Description."
			::= { sleEponOnuClassificationEntry 5 }

		
		sleEponOnuClassificationProtoTypeNum OBJECT-TYPE
			SYNTAX INTEGER (0 | 1..255)
			MAX-ACCESS read-only
			STATUS current
			DESCRIPTION
				"Description."
			::= { sleEponOnuClassificationEntry 6 }

		
		sleEponOnuClassificationL3Addr OBJECT-TYPE
			SYNTAX IpAddress
			MAX-ACCESS read-only
			STATUS current
			DESCRIPTION
				"Description."
			::= { sleEponOnuClassificationEntry 7 }

		
		sleEponOnuClassificationL4Num OBJECT-TYPE
			SYNTAX Integer32
			MAX-ACCESS read-only
			STATUS current
			DESCRIPTION
				"Description."
			::= { sleEponOnuClassificationEntry 8 }

		
		sleEponOnuClassificationL3Mask OBJECT-TYPE
			SYNTAX Integer32 (1..32)
			MAX-ACCESS read-only
			STATUS current
			DESCRIPTION
				"Description."
			::= { sleEponOnuClassificationEntry 9 }

		
		sleEponOnuClassificationCos OBJECT-TYPE
			SYNTAX Integer32 (0..7)
			MAX-ACCESS read-only
			STATUS current
			DESCRIPTION
				"Description."
			::= { sleEponOnuClassificationEntry 10 }

		
		sleEponOnuClassificationVid OBJECT-TYPE
			SYNTAX Integer32 (1..4094)
			MAX-ACCESS read-only
			STATUS current
			DESCRIPTION
				"Description."
			::= { sleEponOnuClassificationEntry 11 }

		
		sleEponOnuClassificationControl OBJECT IDENTIFIER ::= { sleEponOnuClassification 2 }

		
		sleEponOnuClassificationControlRequest OBJECT-TYPE
			SYNTAX INTEGER
				{
				createOnuClassification(1),
				destroyOnuClassification(2)
				}
			MAX-ACCESS read-write
			STATUS current
			DESCRIPTION
				"The request of a user command"
			::= { sleEponOnuClassificationControl 1 }

		
		sleEponOnuClassificationControlStatus OBJECT-TYPE
			SYNTAX SleControlStatusType
			MAX-ACCESS read-only
			STATUS current
			DESCRIPTION
				"The status of user command"
			::= { sleEponOnuClassificationControl 2 }

		
		sleEponOnuClassificationControlTimer OBJECT-TYPE
			SYNTAX Gauge32
			MAX-ACCESS read-write
			STATUS current
			DESCRIPTION
				"The maximum time for the manager for a long running user command"
			::= { sleEponOnuClassificationControl 3 }

		
		sleEponOnuClassificationControlTimeStamp OBJECT-TYPE
			SYNTAX TimeTicks
			MAX-ACCESS read-only
			STATUS current
			DESCRIPTION
				"The time stamp of the last command(end of command)"
			::= { sleEponOnuClassificationControl 4 }

		
		sleEponOnuClassificationControlReqResult OBJECT-TYPE
			SYNTAX SleControlRequestResultType
			MAX-ACCESS read-only
			STATUS current
			DESCRIPTION
				"The result of the last user command"
			::= { sleEponOnuClassificationControl 5 }

		
		sleEponOnuClassificationControlName OBJECT-TYPE
			SYNTAX OCTET STRING (SIZE (1..32))
			MAX-ACCESS read-write
			STATUS current
			DESCRIPTION
				"Description."
			::= { sleEponOnuClassificationControl 6 }

		
		sleEponOnuClassificationControlTrafficDirection OBJECT-TYPE
			SYNTAX INTEGER
				{
				downstream(1),
				upstream(2)
				}
			MAX-ACCESS read-write
			STATUS current
			DESCRIPTION
				"Description."
			::= { sleEponOnuClassificationControl 7 }

		
		sleEponOnuClassificationControlLayer OBJECT-TYPE
			SYNTAX INTEGER
				{
				etherType(1),
				protoType(2),
				layer3Destination(3),
				layer3Source(4),
				layer4Tcp(5),
				layer4Udp(6),
				layer2Cos(7),
				layer2Vid(8)
				}
			MAX-ACCESS read-write
			STATUS current
			DESCRIPTION
				"Description."
			::= { sleEponOnuClassificationControl 8 }

		
		sleEponOnuClassificationControlEtherType OBJECT-TYPE
			SYNTAX Integer32
			MAX-ACCESS read-write
			STATUS current
			DESCRIPTION
				"Description."
			::= { sleEponOnuClassificationControl 9 }

		
		sleEponOnuClassificationControlProtoTypeNum OBJECT-TYPE
			SYNTAX INTEGER (0 | 1..255)
			MAX-ACCESS read-write
			STATUS current
			DESCRIPTION
				"Description."
			::= { sleEponOnuClassificationControl 10 }

		
		sleEponOnuClassificationControlL3Addr OBJECT-TYPE
			SYNTAX IpAddress
			MAX-ACCESS read-write
			STATUS current
			DESCRIPTION
				"Description."
			::= { sleEponOnuClassificationControl 11 }

		
		sleEponOnuClassificationControlL4Num OBJECT-TYPE
			SYNTAX Integer32
			MAX-ACCESS read-write
			STATUS current
			DESCRIPTION
				"Description."
			::= { sleEponOnuClassificationControl 12 }

		
		sleEponOnuClassificationControlL3Mask OBJECT-TYPE
			SYNTAX Integer32 (1..32)
			MAX-ACCESS read-write
			STATUS current
			DESCRIPTION
				"Description."
			::= { sleEponOnuClassificationControl 13 }

		
		sleEponOnuClassificationControlCos OBJECT-TYPE
			SYNTAX Integer32 (0..7)
			MAX-ACCESS read-write
			STATUS current
			DESCRIPTION
				"Description."
			::= { sleEponOnuClassificationControl 14 }

		
		sleEponOnuClassificationControlVid OBJECT-TYPE
			SYNTAX Integer32 (1..4094)
			MAX-ACCESS read-write
			STATUS current
			DESCRIPTION
				"Description."
			::= { sleEponOnuClassificationControl 15 }

		
		sleEponOnuClassificationNotification OBJECT IDENTIFIER ::= { sleEponOnuClassification 3 }

		
		sleEponOnuClassificationCreated NOTIFICATION-TYPE
			OBJECTS { sleEponOnuClassificationControlName }
			STATUS current
			DESCRIPTION 
				"Description."
			::= { sleEponOnuClassificationNotification 1 }

		
		sleEponOnuClassificationDestroyed NOTIFICATION-TYPE
			OBJECTS { sleEponOnuClassificationControlName }
			STATUS current
			DESCRIPTION 
				"Description."
			::= { sleEponOnuClassificationNotification 2 }

		
		sleEponVlan OBJECT IDENTIFIER ::= { sleEpon 9 }

		
		sleEponVlanOltVlan OBJECT IDENTIFIER ::= { sleEponVlan 1 }

		
		sleEponVlanOltVlanTable OBJECT-TYPE
			SYNTAX SEQUENCE OF SleEponVlanOltVlanEntry
			MAX-ACCESS not-accessible
			STATUS current
			DESCRIPTION
				"Description."
			::= { sleEponVlanOltVlan 1 }

		
		sleEponVlanOltVlanEntry OBJECT-TYPE
			SYNTAX SleEponVlanOltVlanEntry
			MAX-ACCESS not-accessible
			STATUS current
			DESCRIPTION
				"Description."
			INDEX { sleEponOltIndex, sleEponOnuIndex }
			::= { sleEponVlanOltVlanTable 1 }

		
		SleEponVlanOltVlanEntry ::=
			SEQUENCE { 
				sleEponVlanOltVlanMode
					INTEGER,
				sleEponVlanOltVlanNestedStack
					EnableFlag,
				sleEponVlanOltVlanPrefix
					INTEGER,
				sleEponVlanOltVlanSuffix
					INTEGER,
				sleEponVlanOltVlanTag
					INTEGER,
				sleEponVlanOltVlanEtherType
					INTEGER
			 }

		sleEponVlanOltVlanMode OBJECT-TYPE
			SYNTAX INTEGER
				{
				none(0),
				exchange(1),
				stack(2)
				}
			MAX-ACCESS read-only
			STATUS current
			DESCRIPTION
				"Description."
			::= { sleEponVlanOltVlanEntry 1 }

		
		sleEponVlanOltVlanNestedStack OBJECT-TYPE
			SYNTAX EnableFlag
			MAX-ACCESS read-only
			STATUS current
			DESCRIPTION
				"Description."
			::= { sleEponVlanOltVlanEntry 2 }

		
		sleEponVlanOltVlanPrefix OBJECT-TYPE
			SYNTAX INTEGER (-1 | 0..255)
			MAX-ACCESS read-only
			STATUS current
			DESCRIPTION
				"Description."
			::= { sleEponVlanOltVlanEntry 3 }

		
		sleEponVlanOltVlanSuffix OBJECT-TYPE
			SYNTAX INTEGER (-1 | 0..15)
			MAX-ACCESS read-only
			STATUS current
			DESCRIPTION
				"Description."
			::= { sleEponVlanOltVlanEntry 4 }

		
		sleEponVlanOltVlanTag OBJECT-TYPE
			SYNTAX INTEGER (-1 | 1..4096)
			MAX-ACCESS read-only
			STATUS current
			DESCRIPTION
				"Description."
			::= { sleEponVlanOltVlanEntry 5 }

		
		sleEponVlanOltVlanEtherType OBJECT-TYPE
			SYNTAX INTEGER
				{
				none(0),
				etherType0x8100(1),
				etherType0x9100(2)
				}
			MAX-ACCESS read-only
			STATUS current
			DESCRIPTION
				"Description."
			::= { sleEponVlanOltVlanEntry 6 }

		
		sleEponVlanOltVlanControl OBJECT IDENTIFIER ::= { sleEponVlanOltVlan 2 }

		
		sleEponVlanOltVlanControlRequest OBJECT-TYPE
			SYNTAX INTEGER
				{
				setEponVlanOltVlanPrefix(1),
				setEponVlanOltVlanProfile(2)
				}
			MAX-ACCESS read-write
			STATUS current
			DESCRIPTION
				"Description."
			::= { sleEponVlanOltVlanControl 1 }

		
		sleEponVlanOltVlanControlStatus OBJECT-TYPE
			SYNTAX SleControlStatusType
			MAX-ACCESS read-only
			STATUS current
			DESCRIPTION
				"Description."
			::= { sleEponVlanOltVlanControl 2 }

		
		sleEponVlanOltVlanControlTimer OBJECT-TYPE
			SYNTAX Gauge32
			MAX-ACCESS read-write
			STATUS current
			DESCRIPTION
				"Description."
			::= { sleEponVlanOltVlanControl 3 }

		
		sleEponVlanOltVlanControlTimeStamp OBJECT-TYPE
			SYNTAX TimeTicks
			MAX-ACCESS read-only
			STATUS current
			DESCRIPTION
				"Description."
			::= { sleEponVlanOltVlanControl 4 }

		
		sleEponVlanOltVlanControlReqResult OBJECT-TYPE
			SYNTAX SleControlRequestResultType
			MAX-ACCESS read-only
			STATUS current
			DESCRIPTION
				"Description."
			::= { sleEponVlanOltVlanControl 5 }

		
		sleEponVlanOltVlanControlOltIndex OBJECT-TYPE
			SYNTAX INTEGER (1..512)
			MAX-ACCESS read-write
			STATUS current
			DESCRIPTION
				"Description."
			::= { sleEponVlanOltVlanControl 6 }

		
		sleEponVlanOltVlanControlOnuIndex OBJECT-TYPE
			SYNTAX INTEGER (1..64)
			MAX-ACCESS read-write
			STATUS current
			DESCRIPTION
				"Description."
			::= { sleEponVlanOltVlanControl 7 }

		
		sleEponVlanOltVlanControlMode OBJECT-TYPE
			SYNTAX INTEGER
				{
				none(0),
				exchange(1),
				stack(2)
				}
			MAX-ACCESS read-write
			STATUS current
			DESCRIPTION
				"Description."
			::= { sleEponVlanOltVlanControl 8 }

		
		sleEponVlanOltVlanControlNestedStack OBJECT-TYPE
			SYNTAX EnableFlag
			MAX-ACCESS read-write
			STATUS current
			DESCRIPTION
				"Description."
			::= { sleEponVlanOltVlanControl 9 }

		
		sleEponVlanOltVlanControlPrefix OBJECT-TYPE
			SYNTAX INTEGER (-1 | 0..255)
			MAX-ACCESS read-write
			STATUS current
			DESCRIPTION
				"Description."
			::= { sleEponVlanOltVlanControl 10 }

		
		sleEponVlanOltVlanControlSuffix OBJECT-TYPE
			SYNTAX INTEGER (-1 | 0..15)
			MAX-ACCESS read-write
			STATUS current
			DESCRIPTION
				"Description."
			::= { sleEponVlanOltVlanControl 11 }

		
		sleEponVlanOltVlanControlVlanTag OBJECT-TYPE
			SYNTAX INTEGER (-1 | 1..4094)
			MAX-ACCESS read-write
			STATUS current
			DESCRIPTION
				"Description."
			::= { sleEponVlanOltVlanControl 12 }

		
		sleEponVlanOltVlanControlEtherType OBJECT-TYPE
			SYNTAX INTEGER
				{
				none(0),
				etherType0x8100(1),
				etherType0x9100(2)
				}
			MAX-ACCESS read-write
			STATUS current
			DESCRIPTION
				"Description."
			::= { sleEponVlanOltVlanControl 13 }

		
		sleEponVlanOltVlanNotification OBJECT IDENTIFIER ::= { sleEponVlanOltVlan 3 }

		
		sleEponVlanOltVlanPrefixChanged NOTIFICATION-TYPE
			OBJECTS { sleEponVlanOltVlanControlRequest, sleEponVlanOltVlanControlTimeStamp, sleEponVlanOltVlanControlReqResult, sleEponVlanOltVlanControlOltIndex, sleEponVlanOltVlanControlPrefix
				 }
			STATUS current
			DESCRIPTION 
				"Description."
			::= { sleEponVlanOltVlanNotification 1 }

		
		sleEponVlanOltVlanProfileChanged NOTIFICATION-TYPE
			OBJECTS { sleEponVlanOltVlanControlRequest, sleEponVlanOltVlanControlTimeStamp, sleEponVlanOltVlanControlReqResult, sleEponVlanOltVlanControlOltIndex, sleEponVlanOltVlanControlOnuIndex, 
				sleEponVlanOltVlanControlMode, sleEponVlanOltVlanControlNestedStack, sleEponVlanOltVlanControlSuffix, sleEponVlanOltVlanControlVlanTag, sleEponVlanOltVlanControlEtherType
				 }
			STATUS current
			DESCRIPTION 
				"Description."
			::= { sleEponVlanOltVlanNotification 2 }

		
		sleEponVlanOnuVlan OBJECT IDENTIFIER ::= { sleEponVlan 2 }

		
		sleEponVlanOnuVlanTable OBJECT-TYPE
			SYNTAX SEQUENCE OF SleEponVlanOnuVlanEntry
			MAX-ACCESS not-accessible
			STATUS current
			DESCRIPTION
				"Description."
			::= { sleEponVlanOnuVlan 1 }

		
		sleEponVlanOnuVlanEntry OBJECT-TYPE
			SYNTAX SleEponVlanOnuVlanEntry
			MAX-ACCESS not-accessible
			STATUS current
			DESCRIPTION
				"Description."
			INDEX { sleEponOltIndex, sleEponOnuIndex }
			::= { sleEponVlanOnuVlanTable 1 }

		
		SleEponVlanOnuVlanEntry ::=
			SEQUENCE { 
				sleEponVlanOnuVlanUpMode
					INTEGER,
				sleEponVlanOnuVlanUpVlanTag
					INTEGER,
				sleEponVlanOnuVlanUpEtherType
					INTEGER,
				sleEponVlanOnuVlanUpPriority
					Integer32,
				sleEponVlanOnuVlanDownMode
					INTEGER,
				sleEponVlanOnuVlanDownVlanTag
					INTEGER,
				sleEponVlanOnuVlanDownPriority
					Integer32
			 }

		sleEponVlanOnuVlanUpMode OBJECT-TYPE
			SYNTAX INTEGER
				{
				none(0),
				exchange(1),
				stack(2)
				}
			MAX-ACCESS read-only
			STATUS current
			DESCRIPTION
				"Description."
			::= { sleEponVlanOnuVlanEntry 1 }

		
		sleEponVlanOnuVlanUpVlanTag OBJECT-TYPE
			SYNTAX INTEGER (-1 | 1..4094)
			MAX-ACCESS read-only
			STATUS current
			DESCRIPTION
				"Description."
			::= { sleEponVlanOnuVlanEntry 2 }

		
		sleEponVlanOnuVlanUpEtherType OBJECT-TYPE
			SYNTAX INTEGER
				{
				none(0),
				etherType0x8100(1),
				etherType0x9100(2)
				}
			MAX-ACCESS read-only
			STATUS current
			DESCRIPTION
				"Description."
			::= { sleEponVlanOnuVlanEntry 3 }

		
		sleEponVlanOnuVlanUpPriority OBJECT-TYPE
			SYNTAX Integer32
			MAX-ACCESS read-only
			STATUS current
			DESCRIPTION
				"Description."
			::= { sleEponVlanOnuVlanEntry 4 }

		
		sleEponVlanOnuVlanDownMode OBJECT-TYPE
			SYNTAX INTEGER
				{
				none(0),
				exchange(1),
				stack(2)
				}
			MAX-ACCESS read-only
			STATUS current
			DESCRIPTION
				"Description."
			::= { sleEponVlanOnuVlanEntry 5 }

		
		sleEponVlanOnuVlanDownVlanTag OBJECT-TYPE
			SYNTAX INTEGER (-1 | 1..4094)
			MAX-ACCESS read-only
			STATUS current
			DESCRIPTION
				"Description."
			::= { sleEponVlanOnuVlanEntry 6 }

		
		sleEponVlanOnuVlanDownPriority OBJECT-TYPE
			SYNTAX Integer32
			MAX-ACCESS read-write
			STATUS current
			DESCRIPTION
				"Description."
			::= { sleEponVlanOnuVlanEntry 7 }

		
		sleEponVlanOnuVlanControl OBJECT IDENTIFIER ::= { sleEponVlanOnuVlan 2 }

		
		sleEponVlanOnuVlanControlRequest OBJECT-TYPE
			SYNTAX INTEGER { setEponVlanOnuVlanProfile(1) }
			MAX-ACCESS read-write
			STATUS current
			DESCRIPTION
				"Description."
			::= { sleEponVlanOnuVlanControl 1 }

		
		sleEponVlanOnuVlanControlStatus OBJECT-TYPE
			SYNTAX SleControlStatusType
			MAX-ACCESS read-only
			STATUS current
			DESCRIPTION
				"Description."
			::= { sleEponVlanOnuVlanControl 2 }

		
		sleEponVlanOnuVlanControlTimer OBJECT-TYPE
			SYNTAX Gauge32
			MAX-ACCESS read-write
			STATUS current
			DESCRIPTION
				"Description."
			::= { sleEponVlanOnuVlanControl 3 }

		
		sleEponVlanOnuVlanControlTimeStamp OBJECT-TYPE
			SYNTAX TimeTicks
			MAX-ACCESS read-only
			STATUS current
			DESCRIPTION
				"Description."
			::= { sleEponVlanOnuVlanControl 4 }

		
		sleEponVlanOnuVlanControlReqResult OBJECT-TYPE
			SYNTAX SleControlRequestResultType
			MAX-ACCESS read-only
			STATUS current
			DESCRIPTION
				"Description."
			::= { sleEponVlanOnuVlanControl 5 }

		
		sleEponVlanOnuVlanControlOltIndex OBJECT-TYPE
			SYNTAX INTEGER (1..512)
			MAX-ACCESS read-write
			STATUS current
			DESCRIPTION
				"Description."
			::= { sleEponVlanOnuVlanControl 6 }

		
		sleEponVlanOnuVlanControlOnuIndex OBJECT-TYPE
			SYNTAX INTEGER (1..64)
			MAX-ACCESS read-write
			STATUS current
			DESCRIPTION
				"Description."
			::= { sleEponVlanOnuVlanControl 7 }

		
		sleEponVlanOnuVlanControlUpMode OBJECT-TYPE
			SYNTAX INTEGER
				{
				none(0),
				exchange(1),
				stack(2)
				}
			MAX-ACCESS read-write
			STATUS current
			DESCRIPTION
				"Description."
			::= { sleEponVlanOnuVlanControl 8 }

		
		sleEponVlanOnuVlanControlUpVlanTag OBJECT-TYPE
			SYNTAX INTEGER (-1 | 1..4094)
			MAX-ACCESS read-write
			STATUS current
			DESCRIPTION
				"Description."
			::= { sleEponVlanOnuVlanControl 9 }

		
		sleEponVlanOnuVlanControlUpEtherType OBJECT-TYPE
			SYNTAX INTEGER
				{
				none(0),
				etherType0x8100(1),
				etherType0x9100(2)
				}
			MAX-ACCESS read-write
			STATUS current
			DESCRIPTION
				"Description."
			::= { sleEponVlanOnuVlanControl 10 }

		
		sleEponVlanOnuVlanControlUpPriority OBJECT-TYPE
			SYNTAX Integer32
			MAX-ACCESS read-write
			STATUS current
			DESCRIPTION
				"Description."
			::= { sleEponVlanOnuVlanControl 11 }

		
		sleEponVlanOnuVlanControlDownMode OBJECT-TYPE
			SYNTAX INTEGER
				{
				none(0),
				exchange(1),
				stack(2)
				}
			MAX-ACCESS read-write
			STATUS current
			DESCRIPTION
				"Description."
			::= { sleEponVlanOnuVlanControl 12 }

		
		sleEponVlanOnuVlanControlDownVlanTag OBJECT-TYPE
			SYNTAX INTEGER (-1 | 1..4094)
			MAX-ACCESS read-write
			STATUS current
			DESCRIPTION
				"Description."
			::= { sleEponVlanOnuVlanControl 13 }

		
		sleEponVlanOnuVlanControlDownPriority OBJECT-TYPE
			SYNTAX Integer32
			MAX-ACCESS read-write
			STATUS current
			DESCRIPTION
				"Description."
			::= { sleEponVlanOnuVlanControl 14 }

		
		sleEponVlanOnuVlanNotification OBJECT IDENTIFIER ::= { sleEponVlanOnuVlan 3 }

		
		sleEponVlanOnuVlanProfileChanged NOTIFICATION-TYPE
			OBJECTS { sleEponVlanOnuVlanControlRequest, sleEponVlanOnuVlanControlTimeStamp, sleEponVlanOnuVlanControlReqResult, sleEponVlanOnuVlanControlOltIndex, sleEponVlanOnuVlanControlOnuIndex, 
				sleEponVlanOnuVlanControlUpMode, sleEponVlanOnuVlanControlUpVlanTag, sleEponVlanOnuVlanControlUpEtherType, sleEponVlanOnuVlanControlDownMode, sleEponVlanOnuVlanControlDownVlanTag
				 }
			STATUS current
			DESCRIPTION 
				"Description."
			::= { sleEponVlanOnuVlanNotification 1 }

		
		sleEponFirmwareMgmt OBJECT IDENTIFIER ::= { sleEpon 10 }

		
		sleEponFirmwareTable OBJECT-TYPE
			SYNTAX SEQUENCE OF SleEponFirmwareEntry
			MAX-ACCESS not-accessible
			STATUS current
			DESCRIPTION
				"Description."
			::= { sleEponFirmwareMgmt 1 }

		
		sleEponFirmwareEntry OBJECT-TYPE
			SYNTAX SleEponFirmwareEntry
			MAX-ACCESS not-accessible
			STATUS current
			DESCRIPTION
				"Description."
			INDEX { sleEponFirmwareType, sleEponFirmwareName }
			::= { sleEponFirmwareTable 1 }

		
		SleEponFirmwareEntry ::=
			SEQUENCE { 
				sleEponFirmwareType
					INTEGER,
				sleEponFirmwareName
					OCTET STRING
			 }

		sleEponFirmwareType OBJECT-TYPE
			SYNTAX INTEGER
				{
				olt(1),
				onu(2)
				}
			MAX-ACCESS read-only
			STATUS current
			DESCRIPTION
				"Description."
			::= { sleEponFirmwareEntry 1 }

		
		sleEponFirmwareName OBJECT-TYPE
			SYNTAX OCTET STRING (SIZE (1..128))
			MAX-ACCESS read-only
			STATUS current
			DESCRIPTION
				"Description."
			::= { sleEponFirmwareEntry 2 }

		
		sleEponFirmwareControl OBJECT IDENTIFIER ::= { sleEponFirmwareMgmt 2 }

		
		sleEponFirmwareControlRequest OBJECT-TYPE
			SYNTAX INTEGER
				{
				setEponFirmwareUpgradeProfile(1),
				deleteEponFirmware(2)
				}
			MAX-ACCESS read-write
			STATUS current
			DESCRIPTION
				"Description."
			::= { sleEponFirmwareControl 1 }

		
		sleEponFirmwareControlStatus OBJECT-TYPE
			SYNTAX SleControlStatusType
			MAX-ACCESS read-only
			STATUS current
			DESCRIPTION
				"Description."
			::= { sleEponFirmwareControl 2 }

		
		sleEponFirmwareControlTimer OBJECT-TYPE
			SYNTAX Gauge32
			MAX-ACCESS read-write
			STATUS current
			DESCRIPTION
				"Description."
			::= { sleEponFirmwareControl 3 }

		
		sleEponFirmwareControlTimeStamp OBJECT-TYPE
			SYNTAX TimeTicks
			MAX-ACCESS read-only
			STATUS current
			DESCRIPTION
				"Description."
			::= { sleEponFirmwareControl 4 }

		
		sleEponFirmwareControlReqResult OBJECT-TYPE
			SYNTAX SleControlRequestResultType
			MAX-ACCESS read-only
			STATUS current
			DESCRIPTION
				"Description."
			::= { sleEponFirmwareControl 5 }

		
		sleEponFirmwareControlName OBJECT-TYPE
			SYNTAX OCTET STRING (SIZE (1..128))
			MAX-ACCESS read-write
			STATUS current
			DESCRIPTION
				"Description."
			::= { sleEponFirmwareControl 6 }

		
		sleEponFirmwareControlUpgradeMethod OBJECT-TYPE
			SYNTAX INTEGER
				{
				ftp(1),
				tftp(2)
				}
			MAX-ACCESS read-write
			STATUS current
			DESCRIPTION
				"Description."
			::= { sleEponFirmwareControl 7 }

		
		sleEponFirmwareControlUpgradeMode OBJECT-TYPE
			SYNTAX INTEGER
				{
				upload(1),
				download(2)
				}
			MAX-ACCESS read-write
			STATUS current
			DESCRIPTION
				"Description."
			::= { sleEponFirmwareControl 8 }

		
		sleEponFirmwareControlServerAddress OBJECT-TYPE
			SYNTAX IpAddress
			MAX-ACCESS read-write
			STATUS current
			DESCRIPTION
				"Description."
			::= { sleEponFirmwareControl 9 }

		
		sleEponFirmwareControlUser OBJECT-TYPE
			SYNTAX OCTET STRING
			MAX-ACCESS read-write
			STATUS current
			DESCRIPTION
				"Description."
			::= { sleEponFirmwareControl 10 }

		
		sleEponFirmwareControlPasswd OBJECT-TYPE
			SYNTAX OCTET STRING
			MAX-ACCESS read-write
			STATUS current
			DESCRIPTION
				"Description."
			::= { sleEponFirmwareControl 11 }

		
		sleEponFirmwareNotification OBJECT IDENTIFIER ::= { sleEponFirmwareMgmt 3 }

		
		sleEponFirmwareUpgradeProfileChanged NOTIFICATION-TYPE
			OBJECTS { sleEponFirmwareControlRequest, sleEponFirmwareControlTimeStamp, sleEponFirmwareControlReqResult, sleEponFirmwareControlName, sleEponFirmwareControlUpgradeMethod, 
				sleEponFirmwareControlUpgradeMode, sleEponFirmwareControlServerAddress, sleEponFirmwareControlUser, sleEponFirmwareControlPasswd }
			STATUS current
			DESCRIPTION 
				"Description."
			::= { sleEponFirmwareNotification 1 }

		
		sleEponFirmwareDeleted NOTIFICATION-TYPE
			OBJECTS { sleEponFirmwareControlRequest, sleEponFirmwareControlTimeStamp, sleEponFirmwareControlReqResult, sleEponFirmwareControlName }
			STATUS current
			DESCRIPTION 
				"Description."
			::= { sleEponFirmwareNotification 2 }

		
		sleEponOnuFirmwareMgmt OBJECT IDENTIFIER ::= { sleEponFirmwareMgmt 4 }

		
		sleEponOnuFirmwareTable OBJECT-TYPE
			SYNTAX SEQUENCE OF SleEponOnuFirmwareEntry
			MAX-ACCESS not-accessible
			STATUS current
			DESCRIPTION
				"Description."
			::= { sleEponOnuFirmwareMgmt 1 }

		
		sleEponOnuFirmwareEntry OBJECT-TYPE
			SYNTAX SleEponOnuFirmwareEntry
			MAX-ACCESS not-accessible
			STATUS current
			DESCRIPTION
				"Description."
			INDEX { sleEponOltIndex, sleEponOnuIndex }
			::= { sleEponOnuFirmwareTable 1 }

		
		SleEponOnuFirmwareEntry ::=
			SEQUENCE { 
				sleEponOnuFirmwareVender
					OCTET STRING,
				sleEponOnuFirmwareChip
					OCTET STRING,
				sleEponOnuFirmwareMaxPort
					Integer32,
				sleEponOnuFirmwareMajor
					Integer32,
				sleEponOnuFirmwareMinor
					Integer32,
				sleEponOnuFirmwareBuild
					Integer32,
				sleEponOnuFirmwareFileName
					OCTET STRING
			 }

		sleEponOnuFirmwareVender OBJECT-TYPE
			SYNTAX OCTET STRING
			MAX-ACCESS read-only
			STATUS current
			DESCRIPTION
				"Vender"
			::= { sleEponOnuFirmwareEntry 1 }

		
		sleEponOnuFirmwareChip OBJECT-TYPE
			SYNTAX OCTET STRING
			MAX-ACCESS read-only
			STATUS current
			DESCRIPTION
				"chip"
			::= { sleEponOnuFirmwareEntry 2 }

		
		sleEponOnuFirmwareMaxPort OBJECT-TYPE
			SYNTAX Integer32
			MAX-ACCESS read-only
			STATUS current
			DESCRIPTION
				"max port"
			::= { sleEponOnuFirmwareEntry 3 }

		
		sleEponOnuFirmwareMajor OBJECT-TYPE
			SYNTAX Integer32
			MAX-ACCESS read-only
			STATUS current
			DESCRIPTION
				"major"
			::= { sleEponOnuFirmwareEntry 4 }

		
		sleEponOnuFirmwareMinor OBJECT-TYPE
			SYNTAX Integer32
			MAX-ACCESS read-only
			STATUS current
			DESCRIPTION
				"minor"
			::= { sleEponOnuFirmwareEntry 5 }

		
		sleEponOnuFirmwareBuild OBJECT-TYPE
			SYNTAX Integer32
			MAX-ACCESS read-only
			STATUS current
			DESCRIPTION
				"build"
			::= { sleEponOnuFirmwareEntry 6 }

		
		sleEponOnuFirmwareFileName OBJECT-TYPE
			SYNTAX OCTET STRING
			MAX-ACCESS read-only
			STATUS current
			DESCRIPTION
				"upgrade file name"
			::= { sleEponOnuFirmwareEntry 7 }

		
		sleEponOnuSipUserConfig OBJECT IDENTIFIER ::= { sleEpon 11 }

		
		sleEponOnuSipUserConfigTable OBJECT-TYPE
			SYNTAX SEQUENCE OF SleEponOnuSipUserConfigEntry
			MAX-ACCESS not-accessible
			STATUS current
			DESCRIPTION
				"Description."
			::= { sleEponOnuSipUserConfig 1 }

		
		sleEponOnuSipUserConfigEntry OBJECT-TYPE
			SYNTAX SleEponOnuSipUserConfigEntry
			MAX-ACCESS not-accessible
			STATUS current
			DESCRIPTION
				"Description."
			INDEX { sleEponOltIndex, sleEponOnuIndex, sleEponOnuSipUserConfigPots }
			::= { sleEponOnuSipUserConfigTable 1 }

		
		SleEponOnuSipUserConfigEntry ::=
			SEQUENCE { 
				sleEponOnuSipUserConfigPots
					INTEGER,
				sleEponOnuSipUserConfigAccount
					OCTET STRING,
				sleEponOnuSipUserConfigName
					OCTET STRING,
				sleEponOnuSipUserConfigPasswd
					OCTET STRING
			 }

		sleEponOnuSipUserConfigPots OBJECT-TYPE
			SYNTAX INTEGER (0..65535)
			MAX-ACCESS read-only
			STATUS current
			DESCRIPTION
				"Description."
			::= { sleEponOnuSipUserConfigEntry 1 }

		
		sleEponOnuSipUserConfigAccount OBJECT-TYPE
			SYNTAX OCTET STRING
			MAX-ACCESS read-only
			STATUS current
			DESCRIPTION
				"Description."
			::= { sleEponOnuSipUserConfigEntry 2 }

		
		sleEponOnuSipUserConfigName OBJECT-TYPE
			SYNTAX OCTET STRING
			MAX-ACCESS read-only
			STATUS current
			DESCRIPTION
				"Description."
			::= { sleEponOnuSipUserConfigEntry 3 }

		
		sleEponOnuSipUserConfigPasswd OBJECT-TYPE
			SYNTAX OCTET STRING
			MAX-ACCESS read-only
			STATUS current
			DESCRIPTION
				"Description."
			::= { sleEponOnuSipUserConfigEntry 4 }

		
		sleEponOnuSipUserConfigControl OBJECT IDENTIFIER ::= { sleEponOnuSipUserConfig 2 }

		
		sleEponOnuSipUserConfigControlRequest OBJECT-TYPE
			SYNTAX INTEGER
				{
				setEponOnuSipUserConfig(1),
				destroyEponOnuSipUserConfig(2)
				}
			MAX-ACCESS read-write
			STATUS current
			DESCRIPTION
				"Description."
			::= { sleEponOnuSipUserConfigControl 1 }

		
		sleEponOnuSipUserConfigControlStatus OBJECT-TYPE
			SYNTAX SleControlStatusType
			MAX-ACCESS read-only
			STATUS current
			DESCRIPTION
				"Description."
			::= { sleEponOnuSipUserConfigControl 2 }

		
		sleEponOnuSipUserConfigControlTimer OBJECT-TYPE
			SYNTAX Gauge32
			MAX-ACCESS read-write
			STATUS current
			DESCRIPTION
				"Description."
			::= { sleEponOnuSipUserConfigControl 3 }

		
		sleEponOnuSipUserConfigControlTimeStamp OBJECT-TYPE
			SYNTAX TimeTicks
			MAX-ACCESS read-only
			STATUS current
			DESCRIPTION
				"Description."
			::= { sleEponOnuSipUserConfigControl 4 }

		
		sleEponOnuSipUserConfigControlReqResult OBJECT-TYPE
			SYNTAX SleControlRequestResultType
			MAX-ACCESS read-only
			STATUS current
			DESCRIPTION
				"Description."
			::= { sleEponOnuSipUserConfigControl 5 }

		
		sleEponOnuSipUserConfigControlOltIndex OBJECT-TYPE
			SYNTAX INTEGER
			MAX-ACCESS read-write
			STATUS current
			DESCRIPTION
				"Description."
			::= { sleEponOnuSipUserConfigControl 6 }

		
		sleEponOnuSipUserConfigControlOnuIndex OBJECT-TYPE
			SYNTAX INTEGER
			MAX-ACCESS read-write
			STATUS current
			DESCRIPTION
				"Description."
			::= { sleEponOnuSipUserConfigControl 7 }

		
		sleEponOnuSipUserConfigControlPots OBJECT-TYPE
			SYNTAX INTEGER
			MAX-ACCESS read-write
			STATUS current
			DESCRIPTION
				"Description."
			::= { sleEponOnuSipUserConfigControl 8 }

		
		sleEponOnuSipUserConfigControlAccount OBJECT-TYPE
			SYNTAX OCTET STRING
			MAX-ACCESS read-write
			STATUS current
			DESCRIPTION
				"Description."
			::= { sleEponOnuSipUserConfigControl 9 }

		
		sleEponOnuSipUserConfigControlName OBJECT-TYPE
			SYNTAX OCTET STRING
			MAX-ACCESS read-write
			STATUS current
			DESCRIPTION
				"Description."
			::= { sleEponOnuSipUserConfigControl 10 }

		
		sleEponOnuSipUserConfigControlPasswd OBJECT-TYPE
			SYNTAX OCTET STRING
			MAX-ACCESS read-write
			STATUS current
			DESCRIPTION
				"Description."
			::= { sleEponOnuSipUserConfigControl 11 }

		
		sleEponOnuSipNotification OBJECT IDENTIFIER ::= { sleEponOnuSipUserConfig 3 }

		
		sleEponOnuSipUserConfigChanged NOTIFICATION-TYPE
			OBJECTS { sleEponOnuSipUserConfigControlRequest, sleEponOnuSipUserConfigControlTimeStamp, sleEponOnuSipUserConfigControlReqResult, sleEponOnuSipUserConfigControlOltIndex, sleEponOnuSipUserConfigControlOnuIndex, 
				sleEponOnuSipUserConfigControlPots, sleEponOnuSipUserConfigControlAccount, sleEponOnuSipUserConfigControlName, sleEponOnuSipUserConfigControlPasswd }
			STATUS current
			DESCRIPTION 
				"Description."
			::= { sleEponOnuSipNotification 1 }

		
		sleEponOnuSipUserConfigDestroyed NOTIFICATION-TYPE
			OBJECTS { sleEponOnuSipUserConfigControlRequest, sleEponOnuSipUserConfigControlTimeStamp, sleEponOnuSipUserConfigControlReqResult, sleEponOnuSipUserConfigControlOltIndex, sleEponOnuSipUserConfigControlOnuIndex, 
				sleEponOnuSipUserConfigControlPots }
			STATUS current
			DESCRIPTION 
				"Description."
			::= { sleEponOnuSipNotification 2 }

		
		sleEponOnuSipPortStatus OBJECT IDENTIFIER ::= { sleEpon 12 }

		
		sleEponOnuSipPortStatusTable OBJECT-TYPE
			SYNTAX SEQUENCE OF SleEponOnuSipPortStatusEntry
			MAX-ACCESS not-accessible
			STATUS current
			DESCRIPTION
				"Description."
			::= { sleEponOnuSipPortStatus 1 }

		
		sleEponOnuSipPortStatusEntry OBJECT-TYPE
			SYNTAX SleEponOnuSipPortStatusEntry
			MAX-ACCESS not-accessible
			STATUS current
			DESCRIPTION
				"Description."
			INDEX { sleEponOltIndex, sleEponOnuIndex, sleEponOnuSipUserConfigPots }
			::= { sleEponOnuSipPortStatusTable 1 }

		
		SleEponOnuSipPortStatusEntry ::=
			SEQUENCE { 
				sleEponOnuVoipPortStatus
					OCTET STRING,
				sleEponOnuSipPortServiceState
					OCTET STRING,
				sleEponOnuSipPortCodecMode
					OCTET STRING
			 }

		sleEponOnuVoipPortStatus OBJECT-TYPE
			SYNTAX OCTET STRING
			MAX-ACCESS read-only
			STATUS current
			DESCRIPTION
				"Description."
			::= { sleEponOnuSipPortStatusEntry 1 }

		
		sleEponOnuSipPortServiceState OBJECT-TYPE
			SYNTAX OCTET STRING
			MAX-ACCESS read-only
			STATUS current
			DESCRIPTION
				"Description."
			::= { sleEponOnuSipPortStatusEntry 2 }

		
		sleEponOnuSipPortCodecMode OBJECT-TYPE
			SYNTAX OCTET STRING
			MAX-ACCESS read-only
			STATUS current
			DESCRIPTION
				"Description."
			::= { sleEponOnuSipPortStatusEntry 3 }

		
		sleEponRule OBJECT IDENTIFIER ::= { sleEpon 13 }

		
		sleEponRuleClause OBJECT IDENTIFIER ::= { sleEponRule 1 }

		
		sleEponRuleClauseTable OBJECT-TYPE
			SYNTAX SEQUENCE OF SleEponRuleClauseEntry
			MAX-ACCESS not-accessible
			STATUS current
			DESCRIPTION
				"Description."
			::= { sleEponRuleClause 1 }

		
		sleEponRuleClauseEntry OBJECT-TYPE
			SYNTAX SleEponRuleClauseEntry
			MAX-ACCESS not-accessible
			STATUS current
			DESCRIPTION
				"Description."
			INDEX { sleEponOltIndex }
			::= { sleEponRuleClauseTable 1 }

		
		SleEponRuleClauseEntry ::=
			SEQUENCE { 
				sleEponRuleClauseQueue
					INTEGER,
				sleEponRuleClauseQueueValue
					Integer32,
				sleEponRuleClauseLayerOperation
					INTEGER,
				sleEponRuleClauseLayerValue
					INTEGER,
				sleEponRuleClauseL2Mac
					MacAddress,
				sleEponRuleClauseL2EthertypeValue
					INTEGER,
				sleEponRuleClauseNetmask
					INTEGER,
				sleEponRuleClauseL3Addr
					IpAddress,
				sleEponRuleClauseTcpUdpPort
					INTEGER,
				sleEponRuleClauseTcpUdpPortNum
					Integer32,
				sleEponRuleClauseProtoType
					INTEGER,
				sleEponRuleClauseProtoTypeNum
					Integer32,
				sleEponRuleClauseVlanType
					INTEGER,
				sleEponRuleClauseVlanValue
					Integer32,
				sleEponRuleClauseLinkIndexValue
					Integer32,
				sleEponRuleClauseMatchMode
					INTEGER
			 }

		sleEponRuleClauseQueue OBJECT-TYPE
			SYNTAX INTEGER
				{
				queuea(1),
				queueb(2)
				}
			MAX-ACCESS read-only
			STATUS current
			DESCRIPTION
				"State Variable Queue
				1.queue-a
				2.queue-b"
			::= { sleEponRuleClauseEntry 1 }

		
		sleEponRuleClauseQueueValue OBJECT-TYPE
			SYNTAX Integer32
			MAX-ACCESS read-only
			STATUS current
			DESCRIPTION
				"rule clause rule queue."
			::= { sleEponRuleClauseEntry 2 }

		
		sleEponRuleClauseLayerOperation OBJECT-TYPE
			SYNTAX INTEGER
				{
				layer2SrcAddr(1),
				layer2DesAddr(2),
				layer2Tos(3),
				layer2Ttl(4),
				layer2EtherType(5),
				layer3SrcAddr(6),
				layer3DesAddr(7)
				}
			MAX-ACCESS read-only
			STATUS current
			DESCRIPTION
				"The rule clause be used to which layer and which type."
			::= { sleEponRuleClauseEntry 3 }

		
		sleEponRuleClauseLayerValue OBJECT-TYPE
			SYNTAX INTEGER (0..7)
			MAX-ACCESS read-only
			STATUS current
			DESCRIPTION
				"layer value."
			::= { sleEponRuleClauseEntry 4 }

		
		sleEponRuleClauseL2Mac OBJECT-TYPE
			SYNTAX MacAddress
			MAX-ACCESS read-only
			STATUS current
			DESCRIPTION
				"Layer 2 MAC address."
			::= { sleEponRuleClauseEntry 5 }

		
		sleEponRuleClauseL2EthertypeValue OBJECT-TYPE
			SYNTAX INTEGER
				{
				null(0),
				ip0x0800(1),
				arp0x0806(2)
				}
			MAX-ACCESS read-write
			STATUS current
			DESCRIPTION
				"Rule Clause L2 Ethertype Value."
			::= { sleEponRuleClauseEntry 6 }

		
		sleEponRuleClauseNetmask OBJECT-TYPE
			SYNTAX INTEGER (1..48)
			MAX-ACCESS read-only
			STATUS current
			DESCRIPTION
				"The netmask.
				1.layer2 range from 1-48
				2.layer3 range from 1-32"
			::= { sleEponRuleClauseEntry 7 }

		
		sleEponRuleClauseL3Addr OBJECT-TYPE
			SYNTAX IpAddress
			MAX-ACCESS read-only
			STATUS current
			DESCRIPTION
				"Chooseing the sourse or destination IP address be used to the rule clause."
			::= { sleEponRuleClauseEntry 8 }

		
		sleEponRuleClauseTcpUdpPort OBJECT-TYPE
			SYNTAX INTEGER
				{
				srcport(1),
				desport(2)
				}
			MAX-ACCESS read-only
			STATUS current
			DESCRIPTION
				"rule clause tcp/udp port."
			::= { sleEponRuleClauseEntry 9 }

		
		sleEponRuleClauseTcpUdpPortNum OBJECT-TYPE
			SYNTAX Integer32 (0..65535)
			MAX-ACCESS read-only
			STATUS current
			DESCRIPTION
				"rule clause tcp/udp port, number range from 0 to 65535."
			::= { sleEponRuleClauseEntry 10 }

		
		sleEponRuleClauseProtoType OBJECT-TYPE
			SYNTAX INTEGER
				{
				protoType(1),
				slowProto(2)
				}
			MAX-ACCESS read-only
			STATUS current
			DESCRIPTION
				"Protocol type
				1.proto-type 
				2.slow-proto 
				ex:For protocol type 1=ICMP 2=IGMP 6=TCP 17=UDP"
			::= { sleEponRuleClauseEntry 11 }

		
		sleEponRuleClauseProtoTypeNum OBJECT-TYPE
			SYNTAX Integer32 (1..255)
			MAX-ACCESS read-only
			STATUS current
			DESCRIPTION
				"The range from 1 to 255"
			::= { sleEponRuleClauseEntry 12 }

		
		sleEponRuleClauseVlanType OBJECT-TYPE
			SYNTAX INTEGER
				{
				svlan0(1),
				svlan1(2),
				cvlan0(3),
				cvlan1(4)
				}
			MAX-ACCESS read-only
			STATUS current
			DESCRIPTION
				"The rule VLAN type:
				1.s-vlan0
				2.s-vlan1
				3.c-vlan0
				4.c-vlan1"
			::= { sleEponRuleClauseEntry 13 }

		
		sleEponRuleClauseVlanValue OBJECT-TYPE
			SYNTAX Integer32
			MAX-ACCESS read-write
			STATUS current
			DESCRIPTION
				"vlan value."
			::= { sleEponRuleClauseEntry 14 }

		
		sleEponRuleClauseLinkIndexValue OBJECT-TYPE
			SYNTAX Integer32
			MAX-ACCESS read-write
			STATUS current
			DESCRIPTION
				"Link index."
			::= { sleEponRuleClauseEntry 15 }

		
		sleEponRuleClauseMatchMode OBJECT-TYPE
			SYNTAX INTEGER
				{
				eq(1),
				neq(2),
				lte(3),
				gte(4),
				fe(5),
				nfe(6),
				al(7)
				}
			MAX-ACCESS read-write
			STATUS current
			DESCRIPTION
				"Description."
			::= { sleEponRuleClauseEntry 16 }

		
		sleEponRuleClauseControl OBJECT IDENTIFIER ::= { sleEponRuleClause 2 }

		
		sleEponRuleClauseControlRequest OBJECT-TYPE
			SYNTAX INTEGER
				{
				setRuleClauseQueue(1),
				setRuleClauseLayer2(2),
				setRuleClauseVlan(3),
				setRuleClauseLayer3(4),
				setRuleClauseTcpUdp(5),
				setRuleClauseProtocol(6),
				setRuleClauseLinkIndex(7),
				noRuleClause(8)
				}
			MAX-ACCESS read-write
			STATUS current
			DESCRIPTION
				"The request of a user command."
			::= { sleEponRuleClauseControl 1 }

		
		sleEponRuleClauseControlStatus OBJECT-TYPE
			SYNTAX SleControlStatusType
			MAX-ACCESS read-only
			STATUS current
			DESCRIPTION
				"The status of user command"
			::= { sleEponRuleClauseControl 2 }

		
		sleEponRuleClauseControlTimer OBJECT-TYPE
			SYNTAX Gauge32
			MAX-ACCESS read-write
			STATUS current
			DESCRIPTION
				"The maximum time for the manager for a long running user command"
			::= { sleEponRuleClauseControl 3 }

		
		sleEponRuleClauseControlTimeStamp OBJECT-TYPE
			SYNTAX TimeTicks
			MAX-ACCESS read-only
			STATUS current
			DESCRIPTION
				"The time stamp of the last command(end of command)"
			::= { sleEponRuleClauseControl 4 }

		
		sleEponRuleClauseControlReqResult OBJECT-TYPE
			SYNTAX SleControlRequestResultType
			MAX-ACCESS read-only
			STATUS current
			DESCRIPTION
				"The result of the last user command"
			::= { sleEponRuleClauseControl 5 }

		
		sleEponRuleClauseControlClauseIndex OBJECT-TYPE
			SYNTAX Integer32
			MAX-ACCESS read-write
			STATUS current
			DESCRIPTION
				"Rule clause index"
			::= { sleEponRuleClauseControl 6 }

		
		sleEponRuleClauseControlClauseMatch OBJECT-TYPE
			SYNTAX INTEGER
				{
				eq(1),
				neq(2),
				lte(3),
				gte(4),
				fe(5),
				nfe(6),
				al(7)
				}
			MAX-ACCESS read-write
			STATUS current
			DESCRIPTION
				"match mode."
			::= { sleEponRuleClauseControl 7 }

		
		sleEponRuleClauseControlQueue OBJECT-TYPE
			SYNTAX INTEGER
				{
				queueA(1),
				queueB(2)
				}
			MAX-ACCESS read-write
			STATUS current
			DESCRIPTION
				"State Variable Queue."
			::= { sleEponRuleClauseControl 8 }

		
		sleEponRuleClauseControlQueueValue OBJECT-TYPE
			SYNTAX INTEGER (0..7)
			MAX-ACCESS read-write
			STATUS current
			DESCRIPTION
				"State Variable Queue Value."
			::= { sleEponRuleClauseControl 9 }

		
		sleEponRuleClauseControlLayerOperation OBJECT-TYPE
			SYNTAX INTEGER
				{
				layer2SrcAddress(1),
				layer2DesAddress(2),
				layer2Tos(3),
				layer2Ttl(4),
				layer2EtherType(5),
				layer3SrcIPAddress(6),
				layer3DesIPAddress(7)
				}
			MAX-ACCESS read-write
			STATUS current
			DESCRIPTION
				"The rule clause be used to which layer and which type.The layer as following:
				"
			::= { sleEponRuleClauseControl 10 }

		
		sleEponRuleClauseControlLayerValue OBJECT-TYPE
			SYNTAX Integer32
			MAX-ACCESS read-write
			STATUS current
			DESCRIPTION
				"layer value."
			::= { sleEponRuleClauseControl 11 }

		
		sleEponRuleClauseControlL2Mac OBJECT-TYPE
			SYNTAX MacAddress
			MAX-ACCESS read-write
			STATUS current
			DESCRIPTION
				"Layer2 Mac address."
			::= { sleEponRuleClauseControl 12 }

		
		sleEponRuleClauseControlL2EtherType OBJECT-TYPE
			SYNTAX INTEGER
				{
				null(0),
				ip0x0800(1),
				arp0x0806(2)
				}
			MAX-ACCESS read-write
			STATUS current
			DESCRIPTION
				"Rule Clause L2 Ethertype Value."
			::= { sleEponRuleClauseControl 13 }

		
		sleEponRuleClauseControlNetmask OBJECT-TYPE
			SYNTAX Integer32 (1..48)
			MAX-ACCESS read-write
			STATUS current
			DESCRIPTION
				"The netmask.
				1.layer2 range from 1-48
				2.layer3 range from 1-32"
			::= { sleEponRuleClauseControl 14 }

		
		sleEponRuleClauseControlL3Addr OBJECT-TYPE
			SYNTAX IpAddress
			MAX-ACCESS read-write
			STATUS current
			DESCRIPTION
				"L3 IP address."
			::= { sleEponRuleClauseControl 15 }

		
		sleEponRuleClauseControlTcpUdpPort OBJECT-TYPE
			SYNTAX INTEGER
				{
				srcPort(1),
				desPort(2)
				}
			MAX-ACCESS read-write
			STATUS current
			DESCRIPTION
				"Tcp port or Udp port."
			::= { sleEponRuleClauseControl 16 }

		
		sleEponRuleClauseControlTcpUdpPortNum OBJECT-TYPE
			SYNTAX Integer32 (0..65535)
			MAX-ACCESS read-write
			STATUS current
			DESCRIPTION
				"Port number range from 0 to 65535."
			::= { sleEponRuleClauseControl 17 }

		
		sleEponRuleClauseControlProtoType OBJECT-TYPE
			SYNTAX INTEGER
				{
				protoType(1),
				slowProtocol(2)
				}
			MAX-ACCESS read-write
			STATUS current
			DESCRIPTION
				"Protocol type
				1.proto-type 
				2.slow-proto 
				ex:For protocol type 1=ICMP 2=IGMP 6=TCP 17=UDP"
			::= { sleEponRuleClauseControl 18 }

		
		sleEponRuleClauseControlProtoTypeNum OBJECT-TYPE
			SYNTAX INTEGER (1..255)
			MAX-ACCESS read-write
			STATUS current
			DESCRIPTION
				"For protocol type .ex :1=ICMP 2=IGMP 6=TCP 17=UDP
				The range from 1 to 255."
			::= { sleEponRuleClauseControl 19 }

		
		sleEponRuleClauseControlVlanType OBJECT-TYPE
			SYNTAX INTEGER
				{
				svlan0(1),
				svlan1(2),
				cvlan0(3),
				cvlan1(4)
				}
			MAX-ACCESS read-write
			STATUS current
			DESCRIPTION
				"The rule VLAN type."
			::= { sleEponRuleClauseControl 20 }

		
		sleEponRuleClauseControlVlanValue OBJECT-TYPE
			SYNTAX Integer32
			MAX-ACCESS read-write
			STATUS current
			DESCRIPTION
				"vlan value."
			::= { sleEponRuleClauseControl 21 }

		
		sleEponRuleClauseControlLinkIndexValue OBJECT-TYPE
			SYNTAX INTEGER (1..32)
			MAX-ACCESS read-write
			STATUS current
			DESCRIPTION
				"Link index."
			::= { sleEponRuleClauseControl 22 }

		
		sleEponRuleClauseNotification OBJECT IDENTIFIER ::= { sleEponRuleClause 3 }

		
		sleEponRuleClauseQueueChanged NOTIFICATION-TYPE
			OBJECTS { sleEponRuleClauseControlRequest, sleEponRuleClauseControlTimeStamp, sleEponRuleClauseControlReqResult, sleEponRuleClauseControlClauseIndex, sleEponRuleClauseControlQueue, 
				sleEponRuleClauseControlQueueValue }
			STATUS current
			DESCRIPTION 
				"Description."
			::= { sleEponRuleClauseNotification 1 }

		
		sleEponRuleClauseLayer2Changed NOTIFICATION-TYPE
			OBJECTS { sleEponRuleClauseControlRequest, sleEponRuleClauseControlTimeStamp, sleEponRuleClauseControlReqResult, sleEponRuleClauseControlClauseIndex, sleEponRuleClauseControlLayerOperation, 
				sleEponRuleClauseControlL2Mac, sleEponRuleClauseControlL2EtherType, sleEponRuleClauseControlNetmask }
			STATUS current
			DESCRIPTION 
				"Description."
			::= { sleEponRuleClauseNotification 2 }

		
		sleEponRuleClauseVlanChanged NOTIFICATION-TYPE
			OBJECTS { sleEponRuleClauseControlRequest, sleEponRuleClauseControlTimeStamp, sleEponRuleClauseControlReqResult, sleEponRuleClauseControlClauseIndex, sleEponRuleClauseControlVlanType, 
				sleEponRuleClauseControlVlanValue }
			STATUS current
			DESCRIPTION 
				"Description."
			::= { sleEponRuleClauseNotification 3 }

		
		sleEponRuleClauseLayer3Changed NOTIFICATION-TYPE
			OBJECTS { sleEponRuleClauseControlRequest, sleEponRuleClauseControlTimeStamp, sleEponRuleClauseControlReqResult, sleEponRuleClauseControlClauseIndex, sleEponRuleClauseControlTcpUdpPort, 
				sleEponRuleClauseControlTcpUdpPortNum }
			STATUS current
			DESCRIPTION 
				"Description."
			::= { sleEponRuleClauseNotification 4 }

		
		sleEponRuleClauseTcpUdpChanged NOTIFICATION-TYPE
			OBJECTS { sleEponRuleClauseControlRequest, sleEponRuleClauseControlTimeStamp, sleEponRuleClauseControlReqResult, sleEponRuleClauseControlClauseIndex, sleEponRuleClauseControlTcpUdpPort, 
				sleEponRuleClauseControlTcpUdpPortNum }
			STATUS current
			DESCRIPTION 
				"Description."
			::= { sleEponRuleClauseNotification 5 }

		
		sleEponRuleClauseProtocolChanged NOTIFICATION-TYPE
			OBJECTS { sleEponRuleClauseControlRequest, sleEponRuleClauseControlTimeStamp, sleEponRuleClauseControlReqResult, sleEponRuleClauseControlClauseIndex, sleEponRuleClauseControlProtoType, 
				sleEponRuleClauseControlProtoTypeNum }
			STATUS current
			DESCRIPTION 
				"Description."
			::= { sleEponRuleClauseNotification 6 }

		
		sleEponRuleClauseLinkIndexChanged NOTIFICATION-TYPE
			OBJECTS { sleEponRuleClauseControlRequest, sleEponRuleClauseControlTimeStamp, sleEponRuleClauseControlReqResult, sleEponRuleClauseControlClauseIndex, sleEponRuleClauseControlLinkIndexValue
				 }
			STATUS current
			DESCRIPTION 
				"Description."
			::= { sleEponRuleClauseNotification 7 }

		
		sleEponRuleClauseDel NOTIFICATION-TYPE
			OBJECTS { sleEponRuleClauseControlRequest, sleEponRuleClauseControlTimeStamp, sleEponRuleClauseControlReqResult, sleEponRuleClauseControlClauseIndex }
			STATUS current
			DESCRIPTION 
				"Description."
			::= { sleEponRuleClauseNotification 8 }

		
		sleEponRuleAction OBJECT IDENTIFIER ::= { sleEponRule 2 }

		
		sleEponRuleActionTable OBJECT-TYPE
			SYNTAX SEQUENCE OF SleEponRuleActionEntry
			MAX-ACCESS not-accessible
			STATUS current
			DESCRIPTION
				"Description."
			::= { sleEponRuleAction 1 }

		
		sleEponRuleActionEntry OBJECT-TYPE
			SYNTAX SleEponRuleActionEntry
			MAX-ACCESS not-accessible
			STATUS current
			DESCRIPTION
				"Description."
			INDEX { sleEponOltIndex }
			::= { sleEponRuleActionTable 1 }

		
		SleEponRuleActionEntry ::=
			SEQUENCE { 
				sleEponRuleActionVlanOperate
					INTEGER,
				sleEponRuleActionVlanMap
					INTEGER,
				sleEponRuleActionEtherType
					OCTET STRING,
				sleEponRuleActionVlanID
					Integer32,
				sleEponRuleActionDiscardOperate
					INTEGER,
				sleEponRuleActionDiscardOperateValue
					INTEGER,
				sleEponRuleActionCaptureHostOperate
					INTEGER,
				sleEponRuleActionCaptureHostFlexibleOperate
					INTEGER,
				sleEponRuleActionQueueId
					Integer32,
				sleEponRuleActionUnicastLinkDestID
					Integer32,
				sleEponRuleActionUnicastLinkDestOffset
					Integer32,
				sleEponRuleActionMulticastLinkDomID
					Integer32,
				sleEponRuleActionMulticastLinkDomOffset
					Integer32,
				sleEponRuleActionCosOperate
					INTEGER,
				sleEponRuleActionCosValue
					Integer32,
				sleEponRuleActionTosOperate
					INTEGER,
				sleEponRuleActionTosValue
					Integer32,
				sleEponRuleActionOutputOperate
					INTEGER,
				sleEponRuleActionOutputValue
					Integer32,
				sleEponRuleActionOutputVlanContent
					INTEGER,
				sleEponRuleActionOutputSourceFiledCopy
					INTEGER,
				sleEponRuleActionQueuePendingOperate
					INTEGER
			 }

		sleEponRuleActionVlanOperate OBJECT-TYPE
			SYNTAX INTEGER
				{
				addEthertype(1),
				clearAdd(2),
				clearDelete(3),
				delete(4),
				addNoEthertype(5)
				}
			MAX-ACCESS read-only
			STATUS current
			DESCRIPTION
				"Vlan Operate."
			::= { sleEponRuleActionEntry 1 }

		
		sleEponRuleActionVlanMap OBJECT-TYPE
			SYNTAX INTEGER (0..15)
			MAX-ACCESS read-only
			STATUS current
			DESCRIPTION
				"VLAN map:0-null,1-Vlan0,2-Vlan1,4-Vlan2
				VLAN map:0x01-vlan0  0x02-vlan1  0x04-vlan2  0x08-vlan3
				"
			::= { sleEponRuleActionEntry 2 }

		
		sleEponRuleActionEtherType OBJECT-TYPE
			SYNTAX OCTET STRING
			MAX-ACCESS read-only
			STATUS current
			DESCRIPTION
				"Ether Type.
				"
			::= { sleEponRuleActionEntry 3 }

		
		sleEponRuleActionVlanID OBJECT-TYPE
			SYNTAX Integer32
			MAX-ACCESS read-only
			STATUS current
			DESCRIPTION
				"vlan ID.Range from 1 to 4096"
			::= { sleEponRuleActionEntry 4 }

		
		sleEponRuleActionDiscardOperate OBJECT-TYPE
			SYNTAX INTEGER
				{
				discard(1),
				cleardiscard(2)
				}
			MAX-ACCESS read-only
			STATUS current
			DESCRIPTION
				"port map operate
				discard(1),
				clear-discard(2)"
			::= { sleEponRuleActionEntry 5 }

		
		sleEponRuleActionDiscardOperateValue OBJECT-TYPE
			SYNTAX INTEGER
				{
				eponPort(1),
				eponPort1(2),
				nniPort0(4),
				nniPort1(8)
				}
			MAX-ACCESS read-only
			STATUS current
			DESCRIPTION
				"Port map:Epon-port0 x01, Epon-port1 0x02 ,NNI-port0 0x04 ,NNI-port1 0x08."
			::= { sleEponRuleActionEntry 6 }

		
		sleEponRuleActionCaptureHostOperate OBJECT-TYPE
			SYNTAX INTEGER
				{
				premod(1),
				postmod(2),
				premodd(3),
				postmodd(4)
				}
			MAX-ACCESS read-only
			STATUS current
			DESCRIPTION
				"Capture to host operate
				pre-mod(1),Pre-modifications
				post-mod(2),Post-modifications
				pre-mod-d(3),Pre-modifications with domain/destination
				post-mod-d(4),Post-modifications with domain/destination"
			::= { sleEponRuleActionEntry 7 }

		
		sleEponRuleActionCaptureHostFlexibleOperate OBJECT-TYPE
			SYNTAX INTEGER
				{
				preMod(1),
				domDest(2),
				queuePend(3),
				clearD(4)
				}
			MAX-ACCESS read-only
			STATUS current
			DESCRIPTION
				"Capture Host Flexible Operate."
			::= { sleEponRuleActionEntry 8 }

		
		sleEponRuleActionQueueId OBJECT-TYPE
			SYNTAX Integer32
			MAX-ACCESS read-only
			STATUS current
			DESCRIPTION
				"Queue Id."
			::= { sleEponRuleActionEntry 9 }

		
		sleEponRuleActionUnicastLinkDestID OBJECT-TYPE
			SYNTAX Integer32
			MAX-ACCESS read-only
			STATUS current
			DESCRIPTION
				"Destination ID on which to set the link"
			::= { sleEponRuleActionEntry 10 }

		
		sleEponRuleActionUnicastLinkDestOffset OBJECT-TYPE
			SYNTAX Integer32
			MAX-ACCESS read-only
			STATUS current
			DESCRIPTION
				"Offset to the link within the destination"
			::= { sleEponRuleActionEntry 11 }

		
		sleEponRuleActionMulticastLinkDomID OBJECT-TYPE
			SYNTAX Integer32
			MAX-ACCESS read-only
			STATUS current
			DESCRIPTION
				"Domain ID on which to set the multicast link
				"
			::= { sleEponRuleActionEntry 12 }

		
		sleEponRuleActionMulticastLinkDomOffset OBJECT-TYPE
			SYNTAX Integer32
			MAX-ACCESS read-only
			STATUS current
			DESCRIPTION
				"Offset to the multicast link within the domain."
			::= { sleEponRuleActionEntry 13 }

		
		sleEponRuleActionCosOperate OBJECT-TYPE
			SYNTAX INTEGER
				{
				cos(1),
				cosRegTag(2),
				cosCopy(3),
				cosClear(4)
				}
			MAX-ACCESS read-write
			STATUS current
			DESCRIPTION
				"Cos Operate."
			::= { sleEponRuleActionEntry 14 }

		
		sleEponRuleActionCosValue OBJECT-TYPE
			SYNTAX Integer32
			MAX-ACCESS read-write
			STATUS current
			DESCRIPTION
				"Cos Value."
			::= { sleEponRuleActionEntry 15 }

		
		sleEponRuleActionTosOperate OBJECT-TYPE
			SYNTAX INTEGER
				{
				tos(1),
				tosClear(2)
				}
			MAX-ACCESS read-write
			STATUS current
			DESCRIPTION
				"Tos Operate."
			::= { sleEponRuleActionEntry 16 }

		
		sleEponRuleActionTosValue OBJECT-TYPE
			SYNTAX Integer32
			MAX-ACCESS read-write
			STATUS current
			DESCRIPTION
				"tos value."
			::= { sleEponRuleActionEntry 17 }

		
		sleEponRuleActionOutputOperate OBJECT-TYPE
			SYNTAX INTEGER
				{
				and(1),
				or(2),
				set(3),
				add(4),
				copy(5)
				}
			MAX-ACCESS read-only
			STATUS current
			DESCRIPTION
				"Rule action output on the selected field
				1.and,Perform a binary AND on the selected field
				2.or,Perform a binary OR on the selected field
				3.set,Set the selected field
				4.add,Add the selected field
				5.copy,Copy the selected field from another field."
			::= { sleEponRuleActionEntry 18 }

		
		sleEponRuleActionOutputValue OBJECT-TYPE
			SYNTAX Integer32
			MAX-ACCESS read-write
			STATUS current
			DESCRIPTION
				"output value."
			::= { sleEponRuleActionEntry 19 }

		
		sleEponRuleActionOutputVlanContent OBJECT-TYPE
			SYNTAX INTEGER (0..8)
			MAX-ACCESS read-only
			STATUS current
			DESCRIPTION
				"0-3 vlan0 4-7 vlan1(0-TPID 1-CoS 2-VID 3-CoS and VID 4-TPID 5-CoS 6-VID 7-CoS and VID 8-IPv4 ToS
				"
			::= { sleEponRuleActionEntry 20 }

		
		sleEponRuleActionOutputSourceFiledCopy OBJECT-TYPE
			SYNTAX INTEGER (0..25)
			MAX-ACCESS read-only
			STATUS current
			DESCRIPTION
				"Source field for the copy."
			::= { sleEponRuleActionEntry 21 }

		
		sleEponRuleActionQueuePendingOperate OBJECT-TYPE
			SYNTAX INTEGER
				{
				set(1),
				clear(2)
				}
			MAX-ACCESS read-only
			STATUS current
			DESCRIPTION
				"queue-pending operate."
			::= { sleEponRuleActionEntry 22 }

		
		sleEponRuleActionControl OBJECT IDENTIFIER ::= { sleEponRuleAction 2 }

		
		sleEponRuleActionControlRequest OBJECT-TYPE
			SYNTAX INTEGER
				{
				ruleActionVlanSet(1),
				ruleActionDiscardSet(2),
				ruleActionCaptureHostSet(3),
				ruleActionCaptureHostFlexibleSet(4),
				ruleActionQueueSet(5),
				ruleActionUnicastLinkSet(6),
				ruleActionMulticastLinkSet(7),
				ruleActionNoOperation(8),
				ruleActionCosSet(9),
				ruleActionTosSet(10),
				ruleActionOutputSet(11),
				ruleActionQueuePendingSet(12),
				ruleActionSleSet(13),
				noRuleAction(14)
				}
			MAX-ACCESS read-write
			STATUS current
			DESCRIPTION
				"The request of a user command."
			::= { sleEponRuleActionControl 1 }

		
		sleEponRuleActionControlStatus OBJECT-TYPE
			SYNTAX SleControlStatusType
			MAX-ACCESS read-only
			STATUS current
			DESCRIPTION
				"The status of user command"
			::= { sleEponRuleActionControl 2 }

		
		sleEponRuleActionControlTimer OBJECT-TYPE
			SYNTAX Gauge32
			MAX-ACCESS read-write
			STATUS current
			DESCRIPTION
				"The maximum time for the manager for a long running user command."
			::= { sleEponRuleActionControl 3 }

		
		sleEponRuleActionControlTimeStamp OBJECT-TYPE
			SYNTAX TimeTicks
			MAX-ACCESS read-only
			STATUS current
			DESCRIPTION
				"The time stamp of the last command(end of command)"
			::= { sleEponRuleActionControl 4 }

		
		sleEponRuleActionControlReqResult OBJECT-TYPE
			SYNTAX SleControlRequestResultType
			MAX-ACCESS read-only
			STATUS current
			DESCRIPTION
				"The result of the last user command"
			::= { sleEponRuleActionControl 5 }

		
		sleEponRuleActionControlIndex OBJECT-TYPE
			SYNTAX Integer32
			MAX-ACCESS read-write
			STATUS current
			DESCRIPTION
				"Rule action index."
			::= { sleEponRuleActionControl 6 }

		
		sleEponRuleActionControlVlanOperate OBJECT-TYPE
			SYNTAX INTEGER
				{
				addEthertype(1),
				clearAdd(2),
				clearD(3),
				delete(4),
				addNoEthertype(5)
				}
			MAX-ACCESS read-write
			STATUS current
			DESCRIPTION
				"Vlan Operate.
				"
			::= { sleEponRuleActionControl 7 }

		
		sleEponRuleActionControlVlanMap OBJECT-TYPE
			SYNTAX INTEGER (0..15)
			MAX-ACCESS read-write
			STATUS current
			DESCRIPTION
				"Rule action VLAN map:0-null,1-Vlan0,2-Vlan1,4-Vlan2.
				Rule action cos copy VLAN map:0x01-vlan0  0x02-vlan1  0x04-vlan2  0x08-vlan3."
			::= { sleEponRuleActionControl 8 }

		
		sleEponRuleActionControlEtherType OBJECT-TYPE
			SYNTAX OCTET STRING
			MAX-ACCESS read-write
			STATUS current
			DESCRIPTION
				"Ethernet Type."
			::= { sleEponRuleActionControl 9 }

		
		sleEponRuleActionControlVlanID OBJECT-TYPE
			SYNTAX Integer32 (1..4096)
			MAX-ACCESS read-write
			STATUS current
			DESCRIPTION
				"vlan ID.Range from 1 to 4096."
			::= { sleEponRuleActionControl 10 }

		
		sleEponRuleActionControlDiscardOperate OBJECT-TYPE
			SYNTAX INTEGER
				{
				discard(1),
				clearDdiscard(2)
				}
			MAX-ACCESS read-write
			STATUS current
			DESCRIPTION
				"discard operate.
				"
			::= { sleEponRuleActionControl 11 }

		
		sleEponRuleActionControlDiscardOperateValue OBJECT-TYPE
			SYNTAX INTEGER
				{
				eponPort(1),
				eponPort1(2),
				nniPort0(4),
				nniPort1(8)
				}
			MAX-ACCESS read-write
			STATUS current
			DESCRIPTION
				"Port map:Epon-port0 x01, Epon-port1 0x02 ,NNI-port0 0x04 ,NNI-port1 0x08."
			::= { sleEponRuleActionControl 12 }

		
		sleEponRuleActionControlCaptureHostOperate OBJECT-TYPE
			SYNTAX INTEGER
				{
				preMod(1),
				postMod(2),
				preModD(3),
				postModD(4)
				}
			MAX-ACCESS read-write
			STATUS current
			DESCRIPTION
				"Capture to host operate."
			::= { sleEponRuleActionControl 13 }

		
		sleEponRuleActionControlCaptureHostFlexibleOperate OBJECT-TYPE
			SYNTAX INTEGER
				{
				perMod(1),
				domDest(2),
				queuePend(3),
				clearD(4)
				}
			MAX-ACCESS read-write
			STATUS current
			DESCRIPTION
				"Capture Host Flexible Operate."
			::= { sleEponRuleActionControl 14 }

		
		sleEponRuleActionControlQueueId OBJECT-TYPE
			SYNTAX Integer32
			MAX-ACCESS read-write
			STATUS current
			DESCRIPTION
				"QueueId."
			::= { sleEponRuleActionControl 15 }

		
		sleEponRuleActionControlQueuependingOperate OBJECT-TYPE
			SYNTAX INTEGER
				{
				set(1),
				clear(2)
				}
			MAX-ACCESS read-write
			STATUS current
			DESCRIPTION
				"queue-pending operate."
			::= { sleEponRuleActionControl 16 }

		
		sleEponRuleActionControlUnicastLinkDestID OBJECT-TYPE
			SYNTAX Integer32
			MAX-ACCESS read-write
			STATUS current
			DESCRIPTION
				"Destination ID on which to set the link."
			::= { sleEponRuleActionControl 17 }

		
		sleEponRuleActionControlUnicastLinkDestOffset OBJECT-TYPE
			SYNTAX Integer32
			MAX-ACCESS read-write
			STATUS current
			DESCRIPTION
				"Offset to the link within the destination."
			::= { sleEponRuleActionControl 18 }

		
		sleEponRuleActionControlMulticastLinkDomID OBJECT-TYPE
			SYNTAX Integer32
			MAX-ACCESS read-write
			STATUS current
			DESCRIPTION
				"Domain ID on which to set the multicast link."
			::= { sleEponRuleActionControl 19 }

		
		sleEponRuleActionControlMulticastLinkDomOffset OBJECT-TYPE
			SYNTAX Integer32
			MAX-ACCESS read-write
			STATUS current
			DESCRIPTION
				"Offset to the multicast link within the domain."
			::= { sleEponRuleActionControl 20 }

		
		sleEponRuleActionControlCosOperate OBJECT-TYPE
			SYNTAX INTEGER
				{
				cos(1),
				cosRepTag(2),
				cosCopy(3),
				cosClear(4)
				}
			MAX-ACCESS read-write
			STATUS current
			DESCRIPTION
				"cos operate.
				"
			::= { sleEponRuleActionControl 21 }

		
		sleEponRuleActionControlCosValue OBJECT-TYPE
			SYNTAX Integer32
			MAX-ACCESS read-write
			STATUS current
			DESCRIPTION
				"cos value."
			::= { sleEponRuleActionControl 22 }

		
		sleEponRuleActionControlTosOperate OBJECT-TYPE
			SYNTAX INTEGER
				{
				tos(1),
				tosClear(2)
				}
			MAX-ACCESS read-write
			STATUS current
			DESCRIPTION
				"tos operate."
			::= { sleEponRuleActionControl 23 }

		
		sleEponRuleActionControlTosValue OBJECT-TYPE
			SYNTAX Integer32
			MAX-ACCESS read-write
			STATUS current
			DESCRIPTION
				"tos value."
			::= { sleEponRuleActionControl 24 }

		
		sleEponRuleActionControlOutputOperate OBJECT-TYPE
			SYNTAX INTEGER
				{
				and(1),
				or(2),
				set(3),
				add(4),
				copy(5)
				}
			MAX-ACCESS read-write
			STATUS current
			DESCRIPTION
				"Rule action output on the selected field
				1.and,Perform a binary AND on the selected field
				2.or,Perform a binary OR on the selected field
				3.set,Set the selected field
				4.add,Add the selected field
				5.copy,Copy the selected field from another field.
				"
			::= { sleEponRuleActionControl 25 }

		
		sleEponRuleActionControlOutputValue OBJECT-TYPE
			SYNTAX Integer32
			MAX-ACCESS read-write
			STATUS current
			DESCRIPTION
				"output value."
			::= { sleEponRuleActionControl 26 }

		
		sleEponRuleActionControlOutputVlanContent OBJECT-TYPE
			SYNTAX INTEGER (0..8)
			MAX-ACCESS read-write
			STATUS current
			DESCRIPTION
				"0-3 vlan0 4-7 vlan1(0-TPID 1-CoS 2-VID 3-CoS and VID 4-TPID 5-CoS 6-VID 7-CoS and VID 8-IPv4 ToS."
			::= { sleEponRuleActionControl 27 }

		
		sleEponRuleActionControlOutputSourceFiledCopy OBJECT-TYPE
			SYNTAX Integer32 (1..25)
			MAX-ACCESS read-write
			STATUS current
			DESCRIPTION
				"Source field for the copy."
			::= { sleEponRuleActionControl 28 }

		
		sleEponRuleActionNotification OBJECT IDENTIFIER ::= { sleEponRuleAction 3 }

		
		sleEponRuleActionVlanChanged NOTIFICATION-TYPE
			OBJECTS { sleEponRuleActionControlRequest, sleEponRuleActionControlTimeStamp, sleEponRuleActionControlReqResult, sleEponRuleActionControlIndex, sleEponRuleActionControlVlanOperate, 
				sleEponRuleActionControlVlanMap, sleEponRuleActionControlEtherType, sleEponRuleActionControlVlanID }
			STATUS current
			DESCRIPTION 
				"Description."
			::= { sleEponRuleActionNotification 1 }

		
		sleEponRuleActionDiscardChanged NOTIFICATION-TYPE
			OBJECTS { sleEponRuleActionControlRequest, sleEponRuleActionControlTimeStamp, sleEponRuleActionControlReqResult, sleEponRuleActionControlIndex, sleEponRuleActionControlDiscardOperate, 
				sleEponRuleActionControlDiscardOperateValue }
			STATUS current
			DESCRIPTION 
				"Description."
			::= { sleEponRuleActionNotification 2 }

		
		sleEponRuleActionCaptureHostChanged NOTIFICATION-TYPE
			OBJECTS { sleEponRuleActionControlRequest, sleEponRuleActionControlTimeStamp, sleEponRuleActionControlReqResult, sleEponRuleActionControlIndex, sleEponRuleActionControlCaptureHostOperate
				 }
			STATUS current
			DESCRIPTION 
				"Description."
			::= { sleEponRuleActionNotification 3 }

		
		sleEponRuleActionCaptureHostFlexibleChanged NOTIFICATION-TYPE
			OBJECTS { sleEponRuleActionControlRequest, sleEponRuleActionControlTimeStamp, sleEponRuleActionControlReqResult, sleEponRuleActionControlIndex, sleEponRuleActionControlCaptureHostFlexibleOperate
				 }
			STATUS current
			DESCRIPTION 
				"Description."
			::= { sleEponRuleActionNotification 4 }

		
		sleEponRuleActionQueueChanged NOTIFICATION-TYPE
			OBJECTS { sleEponRuleActionControlRequest, sleEponRuleActionControlTimeStamp, sleEponRuleActionControlReqResult, sleEponRuleActionControlIndex, sleEponRuleActionControlQueueId
				 }
			STATUS current
			DESCRIPTION 
				"Description."
			::= { sleEponRuleActionNotification 5 }

		
		sleEponRuleActionUnicastLinkChanged NOTIFICATION-TYPE
			OBJECTS { sleEponRuleActionControlRequest, sleEponRuleActionControlTimeStamp, sleEponRuleActionControlReqResult, sleEponRuleActionControlIndex, sleEponRuleActionControlUnicastLinkDestID, 
				sleEponRuleActionControlUnicastLinkDestOffset }
			STATUS current
			DESCRIPTION 
				"Description."
			::= { sleEponRuleActionNotification 6 }

		
		sleEponRuleActionMulticastLinkChanged NOTIFICATION-TYPE
			OBJECTS { sleEponRuleActionControlRequest, sleEponRuleActionControlTimeStamp, sleEponRuleActionControlReqResult, sleEponRuleActionControlMulticastLinkDomID, sleEponRuleActionControlMulticastLinkDomOffset
				 }
			STATUS current
			DESCRIPTION 
				"Description."
			::= { sleEponRuleActionNotification 7 }

		
		sleEponRuleActionNoOperation NOTIFICATION-TYPE
			OBJECTS { sleEponRuleActionControlRequest, sleEponRuleActionControlTimeStamp, sleEponRuleActionControlReqResult, sleEponRuleActionControlIndex }
			STATUS current
			DESCRIPTION 
				"Description."
			::= { sleEponRuleActionNotification 8 }

		
		sleEponRuleActionCosChanged NOTIFICATION-TYPE
			OBJECTS { sleEponRuleActionControlRequest, sleEponRuleActionControlTimeStamp, sleEponRuleActionControlReqResult, sleEponRuleActionControlIndex, sleEponRuleActionControlCosOperate, 
				sleEponRuleActionControlCosValue }
			STATUS current
			DESCRIPTION 
				"Description."
			::= { sleEponRuleActionNotification 9 }

		
		sleEponRuleActionTosChanged NOTIFICATION-TYPE
			OBJECTS { sleEponRuleActionControlRequest, sleEponRuleActionControlTimeStamp, sleEponRuleActionControlReqResult, sleEponRuleActionControlIndex, sleEponRuleActionControlTosOperate, 
				sleEponRuleActionControlTosValue }
			STATUS current
			DESCRIPTION 
				"Description."
			::= { sleEponRuleActionNotification 10 }

		
		sleEponRuleActionOutputChanged NOTIFICATION-TYPE
			OBJECTS { sleEponRuleActionControlRequest, sleEponRuleActionControlTimeStamp, sleEponRuleActionControlReqResult, sleEponRuleActionControlIndex, sleEponRuleActionControlOutputOperate, 
				sleEponRuleActionControlOutputValue, sleEponRuleActionControlOutputSourceFiledCopy }
			STATUS current
			DESCRIPTION 
				"Description."
			::= { sleEponRuleActionNotification 11 }

		
		sleEponRuleActionQueuePendingChanged NOTIFICATION-TYPE
			OBJECTS { sleEponRuleActionControlRequest, sleEponRuleActionControlTimeStamp, sleEponRuleActionControlReqResult, sleEponRuleActionControlQueueId }
			STATUS current
			DESCRIPTION 
				"Description."
			::= { sleEponRuleActionNotification 12 }

		
		sleEponRuleActionSleChanged NOTIFICATION-TYPE
			OBJECTS { sleEponRuleActionControlRequest, sleEponRuleActionControlTimeStamp, sleEponRuleActionControlReqResult, sleEponRuleActionControlIndex }
			STATUS current
			DESCRIPTION 
				"Description."
			::= { sleEponRuleActionNotification 13 }

		
		sleEponRuleActionNoRuleAction NOTIFICATION-TYPE
			OBJECTS { sleEponProfilePortControlRequest, sleEponRuleActionControlRequest, sleEponRuleActionControlTimeStamp, sleEponRuleActionControlReqResult, sleEponRuleActionControlIndex
				 }
			STATUS current
			DESCRIPTION 
				"Description."
			::= { sleEponRuleActionNotification 14 }

		
		sleEponRuleModify OBJECT IDENTIFIER ::= { sleEponRule 3 }

		
		sleEponRuleModifyTable OBJECT-TYPE
			SYNTAX SEQUENCE OF SleEponRuleModifyEntry
			MAX-ACCESS not-accessible
			STATUS current
			DESCRIPTION
				"Description."
			::= { sleEponRuleModify 1 }

		
		sleEponRuleModifyEntry OBJECT-TYPE
			SYNTAX SleEponRuleModifyEntry
			MAX-ACCESS not-accessible
			STATUS current
			DESCRIPTION
				"Description."
			INDEX { sleEponOltIndex }
			::= { sleEponRuleModifyTable 1 }

		
		SleEponRuleModifyEntry ::=
			SEQUENCE { 
				sleEponRuleModifyRuleName
					OCTET STRING,
				sleEponRuleModifyTrafficDirection
					INTEGER,
				sleEponRuleModifyPriorityValue
					INTEGER,
				sleEponRuleModifyCIndex
					OCTET STRING,
				sleEponRuleModifyAIndex
					OCTET STRING
			 }

		sleEponRuleModifyRuleName OBJECT-TYPE
			SYNTAX OCTET STRING
			MAX-ACCESS read-only
			STATUS current
			DESCRIPTION
				"Pon rule name."
			::= { sleEponRuleModifyEntry 1 }

		
		sleEponRuleModifyTrafficDirection OBJECT-TYPE
			SYNTAX INTEGER
				{
				downstream(1),
				upstream(2)
				}
			MAX-ACCESS read-only
			STATUS current
			DESCRIPTION
				"The traffic direction of Rule .
				"
			::= { sleEponRuleModifyEntry 2 }

		
		sleEponRuleModifyPriorityValue OBJECT-TYPE
			SYNTAX INTEGER (0..15)
			MAX-ACCESS read-only
			STATUS current
			DESCRIPTION
				"Priority Value."
			::= { sleEponRuleModifyEntry 3 }

		
		sleEponRuleModifyCIndex OBJECT-TYPE
			SYNTAX OCTET STRING
			MAX-ACCESS read-only
			STATUS current
			DESCRIPTION
				"Rule clause index."
			::= { sleEponRuleModifyEntry 4 }

		
		sleEponRuleModifyAIndex OBJECT-TYPE
			SYNTAX OCTET STRING
			MAX-ACCESS read-only
			STATUS current
			DESCRIPTION
				"Rule action index."
			::= { sleEponRuleModifyEntry 5 }

		
		sleEponRuleModifyControl OBJECT IDENTIFIER ::= { sleEponRuleModify 2 }

		
		sleEponRuleModifyControlRequest OBJECT-TYPE
			SYNTAX INTEGER
				{
				ponRuleCreate(1),
				ponRuleModifyPriority(2),
				ponRuleModifyTrafficDir(3),
				ponRuleModifyClauseAdd(4),
				ponRuleModifyActionAdd(5),
				ponRuleModifyClauseDel(6),
				ponRuleModifyActionDel(7),
				noPonRule(8),
				oltRuleAddApply(9),
				oltRuleDelApply(10)
				}
			MAX-ACCESS read-write
			STATUS current
			DESCRIPTION
				"The request of a user command."
			::= { sleEponRuleModifyControl 1 }

		
		sleEponRuleModifyControlStatus OBJECT-TYPE
			SYNTAX SleControlStatusType
			MAX-ACCESS read-only
			STATUS current
			DESCRIPTION
				"The status of user command"
			::= { sleEponRuleModifyControl 2 }

		
		sleEponRuleModifyControlTimer OBJECT-TYPE
			SYNTAX Gauge32
			MAX-ACCESS read-write
			STATUS current
			DESCRIPTION
				"The maximum time for the manager for a long running user command"
			::= { sleEponRuleModifyControl 3 }

		
		sleEponRuleModifyControlTimeStamp OBJECT-TYPE
			SYNTAX TimeTicks
			MAX-ACCESS read-only
			STATUS current
			DESCRIPTION
				"The time stamp of the last command(end of command)"
			::= { sleEponRuleModifyControl 4 }

		
		sleEponRuleModifyControlReqResult OBJECT-TYPE
			SYNTAX SleControlRequestResultType
			MAX-ACCESS read-only
			STATUS current
			DESCRIPTION
				"The result of the last user command"
			::= { sleEponRuleModifyControl 5 }

		
		sleEponRuleModifyControlOltId OBJECT-TYPE
			SYNTAX INTEGER (1..24)
			MAX-ACCESS read-write
			STATUS current
			DESCRIPTION
				"Olt index."
			::= { sleEponRuleModifyControl 6 }

		
		sleEponRuleModifyControlRuleName OBJECT-TYPE
			SYNTAX OCTET STRING
			MAX-ACCESS read-write
			STATUS current
			DESCRIPTION
				"Pon rule name."
			::= { sleEponRuleModifyControl 7 }

		
		sleEponRuleModifyControlTrafficDirection OBJECT-TYPE
			SYNTAX INTEGER
				{
				downstream(1),
				upstream(2)
				}
			MAX-ACCESS read-write
			STATUS current
			DESCRIPTION
				"The traffic direction of Rule .
				"
			::= { sleEponRuleModifyControl 8 }

		
		sleEponRuleModifyControlPriorityValue OBJECT-TYPE
			SYNTAX INTEGER (0..15)
			MAX-ACCESS read-write
			STATUS current
			DESCRIPTION
				"Priority Value."
			::= { sleEponRuleModifyControl 9 }

		
		sleEponRuleModifyControlCIndex OBJECT-TYPE
			SYNTAX INTEGER (1..8)
			MAX-ACCESS read-write
			STATUS current
			DESCRIPTION
				"Rule clause index."
			::= { sleEponRuleModifyControl 10 }

		
		sleEponRuleModifyControlAIndex OBJECT-TYPE
			SYNTAX INTEGER (1..8)
			MAX-ACCESS read-write
			STATUS current
			DESCRIPTION
				"Rule action index."
			::= { sleEponRuleModifyControl 11 }

		
		sleEponRuleModifyNotification OBJECT IDENTIFIER ::= { sleEponRuleModify 3 }

		
		sleEponRuleOltRuleCreate NOTIFICATION-TYPE
			OBJECTS { sleEponRuleModifyControlRequest, sleEponRuleModifyControlTimeStamp, sleEponRuleModifyControlReqResult, sleEponRuleModifyControlRuleName, sleEponRuleModifyControlPriorityValue, 
				sleEponRuleModifyControlCIndex, sleEponRuleModifyControlAIndex }
			STATUS current
			DESCRIPTION 
				"Description."
			::= { sleEponRuleModifyNotification 1 }

		
		sleEponRuleModifyPriorityChange NOTIFICATION-TYPE
			OBJECTS { sleEponRuleModifyControlRequest, sleEponRuleModifyControlTimeStamp, sleEponRuleModifyControlReqResult, sleEponRuleModifyControlRuleName, sleEponRuleModifyControlPriorityValue, 
				sleEponRuleModifyControlTrafficDirection }
			STATUS current
			DESCRIPTION 
				"Description."
			::= { sleEponRuleModifyNotification 2 }

		
		sleEponRuleModifyTrafficDirChange NOTIFICATION-TYPE
			OBJECTS { sleEponRuleModifyControlRequest, sleEponRuleModifyControlTimeStamp, sleEponRuleModifyControlReqResult, sleEponRuleModifyControlRuleName, sleEponRuleModifyControlPriorityValue, 
				sleEponRuleModifyControlTrafficDirection }
			STATUS current
			DESCRIPTION 
				"Description."
			::= { sleEponRuleModifyNotification 3 }

		
		sleEponRuleModifyClauseAdd NOTIFICATION-TYPE
			OBJECTS { sleEponRuleModifyControlRequest, sleEponRuleModifyControlTimeStamp, sleEponRuleModifyControlReqResult, sleEponRuleModifyControlRuleName, sleEponRuleModifyControlCIndex, 
				sleEponRuleModifyControlAIndex }
			STATUS current
			DESCRIPTION 
				"Description."
			::= { sleEponRuleModifyNotification 4 }

		
		sleEponRuleModifyActionAdd NOTIFICATION-TYPE
			OBJECTS { sleEponRuleModifyControlRequest, sleEponRuleModifyControlTimeStamp, sleEponRuleModifyControlReqResult, sleEponRuleModifyControlRuleName, sleEponRuleModifyControlCIndex, 
				sleEponRuleModifyControlAIndex }
			STATUS current
			DESCRIPTION 
				"Description."
			::= { sleEponRuleModifyNotification 5 }

		
		sleEponRuleModifyClauseDel NOTIFICATION-TYPE
			OBJECTS { sleEponRuleModifyControlRequest, sleEponRuleModifyControlTimeStamp, sleEponRuleModifyControlReqResult, sleEponRuleModifyControlRuleName, sleEponRuleModifyControlCIndex, 
				sleEponRuleModifyControlAIndex }
			STATUS current
			DESCRIPTION 
				"Description."
			::= { sleEponRuleModifyNotification 6 }

		
		sleEponRuleModifyActionDel NOTIFICATION-TYPE
			OBJECTS { sleEponRuleModifyControlRequest, sleEponRuleModifyControlTimeStamp, sleEponRuleModifyControlReqResult, sleEponRuleModifyControlRuleName, sleEponRuleModifyControlCIndex, 
				sleEponRuleModifyControlAIndex }
			STATUS current
			DESCRIPTION 
				"Description."
			::= { sleEponRuleModifyNotification 7 }

		
		sleEponRuleOltRuleDelete NOTIFICATION-TYPE
			OBJECTS { sleEponRuleModifyControlRequest, sleEponRuleModifyControlReqResult, sleEponRuleModifyControlOltId, sleEponRuleModifyControlTimeStamp, sleEponRuleModifyControlRuleName
				 }
			STATUS current
			DESCRIPTION 
				"Description."
			::= { sleEponRuleModifyNotification 8 }

		
		sleEponRuleOltRuleAddApply NOTIFICATION-TYPE
			OBJECTS { sleEponRuleModifyControlRequest, sleEponRuleModifyControlTimeStamp, sleEponRuleModifyControlReqResult, sleEponRuleModifyControlOltId, sleEponRuleModifyControlRuleName
				 }
			STATUS current
			DESCRIPTION 
				"Description."
			::= { sleEponRuleModifyNotification 9 }

		
		sleEponRuleOltRuleDelApply NOTIFICATION-TYPE
			OBJECTS { sleEponRuleModifyControlRequest, sleEponRuleModifyControlTimeStamp, sleEponRuleModifyControlReqResult, sleEponRuleModifyControlOltId, sleEponRuleModifyControlRuleName
				 }
			STATUS current
			DESCRIPTION 
				"Description."
			::= { sleEponRuleModifyNotification 10 }

		
		sleEponOnuRule OBJECT IDENTIFIER ::= { sleEponRule 4 }

		
		sleEponOnuRuleTable OBJECT-TYPE
			SYNTAX SEQUENCE OF SleEponOnuRuleEntry
			MAX-ACCESS not-accessible
			STATUS current
			DESCRIPTION
				"Description."
			::= { sleEponOnuRule 1 }

		
		sleEponOnuRuleEntry OBJECT-TYPE
			SYNTAX SleEponOnuRuleEntry
			MAX-ACCESS not-accessible
			STATUS current
			DESCRIPTION
				"Epon onu rule table."
			INDEX { sleEponOnuRuleIndex }
			::= { sleEponOnuRuleTable 1 }

		
		SleEponOnuRuleEntry ::=
			SEQUENCE { 
				sleEponOnuRuleName
					OCTET STRING,
				sleEponOnuRuleIndex
					Integer32,
				sleEponOnuRuleDirection
					INTEGER,
				sleEponOnuRulePriority
					Integer32,
				sleEponOnuRuleDscp
					OCTET STRING,
				sleEponOnuRuleLinkIndex
					INTEGER,
				sleEponOnuRuleQueueIndex
					INTEGER
			 }

		sleEponOnuRuleName OBJECT-TYPE
			SYNTAX OCTET STRING
			MAX-ACCESS read-only
			STATUS current
			DESCRIPTION
				"Epon onu rule name."
			::= { sleEponOnuRuleEntry 1 }

		
		sleEponOnuRuleIndex OBJECT-TYPE
			SYNTAX Integer32 (1..512)
			MAX-ACCESS read-only
			STATUS current
			DESCRIPTION
				"Rule Index"
			::= { sleEponOnuRuleEntry 2 }

		
		sleEponOnuRuleDirection OBJECT-TYPE
			SYNTAX INTEGER
				{
				dowbStream(1),
				upStream(2)
				}
			MAX-ACCESS read-only
			STATUS current
			DESCRIPTION
				"Traffic direction."
			::= { sleEponOnuRuleEntry 3 }

		
		sleEponOnuRulePriority OBJECT-TYPE
			SYNTAX Integer32
			MAX-ACCESS read-only
			STATUS current
			DESCRIPTION
				"Priority."
			::= { sleEponOnuRuleEntry 4 }

		
		sleEponOnuRuleDscp OBJECT-TYPE
			SYNTAX OCTET STRING
			MAX-ACCESS read-write
			STATUS current
			DESCRIPTION
				"Epon onu rule dscp."
			::= { sleEponOnuRuleEntry 5 }

		
		sleEponOnuRuleLinkIndex OBJECT-TYPE
			SYNTAX INTEGER (0..1)
			MAX-ACCESS read-write
			STATUS current
			DESCRIPTION
				"Epon onu rule link index."
			::= { sleEponOnuRuleEntry 6 }

		
		sleEponOnuRuleQueueIndex OBJECT-TYPE
			SYNTAX INTEGER (0..3)
			MAX-ACCESS read-write
			STATUS current
			DESCRIPTION
				"Epon onu rule queue index"
			::= { sleEponOnuRuleEntry 7 }

		
		sleEponOnuRuleControl OBJECT IDENTIFIER ::= { sleEponOnuRule 2 }

		
		sleEponOnuRuleControlRequest OBJECT-TYPE
			SYNTAX INTEGER
				{
				createOnuRule(1),
				deleteOnuRule(2)
				}
			MAX-ACCESS read-write
			STATUS current
			DESCRIPTION
				"The request of a user command."
			::= { sleEponOnuRuleControl 1 }

		
		sleEponOnuRuleControlStatus OBJECT-TYPE
			SYNTAX SleControlStatusType
			MAX-ACCESS read-only
			STATUS current
			DESCRIPTION
				"The status of user command."
			::= { sleEponOnuRuleControl 2 }

		
		sleEponOnuRuleControlTimer OBJECT-TYPE
			SYNTAX Gauge32
			MAX-ACCESS read-write
			STATUS current
			DESCRIPTION
				"The maximum time for the manager for a long running user command."
			::= { sleEponOnuRuleControl 3 }

		
		sleEponOnuRuleControlTimeStamp OBJECT-TYPE
			SYNTAX TimeTicks
			MAX-ACCESS read-only
			STATUS current
			DESCRIPTION
				"The time stamp of the last command(end of command)."
			::= { sleEponOnuRuleControl 4 }

		
		sleEponOnuRuleControlReqResult OBJECT-TYPE
			SYNTAX SleControlRequestResultType
			MAX-ACCESS read-only
			STATUS current
			DESCRIPTION
				"The result of the last user command."
			::= { sleEponOnuRuleControl 5 }

		
		sleEponOnuRuleControlRuleName OBJECT-TYPE
			SYNTAX OCTET STRING
			MAX-ACCESS read-write
			STATUS current
			DESCRIPTION
				"Epon onu rule name."
			::= { sleEponOnuRuleControl 6 }

		
		sleEponOnuRuleControlDscp OBJECT-TYPE
			SYNTAX INTEGER
				{
				cs01(1),
				cs23(2),
				cs45(3),
				cs67(4)
				}
			MAX-ACCESS read-write
			STATUS current
			DESCRIPTION
				"Epon onu rule dscp."
			::= { sleEponOnuRuleControl 7 }

		
		sleEponOnuRuleControlLinkIndex OBJECT-TYPE
			SYNTAX INTEGER (0..1)
			MAX-ACCESS read-write
			STATUS current
			DESCRIPTION
				"Epon onu rule link index."
			::= { sleEponOnuRuleControl 8 }

		
		sleEponOnuRuleControlQueueIndex OBJECT-TYPE
			SYNTAX INTEGER (0..3)
			MAX-ACCESS read-write
			STATUS current
			DESCRIPTION
				"Epon onu rule queue index"
			::= { sleEponOnuRuleControl 9 }

		
		sleEponOnuRuleNotification OBJECT IDENTIFIER ::= { sleEponOnuRule 3 }

		
		sleEponOnuRuleChanged NOTIFICATION-TYPE
			OBJECTS { sleEponOnuRuleControlRequest, sleEponOnuRuleControlTimeStamp, sleEponOnuRuleControlReqResult, sleEponOnuRuleControlRuleName }
			STATUS current
			DESCRIPTION 
				"Trap of create or delete onu rule."
			::= { sleEponOnuRuleNotification 1 }

		
		sleEponOnuRuleProfile OBJECT IDENTIFIER ::= { sleEponRule 5 }

		
		sleEponOnuRuleProfileTable OBJECT-TYPE
			SYNTAX SEQUENCE OF SleEponOnuRuleProfileEntry
			MAX-ACCESS not-accessible
			STATUS current
			DESCRIPTION
				"Description."
			::= { sleEponOnuRuleProfile 1 }

		
		sleEponOnuRuleProfileEntry OBJECT-TYPE
			SYNTAX SleEponOnuRuleProfileEntry
			MAX-ACCESS not-accessible
			STATUS current
			DESCRIPTION
				"Description."
			INDEX { sleEponOnuRuleProfileName }
			::= { sleEponOnuRuleProfileTable 1 }

		
		SleEponOnuRuleProfileEntry ::=
			SEQUENCE { 
				sleEponOnuRuleProfileName
					OCTET STRING,
				sleEponRuleOnuProfilePolicyCount
					Unsigned32,
				sleEponRuleOnuProfileRefCount
					Unsigned32,
				sleEponOnuRuleRefProfileNameList
					OCTET STRING
			 }

		sleEponOnuRuleProfileName OBJECT-TYPE
			SYNTAX OCTET STRING
			MAX-ACCESS read-only
			STATUS current
			DESCRIPTION
				"rule profile name"
			::= { sleEponOnuRuleProfileEntry 1 }

		
		sleEponRuleOnuProfilePolicyCount OBJECT-TYPE
			SYNTAX Unsigned32
			MAX-ACCESS read-only
			STATUS current
			DESCRIPTION
				"policy count"
			::= { sleEponOnuRuleProfileEntry 2 }

		
		sleEponRuleOnuProfileRefCount OBJECT-TYPE
			SYNTAX Unsigned32
			MAX-ACCESS read-only
			STATUS current
			DESCRIPTION
				"count of reference by profile"
			::= { sleEponOnuRuleProfileEntry 3 }

		
		sleEponOnuRuleRefProfileNameList OBJECT-TYPE
			SYNTAX OCTET STRING
			MAX-ACCESS read-only
			STATUS current
			DESCRIPTION
				"referring profile name list"
			::= { sleEponOnuRuleProfileEntry 4 }

		
		sleEponOnuRulePolicyTable OBJECT-TYPE
			SYNTAX SEQUENCE OF SleEponOnuRulePolicyEntry
			MAX-ACCESS not-accessible
			STATUS current
			DESCRIPTION
				"Description."
			::= { sleEponOnuRuleProfile 2 }

		
		sleEponOnuRulePolicyEntry OBJECT-TYPE
			SYNTAX SleEponOnuRulePolicyEntry
			MAX-ACCESS not-accessible
			STATUS current
			DESCRIPTION
				"Description."
			INDEX { sleEponOnuRuleProfileName, sleEponOnuRulePolicyIndex }
			::= { sleEponOnuRulePolicyTable 1 }

		
		SleEponOnuRulePolicyEntry ::=
			SEQUENCE { 
				sleEponOnuRulePolicyIndex
					INTEGER,
				sleEponOnuRulePolicyDirection
					INTEGER,
				sleEponOnuRulePolicyPriority
					INTEGER,
				sleEponOnuRulePolicyFlowCount
					Unsigned32,
				sleEponOnuRulePolicyFlowString
					OCTET STRING,
				sleEponOnuRulePolicyActionCount
					Unsigned32,
				sleEponOnuRulePolicyActionString
					OCTET STRING
			 }

		sleEponOnuRulePolicyIndex OBJECT-TYPE
			SYNTAX INTEGER (1..16)
			MAX-ACCESS read-only
			STATUS current
			DESCRIPTION
				"policy index"
			::= { sleEponOnuRulePolicyEntry 1 }

		
		sleEponOnuRulePolicyDirection OBJECT-TYPE
			SYNTAX INTEGER
				{
				upStream(1),
				downStream(2)
				}
			MAX-ACCESS read-only
			STATUS current
			DESCRIPTION
				"policy direction"
			::= { sleEponOnuRulePolicyEntry 2 }

		
		sleEponOnuRulePolicyPriority OBJECT-TYPE
			SYNTAX INTEGER
				{
				low(1),
				medium(2),
				high(3)
				}
			MAX-ACCESS read-only
			STATUS current
			DESCRIPTION
				"policy priority"
			::= { sleEponOnuRulePolicyEntry 3 }

		
		sleEponOnuRulePolicyFlowCount OBJECT-TYPE
			SYNTAX Unsigned32
			MAX-ACCESS read-only
			STATUS current
			DESCRIPTION
				"referred flow count"
			::= { sleEponOnuRulePolicyEntry 4 }

		
		sleEponOnuRulePolicyFlowString OBJECT-TYPE
			SYNTAX OCTET STRING
			MAX-ACCESS read-only
			STATUS current
			DESCRIPTION
				"referred flow list"
			::= { sleEponOnuRulePolicyEntry 5 }

		
		sleEponOnuRulePolicyActionCount OBJECT-TYPE
			SYNTAX Unsigned32
			MAX-ACCESS read-only
			STATUS current
			DESCRIPTION
				"referred action count"
			::= { sleEponOnuRulePolicyEntry 6 }

		
		sleEponOnuRulePolicyActionString OBJECT-TYPE
			SYNTAX OCTET STRING
			MAX-ACCESS read-only
			STATUS current
			DESCRIPTION
				"referred action id list"
			::= { sleEponOnuRulePolicyEntry 7 }

		
		sleEponOnuRuleProfileControl OBJECT IDENTIFIER ::= { sleEponOnuRuleProfile 3 }

		
		sleEponOnuRuleProfileControlRequest OBJECT-TYPE
			SYNTAX INTEGER
				{
				creatRuleProfileWithoutPolicy(1),
				createRuleProfileWithPolicy(2),
				setRuleProfilePolicy(3),
				noRuleProfilePolicy(4),
				noRuleProfile(5)
				}
			MAX-ACCESS read-write
			STATUS current
			DESCRIPTION
				"Description."
			::= { sleEponOnuRuleProfileControl 1 }

		
		sleEponOnuRuleProfileControlStatus OBJECT-TYPE
			SYNTAX SleControlStatusType
			MAX-ACCESS read-only
			STATUS current
			DESCRIPTION
				"Description."
			::= { sleEponOnuRuleProfileControl 2 }

		
		sleEponOnuRuleProfileControlTimer OBJECT-TYPE
			SYNTAX Gauge32
			MAX-ACCESS read-write
			STATUS current
			DESCRIPTION
				"Description."
			::= { sleEponOnuRuleProfileControl 3 }

		
		sleEponOnuRuleProfileControlTimeStamp OBJECT-TYPE
			SYNTAX TimeTicks
			MAX-ACCESS read-only
			STATUS current
			DESCRIPTION
				"Description."
			::= { sleEponOnuRuleProfileControl 4 }

		
		sleEponOnuRuleProfileControlReqResult OBJECT-TYPE
			SYNTAX SleControlRequestResultType
			MAX-ACCESS read-only
			STATUS current
			DESCRIPTION
				"Description."
			::= { sleEponOnuRuleProfileControl 5 }

		
		sleEponOnuRuleProfileControlName OBJECT-TYPE
			SYNTAX OCTET STRING
			MAX-ACCESS read-write
			STATUS current
			DESCRIPTION
				"rule profile name"
			::= { sleEponOnuRuleProfileControl 6 }

		
		sleEponOnuRuleProfileControlPolicyIndex OBJECT-TYPE
			SYNTAX INTEGER (1..16)
			MAX-ACCESS read-write
			STATUS current
			DESCRIPTION
				"policy index"
			::= { sleEponOnuRuleProfileControl 7 }

		
		sleEponOnuRuleProfileControlPolicyDirection OBJECT-TYPE
			SYNTAX INTEGER
				{
				upStream(1),
				downStream(2)
				}
			MAX-ACCESS read-write
			STATUS current
			DESCRIPTION
				"policy direction"
			::= { sleEponOnuRuleProfileControl 8 }

		
		sleEponOnuRuleProfileControlPolicyPriority OBJECT-TYPE
			SYNTAX INTEGER
				{
				low(1),
				medium(2),
				high(3)
				}
			MAX-ACCESS read-write
			STATUS current
			DESCRIPTION
				"policy priority"
			::= { sleEponOnuRuleProfileControl 9 }

		
		sleEponOnuRuleProfileControlPolicyFlowList OBJECT-TYPE
			SYNTAX OCTET STRING
			MAX-ACCESS read-write
			STATUS current
			DESCRIPTION
				"Flow list for current policy, the write format is 1,2...16"
			::= { sleEponOnuRuleProfileControl 10 }

		
		sleEponOnuRuleProfileControlPolicyActionList OBJECT-TYPE
			SYNTAX OCTET STRING
			MAX-ACCESS read-write
			STATUS current
			DESCRIPTION
				"Action list for current policy, the writing format is 1,2...16"
			::= { sleEponOnuRuleProfileControl 11 }

		
		sleEponRuleProfileNotification OBJECT IDENTIFIER ::= { sleEponOnuRuleProfile 4 }

		
		sleEponOnuRuleProfileChanged NOTIFICATION-TYPE
			OBJECTS { sleEponOnuRuleProfileControlRequest, sleEponOnuRuleProfileControlTimeStamp, sleEponOnuRuleProfileControlReqResult, sleEponOnuRuleProfileControlName }
			STATUS current
			DESCRIPTION 
				"Description."
			::= { sleEponRuleProfileNotification 1 }

		
		sleEponOnuRuleFlow OBJECT IDENTIFIER ::= { sleEponRule 6 }

		
		sleEponOnuRuleFlowTable OBJECT-TYPE
			SYNTAX SEQUENCE OF SleEponOnuRuleFlowEntry
			MAX-ACCESS not-accessible
			STATUS current
			DESCRIPTION
				"Description."
			::= { sleEponOnuRuleFlow 1 }

		
		sleEponOnuRuleFlowEntry OBJECT-TYPE
			SYNTAX SleEponOnuRuleFlowEntry
			MAX-ACCESS not-accessible
			STATUS current
			DESCRIPTION
				"Description."
			INDEX { sleEponOnuRuleFlowIndex }
			::= { sleEponOnuRuleFlowTable 1 }

		
		SleEponOnuRuleFlowEntry ::=
			SEQUENCE { 
				sleEponOnuRuleFlowIndex
					INTEGER,
				sleEponOnuRuleFlowType
					INTEGER,
				sleEponOnuRuleFlowRefCount
					Integer32,
				sleEponOnuRuleFlowOP
					INTEGER,
				sleEponOnuRuleFlowEthType
					Unsigned32,
				sleEponOnuRuleFlowPort
					Integer32,
				sleEponOnuRuleFlowMacAddress
					OCTET STRING,
				sleEponOnuRuleFlowIpAddress
					IpAddress,
				sleEponOnuRuleFlowMacMask
					INTEGER,
				sleEponOnuRuleFlowIpMask
					INTEGER
			 }

		sleEponOnuRuleFlowIndex OBJECT-TYPE
			SYNTAX INTEGER (1..1024)
			MAX-ACCESS read-only
			STATUS current
			DESCRIPTION
				"flow index"
			::= { sleEponOnuRuleFlowEntry 1 }

		
		sleEponOnuRuleFlowType OBJECT-TYPE
			SYNTAX INTEGER
				{
				dstMac(1),
				srcMac(2),
				ethType(3),
				srcPort(8),
				dstPort(9),
				srcIP(12),
				dstIP(14)
				}
			MAX-ACCESS read-only
			STATUS current
			DESCRIPTION
				"flow type"
			::= { sleEponOnuRuleFlowEntry 2 }

		
		sleEponOnuRuleFlowRefCount OBJECT-TYPE
			SYNTAX Integer32
			MAX-ACCESS read-only
			STATUS current
			DESCRIPTION
				"count referred by rule policy"
			::= { sleEponOnuRuleFlowEntry 3 }

		
		sleEponOnuRuleFlowOP OBJECT-TYPE
			SYNTAX INTEGER
				{
				match(1),
				noMatch(2),
				allMatch(7)
				}
			MAX-ACCESS read-only
			STATUS current
			DESCRIPTION
				"operation"
			::= { sleEponOnuRuleFlowEntry 4 }

		
		sleEponOnuRuleFlowEthType OBJECT-TYPE
			SYNTAX Unsigned32
			MAX-ACCESS read-only
			STATUS current
			DESCRIPTION
				"0x0800=IP 0x0806=ARP"
			::= { sleEponOnuRuleFlowEntry 5 }

		
		sleEponOnuRuleFlowPort OBJECT-TYPE
			SYNTAX Integer32
			MAX-ACCESS read-only
			STATUS current
			DESCRIPTION
				"Port"
			::= { sleEponOnuRuleFlowEntry 6 }

		
		sleEponOnuRuleFlowMacAddress OBJECT-TYPE
			SYNTAX OCTET STRING
			MAX-ACCESS read-only
			STATUS current
			DESCRIPTION
				"Mac Address"
			::= { sleEponOnuRuleFlowEntry 7 }

		
		sleEponOnuRuleFlowIpAddress OBJECT-TYPE
			SYNTAX IpAddress
			MAX-ACCESS read-only
			STATUS current
			DESCRIPTION
				"Ip Address"
			::= { sleEponOnuRuleFlowEntry 8 }

		
		sleEponOnuRuleFlowMacMask OBJECT-TYPE
			SYNTAX INTEGER (1..48)
			MAX-ACCESS read-only
			STATUS current
			DESCRIPTION
				"Mask for Mac and IP address"
			::= { sleEponOnuRuleFlowEntry 9 }

		
		sleEponOnuRuleFlowIpMask OBJECT-TYPE
			SYNTAX INTEGER (1..32)
			MAX-ACCESS read-only
			STATUS current
			DESCRIPTION
				"Mask for Mac and IP address"
			::= { sleEponOnuRuleFlowEntry 10 }

		
		sleEponOnuRuleFlowControl OBJECT IDENTIFIER ::= { sleEponOnuRuleFlow 2 }

		
		sleEponOnuRuleFlowControlRequest OBJECT-TYPE
			SYNTAX INTEGER
				{
				setRuleFlow(1),
				noRuleFlow(2)
				}
			MAX-ACCESS read-write
			STATUS current
			DESCRIPTION
				"Description."
			::= { sleEponOnuRuleFlowControl 1 }

		
		sleEponOnuRuleFlowControlStatus OBJECT-TYPE
			SYNTAX SleControlStatusType
			MAX-ACCESS read-only
			STATUS current
			DESCRIPTION
				"Description."
			::= { sleEponOnuRuleFlowControl 2 }

		
		sleEponOnuRuleFlowControlTimer OBJECT-TYPE
			SYNTAX Gauge32
			MAX-ACCESS read-write
			STATUS current
			DESCRIPTION
				"Description."
			::= { sleEponOnuRuleFlowControl 3 }

		
		sleEponOnuRuleFlowControlTimeStamp OBJECT-TYPE
			SYNTAX TimeTicks
			MAX-ACCESS read-only
			STATUS current
			DESCRIPTION
				"Description."
			::= { sleEponOnuRuleFlowControl 4 }

		
		sleEponOnuRuleFlowControlReqResult OBJECT-TYPE
			SYNTAX SleControlRequestResultType
			MAX-ACCESS read-only
			STATUS current
			DESCRIPTION
				"Description."
			::= { sleEponOnuRuleFlowControl 5 }

		
		sleEponOnuRuleFlowControlIndex OBJECT-TYPE
			SYNTAX INTEGER (1..1024)
			MAX-ACCESS read-write
			STATUS current
			DESCRIPTION
				"Description."
			::= { sleEponOnuRuleFlowControl 6 }

		
		sleEponOnuRuleFlowControlType OBJECT-TYPE
			SYNTAX INTEGER
				{
				dstMac(1),
				srcMac(2),
				ethType(3),
				srcPort(8),
				dstPort(9),
				srcIp(12),
				dstIp(14)
				}
			MAX-ACCESS read-write
			STATUS current
			DESCRIPTION
				"Description."
			::= { sleEponOnuRuleFlowControl 7 }

		
		sleEponOnuRuleFlowControlOP OBJECT-TYPE
			SYNTAX INTEGER
				{
				match(1),
				noMatch(2),
				allMatch(7)
				}
			MAX-ACCESS read-write
			STATUS current
			DESCRIPTION
				"Description."
			::= { sleEponOnuRuleFlowControl 8 }

		
		sleEponOnuRuleFlowControlEthType OBJECT-TYPE
			SYNTAX Unsigned32
			MAX-ACCESS read-write
			STATUS current
			DESCRIPTION
				"Description."
			::= { sleEponOnuRuleFlowControl 9 }

		
		sleEponOnuRuleFlowControlPort OBJECT-TYPE
			SYNTAX INTEGER (1..65535)
			MAX-ACCESS read-write
			STATUS current
			DESCRIPTION
				"Description."
			::= { sleEponOnuRuleFlowControl 10 }

		
		sleEponOnuRuleFlowControlMacAddress OBJECT-TYPE
			SYNTAX OCTET STRING
			MAX-ACCESS read-write
			STATUS current
			DESCRIPTION
				"Description."
			::= { sleEponOnuRuleFlowControl 11 }

		
		sleEponOnuRuleFlowControlIpAddress OBJECT-TYPE
			SYNTAX IpAddress
			MAX-ACCESS read-write
			STATUS current
			DESCRIPTION
				"Description."
			::= { sleEponOnuRuleFlowControl 12 }

		
		sleEponOnuRuleFlowControlMacMask OBJECT-TYPE
			SYNTAX INTEGER (1..48)
			MAX-ACCESS read-write
			STATUS current
			DESCRIPTION
				"Description."
			::= { sleEponOnuRuleFlowControl 13 }

		
		sleEponOnuRuleFlowControlIpMask OBJECT-TYPE
			SYNTAX INTEGER (1..32)
			MAX-ACCESS read-write
			STATUS current
			DESCRIPTION
				"Description."
			::= { sleEponOnuRuleFlowControl 14 }

		
		sleEponOnuRuleFlowNotification OBJECT IDENTIFIER ::= { sleEponOnuRuleFlow 3 }

		
		sleEponOnuRuleFlowChanged NOTIFICATION-TYPE
			OBJECTS { sleEponOnuRuleFlowControlRequest, sleEponOnuRuleFlowControlTimeStamp, sleEponOnuRuleFlowControlReqResult, sleEponOnuRuleFlowControlIndex }
			STATUS current
			DESCRIPTION 
				"Description."
			::= { sleEponOnuRuleFlowNotification 1 }

		
		sleEponOnuRuleAction OBJECT IDENTIFIER ::= { sleEponRule 7 }

		
		sleEponOnuRuleActionTable OBJECT-TYPE
			SYNTAX SEQUENCE OF SleEponOnuRuleActionEntry
			MAX-ACCESS not-accessible
			STATUS current
			DESCRIPTION
				"Description."
			::= { sleEponOnuRuleAction 1 }

		
		sleEponOnuRuleActionEntry OBJECT-TYPE
			SYNTAX SleEponOnuRuleActionEntry
			MAX-ACCESS not-accessible
			STATUS current
			DESCRIPTION
				"Description."
			INDEX { sleEponOnuRuleActionIndex }
			::= { sleEponOnuRuleActionTable 1 }

		
		SleEponOnuRuleActionEntry ::=
			SEQUENCE { 
				sleEponOnuRuleActionIndex
					INTEGER,
				sleEponOnuRuleActionType
					INTEGER,
				sleEponOnuRuleActionRefCount
					Unsigned32
			 }

		sleEponOnuRuleActionIndex OBJECT-TYPE
			SYNTAX INTEGER (1..1024)
			MAX-ACCESS read-only
			STATUS current
			DESCRIPTION
				"Index of Rule action, applied for V8500"
			::= { sleEponOnuRuleActionEntry 1 }

		
		sleEponOnuRuleActionType OBJECT-TYPE
			SYNTAX INTEGER
				{
				deny(14),
				permit(16)
				}
			MAX-ACCESS read-only
			STATUS current
			DESCRIPTION
				"action type of Epon Rule, applied for V8500"
			::= { sleEponOnuRuleActionEntry 2 }

		
		sleEponOnuRuleActionRefCount OBJECT-TYPE
			SYNTAX Unsigned32
			MAX-ACCESS read-only
			STATUS current
			DESCRIPTION
				"count that referred by rule policy"
			::= { sleEponOnuRuleActionEntry 3 }

		
		sleEponOnuRuleActionControl OBJECT IDENTIFIER ::= { sleEponOnuRuleAction 2 }

		
		sleEponOnuRuleActionControlRequest OBJECT-TYPE
			SYNTAX INTEGER
				{
				setRuleFlow(1),
				noRuleFlow(2)
				}
			MAX-ACCESS read-write
			STATUS current
			DESCRIPTION
				"Description."
			::= { sleEponOnuRuleActionControl 1 }

		
		sleEponOnuRuleActionControlStatus OBJECT-TYPE
			SYNTAX SleControlStatusType
			MAX-ACCESS read-only
			STATUS current
			DESCRIPTION
				"Description."
			::= { sleEponOnuRuleActionControl 2 }

		
		sleEponOnuRuleActionControlTimer OBJECT-TYPE
			SYNTAX Gauge32
			MAX-ACCESS read-write
			STATUS current
			DESCRIPTION
				"Description."
			::= { sleEponOnuRuleActionControl 3 }

		
		sleEponOnuRuleActionControlTimeStamp OBJECT-TYPE
			SYNTAX TimeTicks
			MAX-ACCESS read-only
			STATUS current
			DESCRIPTION
				"Description."
			::= { sleEponOnuRuleActionControl 4 }

		
		sleEponOnuRuleActionControlReqResult OBJECT-TYPE
			SYNTAX SleControlRequestResultType
			MAX-ACCESS read-only
			STATUS current
			DESCRIPTION
				"Description."
			::= { sleEponOnuRuleActionControl 5 }

		
		sleEponOnuRuleActionControlIndex OBJECT-TYPE
			SYNTAX INTEGER (1..1024)
			MAX-ACCESS read-write
			STATUS current
			DESCRIPTION
				"Rule action index."
			::= { sleEponOnuRuleActionControl 6 }

		
		sleEponOnuRuleActionControlType OBJECT-TYPE
			SYNTAX INTEGER
				{
				deny(14),
				permit(16)
				}
			MAX-ACCESS read-write
			STATUS current
			DESCRIPTION
				"Rule action type, applied for V8500"
			::= { sleEponOnuRuleActionControl 7 }

		
		sleEponOnuRuleActionNotification OBJECT IDENTIFIER ::= { sleEponOnuRuleAction 3 }

		
		sleEponOnuRuleActionChanged NOTIFICATION-TYPE
			OBJECTS { sleEponOnuRuleActionControlRequest, sleEponOnuRuleActionControlTimeStamp, sleEponOnuRuleActionControlReqResult, sleEponOnuRuleActionControlIndex }
			STATUS current
			DESCRIPTION 
				"applied for V8500"
			::= { sleEponOnuRuleActionNotification 1 }

		
		sleEponDBA OBJECT IDENTIFIER ::= { sleEpon 14 }

		
		sleEponOltDBA OBJECT IDENTIFIER ::= { sleEponDBA 1 }

		
		sleEponOltDBATable OBJECT-TYPE
			SYNTAX SEQUENCE OF SleEponOltDBAEntry
			MAX-ACCESS not-accessible
			STATUS current
			DESCRIPTION
				"Description."
			::= { sleEponOltDBA 1 }

		
		sleEponOltDBAEntry OBJECT-TYPE
			SYNTAX SleEponOltDBAEntry
			MAX-ACCESS not-accessible
			STATUS current
			DESCRIPTION
				"Description."
			INDEX { sleEponOltIndex }
			::= { sleEponOltDBATable 1 }

		
		SleEponOltDBAEntry ::=
			SEQUENCE { 
				sleEponOltDBAGlobalOltLinkOperate
					INTEGER,
				sleEponOltDBAOverGrantMonConfMonitoringInterval
					INTEGER,
				sleEponOltDBAOverGrantMonConfMaxDBAGrantSize
					INTEGER,
				sleEponOltDBAOverGrantMonConfMinGrantUtilization
					INTEGER,
				sleEponOltDBAOverGrantMonConfLeakyBucketCounterValue
					INTEGER,
				sleEponOltDBAMinShaperBandwidth
					INTEGER,
				sleEponOltDBAMinShaperBurstSize
					INTEGER,
				sleEponOltDBAMinShaperScheduleLevel
					INTEGER,
				sleEponOltDBAMinShaperWeight
					INTEGER,
				sleEponOltDBAMaxShaperBandwidth
					INTEGER,
				sleEponOltDBAMaxShaperBurstSize
					INTEGER,
				sleEponOltDBAMaxShaperScheduleLevel
					INTEGER,
				sleEponOltDBAMaxShaperWeight
					INTEGER
			 }

		sleEponOltDBAGlobalOltLinkOperate OBJECT-TYPE
			SYNTAX INTEGER
				{
				disable(0),
				enable(1)
				}
			MAX-ACCESS read-only
			STATUS current
			DESCRIPTION
				"Global olt link options.
				enable
				disable"
			::= { sleEponOltDBAEntry 1 }

		
		sleEponOltDBAOverGrantMonConfMonitoringInterval OBJECT-TYPE
			SYNTAX INTEGER (50..65535)
			MAX-ACCESS read-only
			STATUS current
			DESCRIPTION
				"Monitoring Interval."
			::= { sleEponOltDBAEntry 2 }

		
		sleEponOltDBAOverGrantMonConfMaxDBAGrantSize OBJECT-TYPE
			SYNTAX INTEGER (0..65535)
			MAX-ACCESS read-only
			STATUS current
			DESCRIPTION
				"Maximum DBA grant size."
			::= { sleEponOltDBAEntry 3 }

		
		sleEponOltDBAOverGrantMonConfMinGrantUtilization OBJECT-TYPE
			SYNTAX INTEGER (0..255)
			MAX-ACCESS read-only
			STATUS current
			DESCRIPTION
				"Minimum grant utilization."
			::= { sleEponOltDBAEntry 4 }

		
		sleEponOltDBAOverGrantMonConfLeakyBucketCounterValue OBJECT-TYPE
			SYNTAX INTEGER (0..255)
			MAX-ACCESS read-only
			STATUS current
			DESCRIPTION
				"Leaky bucket counter value."
			::= { sleEponOltDBAEntry 5 }

		
		sleEponOltDBAMinShaperBandwidth OBJECT-TYPE
			SYNTAX INTEGER (256..1000000)
			MAX-ACCESS read-only
			STATUS current
			DESCRIPTION
				"min shaper bandwidth"
			::= { sleEponOltDBAEntry 6 }

		
		sleEponOltDBAMinShaperBurstSize OBJECT-TYPE
			SYNTAX INTEGER (1..256)
			MAX-ACCESS read-only
			STATUS current
			DESCRIPTION
				"min shaper burst size"
			::= { sleEponOltDBAEntry 7 }

		
		sleEponOltDBAMinShaperScheduleLevel OBJECT-TYPE
			SYNTAX INTEGER (0..7)
			MAX-ACCESS read-only
			STATUS current
			DESCRIPTION
				"min shaper schedule level"
			::= { sleEponOltDBAEntry 8 }

		
		sleEponOltDBAMinShaperWeight OBJECT-TYPE
			SYNTAX INTEGER (2..32)
			MAX-ACCESS read-only
			STATUS current
			DESCRIPTION
				"Min shaper weight"
			::= { sleEponOltDBAEntry 9 }

		
		sleEponOltDBAMaxShaperBandwidth OBJECT-TYPE
			SYNTAX INTEGER (256..1000000)
			MAX-ACCESS read-only
			STATUS current
			DESCRIPTION
				"max shaper bandwidth"
			::= { sleEponOltDBAEntry 10 }

		
		sleEponOltDBAMaxShaperBurstSize OBJECT-TYPE
			SYNTAX INTEGER (1..256)
			MAX-ACCESS read-only
			STATUS current
			DESCRIPTION
				"max shaper burst size"
			::= { sleEponOltDBAEntry 11 }

		
		sleEponOltDBAMaxShaperScheduleLevel OBJECT-TYPE
			SYNTAX INTEGER (0..7)
			MAX-ACCESS read-only
			STATUS current
			DESCRIPTION
				"max shaper schedule level"
			::= { sleEponOltDBAEntry 12 }

		
		sleEponOltDBAMaxShaperWeight OBJECT-TYPE
			SYNTAX INTEGER (2..32)
			MAX-ACCESS read-only
			STATUS current
			DESCRIPTION
				"max shaper weight"
			::= { sleEponOltDBAEntry 13 }

		
		sleEponOltDBAPollingRateTable OBJECT-TYPE
			SYNTAX SEQUENCE OF SleEponOltDBAPollingRateEntry
			MAX-ACCESS not-accessible
			STATUS current
			DESCRIPTION
				"olt dba polling rate table"
			::= { sleEponOltDBA 2 }

		
		sleEponOltDBAPollingRateEntry OBJECT-TYPE
			SYNTAX SleEponOltDBAPollingRateEntry
			MAX-ACCESS not-accessible
			STATUS current
			DESCRIPTION
				"Description."
			INDEX { sleEponOltIndex, sleEponOltDBADBAPollingRateLevel }
			::= { sleEponOltDBAPollingRateTable 1 }

		
		SleEponOltDBAPollingRateEntry ::=
			SEQUENCE { 
				sleEponOltDBADBAPollingRateLevel
					INTEGER,
				sleEponOltDBADBAPollingRateRate
					INTEGER
			 }

		sleEponOltDBADBAPollingRateLevel OBJECT-TYPE
			SYNTAX INTEGER (0..7)
			MAX-ACCESS read-only
			STATUS current
			DESCRIPTION
				"Polling rate level."
			::= { sleEponOltDBAPollingRateEntry 1 }

		
		sleEponOltDBADBAPollingRateRate OBJECT-TYPE
			SYNTAX INTEGER (0..65535)
			MAX-ACCESS read-write
			STATUS current
			DESCRIPTION
				"Polling rate rate."
			::= { sleEponOltDBAPollingRateEntry 2 }

		
		sleEponOltDBADropDownTable OBJECT-TYPE
			SYNTAX SEQUENCE OF SleEponOltDBADropDownEntry
			MAX-ACCESS not-accessible
			STATUS current
			DESCRIPTION
				"shaper drop down and  drop down"
			::= { sleEponOltDBA 3 }

		
		sleEponOltDBADropDownEntry OBJECT-TYPE
			SYNTAX SleEponOltDBADropDownEntry
			MAX-ACCESS not-accessible
			STATUS current
			DESCRIPTION
				"Description."
			INDEX { sleEponOltIndex, eEponOltDBADropDownLevel }
			::= { sleEponOltDBADropDownTable 1 }

		
		SleEponOltDBADropDownEntry ::=
			SEQUENCE { 
				eEponOltDBADropDownLevel
					INTEGER,
				sleEponOltDBAShaDropDownWeights
					INTEGER,
				sleEponOltDBADropDownWeights
					Integer32
			 }

		eEponOltDBADropDownLevel OBJECT-TYPE
			SYNTAX INTEGER (1..7)
			MAX-ACCESS read-only
			STATUS current
			DESCRIPTION
				"the level of shaper drop down and drop down weights "
			::= { sleEponOltDBADropDownEntry 1 }

		
		sleEponOltDBAShaDropDownWeights OBJECT-TYPE
			SYNTAX INTEGER (0..256)
			MAX-ACCESS read-write
			STATUS current
			DESCRIPTION
				"Shaper drop down weights."
			::= { sleEponOltDBADropDownEntry 2 }

		
		sleEponOltDBADropDownWeights OBJECT-TYPE
			SYNTAX Integer32
			MAX-ACCESS read-write
			STATUS current
			DESCRIPTION
				"Drop down weights."
			::= { sleEponOltDBADropDownEntry 3 }

		
		sleEponOltDBAControl OBJECT IDENTIFIER ::= { sleEponOltDBA 4 }

		
		sleEponOltDBAControlRequest OBJECT-TYPE
			SYNTAX INTEGER
				{
				setDBAPollingRate(1),
				setDBAShaperDropDownWeights(2),
				setDBADropDownWeights(3),
				setDBALinkEnable(4),
				setDBALinkDisable(5),
				setDBAGlobalOltLinkOptions(6),
				setDBALinkGrantMonConf(7),
				setDBAMultiQueueSla(8),
				noDBAMultiQueueSla(9)
				}
			MAX-ACCESS read-write
			STATUS current
			DESCRIPTION
				"The request of a user command."
			::= { sleEponOltDBAControl 1 }

		
		sleEponOltDBAControlStatus OBJECT-TYPE
			SYNTAX SleControlStatusType
			MAX-ACCESS read-only
			STATUS current
			DESCRIPTION
				"The status of user command."
			::= { sleEponOltDBAControl 2 }

		
		sleEponOltDBAControlTimer OBJECT-TYPE
			SYNTAX Gauge32
			MAX-ACCESS read-write
			STATUS current
			DESCRIPTION
				"The maximum time for the manager for a long running user command."
			::= { sleEponOltDBAControl 3 }

		
		sleEponOltDBAControlTimeStamp OBJECT-TYPE
			SYNTAX TimeTicks
			MAX-ACCESS read-only
			STATUS current
			DESCRIPTION
				"The time stamp of the last command(end of command)."
			::= { sleEponOltDBAControl 4 }

		
		sleEponOltDBAControlReqResult OBJECT-TYPE
			SYNTAX SleControlRequestResultType
			MAX-ACCESS read-only
			STATUS current
			DESCRIPTION
				"The result of the last user command."
			::= { sleEponOltDBAControl 5 }

		
		sleEponOltDBAControlOltIndex OBJECT-TYPE
			SYNTAX INTEGER (1..32)
			MAX-ACCESS read-write
			STATUS current
			DESCRIPTION
				"Olt index."
			::= { sleEponOltDBAControl 6 }

		
		sleEponOltDBAControlOnuIndex OBJECT-TYPE
			SYNTAX INTEGER (1..64)
			MAX-ACCESS read-write
			STATUS current
			DESCRIPTION
				"Onu index."
			::= { sleEponOltDBAControl 7 }

		
		sleEponOltDBAControlDBAPollingRateLevel OBJECT-TYPE
			SYNTAX INTEGER (0..7)
			MAX-ACCESS read-write
			STATUS current
			DESCRIPTION
				"Polling rate level."
			::= { sleEponOltDBAControl 8 }

		
		sleEponOltDBAControlDBAPollingRateRate OBJECT-TYPE
			SYNTAX INTEGER (0..65535)
			MAX-ACCESS read-write
			STATUS current
			DESCRIPTION
				"Polling rate."
			::= { sleEponOltDBAControl 9 }

		
		sleEponOltDBAControlShaDropDownWeightsLevel OBJECT-TYPE
			SYNTAX INTEGER (1..7)
			MAX-ACCESS read-write
			STATUS current
			DESCRIPTION
				"Shaper dropdown weights level."
			::= { sleEponOltDBAControl 10 }

		
		sleEponOltDBAControlShaDropDownWeights OBJECT-TYPE
			SYNTAX INTEGER (0..256)
			MAX-ACCESS read-write
			STATUS current
			DESCRIPTION
				"Shaper drop down weights."
			::= { sleEponOltDBAControl 11 }

		
		sleEponOltDBAControlDropDownWeightsLevel OBJECT-TYPE
			SYNTAX INTEGER (1..7)
			MAX-ACCESS read-write
			STATUS current
			DESCRIPTION
				"Drop down weights level."
			::= { sleEponOltDBAControl 12 }

		
		sleEponOltDBAControlDropDownWeightsl OBJECT-TYPE
			SYNTAX INTEGER (0..256)
			MAX-ACCESS read-write
			STATUS current
			DESCRIPTION
				"Drop down weights."
			::= { sleEponOltDBAControl 13 }

		
		sleEponOltDBAControlGlobalOltLinkOperate OBJECT-TYPE
			SYNTAX INTEGER
				{
				disable(0),
				enable(1)
				}
			MAX-ACCESS read-write
			STATUS current
			DESCRIPTION
				"Global olt link options.
				enable
				disable"
			::= { sleEponOltDBAControl 14 }

		
		sleEponOltDBAControlOverGrantMonConfMonitoringInterval OBJECT-TYPE
			SYNTAX INTEGER (50..65535)
			MAX-ACCESS read-write
			STATUS current
			DESCRIPTION
				"Monitoring Interval."
			::= { sleEponOltDBAControl 15 }

		
		sleEponOltDBAControlOverGrantMonConfMaxDBAGrantSize OBJECT-TYPE
			SYNTAX INTEGER (0..65535)
			MAX-ACCESS read-write
			STATUS current
			DESCRIPTION
				"Maximum DBA grant size."
			::= { sleEponOltDBAControl 16 }

		
		sleEponOltDBAControlOverGrantMonConfMinGrantUtilization OBJECT-TYPE
			SYNTAX INTEGER (0..255)
			MAX-ACCESS read-write
			STATUS current
			DESCRIPTION
				"Minimum grant utilization."
			::= { sleEponOltDBAControl 17 }

		
		sleEponOltDBAControlOverGrantMonConfLeakyBucketCounterValue OBJECT-TYPE
			SYNTAX INTEGER (0..255)
			MAX-ACCESS read-write
			STATUS current
			DESCRIPTION
				"Leaky bucket counter value."
			::= { sleEponOltDBAControl 18 }

		
		sleEponOltDBAControlMinShaperBandwidth OBJECT-TYPE
			SYNTAX INTEGER (256..1000000)
			MAX-ACCESS read-write
			STATUS current
			DESCRIPTION
				"min shaper bandwidth"
			::= { sleEponOltDBAControl 19 }

		
		sleEponOltDBAControlMinShaperBurstSize OBJECT-TYPE
			SYNTAX INTEGER (1..256)
			MAX-ACCESS read-write
			STATUS current
			DESCRIPTION
				"min shaper burst size"
			::= { sleEponOltDBAControl 20 }

		
		sleEponOltDBAControlMinShaperScheduleLevel OBJECT-TYPE
			SYNTAX INTEGER (0..7)
			MAX-ACCESS read-write
			STATUS current
			DESCRIPTION
				"min shaper schedule level"
			::= { sleEponOltDBAControl 21 }

		
		sleEponOltDBAControlMinShaperWeight OBJECT-TYPE
			SYNTAX INTEGER (2..32)
			MAX-ACCESS read-write
			STATUS current
			DESCRIPTION
				"min shaper weight"
			::= { sleEponOltDBAControl 22 }

		
		sleEponOltDBAControlMaxShaperBandwidth OBJECT-TYPE
			SYNTAX INTEGER (256..1000000)
			MAX-ACCESS read-write
			STATUS current
			DESCRIPTION
				"max shaper bandwidth"
			::= { sleEponOltDBAControl 23 }

		
		sleEponOltDBAControlMaxShaperBurstSize OBJECT-TYPE
			SYNTAX INTEGER (1..256)
			MAX-ACCESS read-write
			STATUS current
			DESCRIPTION
				"max shaper burst size"
			::= { sleEponOltDBAControl 24 }

		
		sleEponOltDBAControlMaxShaperScheduleLevel OBJECT-TYPE
			SYNTAX INTEGER (0..7)
			MAX-ACCESS read-write
			STATUS current
			DESCRIPTION
				"max shaper schedule level"
			::= { sleEponOltDBAControl 25 }

		
		sleEponOltDBAControlMaxShaperWeight OBJECT-TYPE
			SYNTAX INTEGER (2..32)
			MAX-ACCESS read-write
			STATUS current
			DESCRIPTION
				"max shaper weight"
			::= { sleEponOltDBAControl 26 }

		
		selEponOltDBAControlDirection OBJECT-TYPE
			SYNTAX Integer32
			MAX-ACCESS read-write
			STATUS current
			DESCRIPTION
				"Description."
			::= { sleEponOltDBAControl 27 }

		
		sleEponOltDBANotification OBJECT IDENTIFIER ::= { sleEponOltDBA 5 }

		
		sleEponOLtDBAShaperDropDownWeightsChanged NOTIFICATION-TYPE
			OBJECTS { sleEponOltDBAControlRequest, sleEponOltDBAControlTimeStamp, sleEponOltDBAControlReqResult, sleEponOltDBAControlShaDropDownWeightsLevel, sleEponOltDBAControlShaDropDownWeights
				 }
			STATUS current
			DESCRIPTION 
				"Shaper drop down weights changed."
			::= { sleEponOltDBANotification 1 }

		
		sleEponOLtDBADropDownWeightsChanged NOTIFICATION-TYPE
			OBJECTS { sleEponOltDBAControlRequest, sleEponOltDBAControlTimeStamp, sleEponOltDBAControlReqResult, sleEponOltDBAControlDropDownWeightsLevel, sleEponOltDBAControlDropDownWeightsl
				 }
			STATUS current
			DESCRIPTION 
				"DBA drop down weights changed."
			::= { sleEponOltDBANotification 2 }

		
		sleEponOltDBALinkChanged NOTIFICATION-TYPE
			OBJECTS { sleEponOltDBAControlRequest, sleEponOltDBAControlTimeStamp, sleEponOltDBAControlReqResult }
			STATUS current
			DESCRIPTION 
				"DBA link state changed."
			::= { sleEponOltDBANotification 3 }

		
		sleEponOLtDBADGlobalOltLinkChanged NOTIFICATION-TYPE
			OBJECTS { sleEponOltDBAControlRequest, sleEponOltDBAControlTimeStamp, sleEponOltDBAControlReqResult, sleEponOltDBAControlGlobalOltLinkOperate }
			STATUS current
			DESCRIPTION 
				"Global olt link state changed trap."
			::= { sleEponOltDBANotification 4 }

		
		sleEponOLtDBADOverGrantMonConfChanged NOTIFICATION-TYPE
			OBJECTS { sleEponOltDBAControlRequest, sleEponOltDBAControlTimeStamp, sleEponOltDBAControlReqResult, sleEponOltDBAControlOverGrantMonConfMonitoringInterval, sleEponOltDBAControlOverGrantMonConfMaxDBAGrantSize, 
				sleEponOltDBAControlOverGrantMonConfMinGrantUtilization, sleEponOltDBAControlOverGrantMonConfLeakyBucketCounterValue }
			STATUS current
			DESCRIPTION 
				"Olt DBA over-grant-mon-conf changed trap."
			::= { sleEponOltDBANotification 5 }

		
		sleEponOltDBAPollingRateChanged NOTIFICATION-TYPE
			OBJECTS { sleEponOltDBAControlRequest, sleEponOltDBAControlTimeStamp, sleEponOltDBAControlReqResult, sleEponOltDBAControlDBAPollingRateLevel, sleEponOltDBAControlDBAPollingRateRate
				 }
			STATUS current
			DESCRIPTION 
				"Polling rate changed trap."
			::= { sleEponOltDBANotification 6 }

		
		sleEponOltDBAMultiQueueSlaChanged NOTIFICATION-TYPE
			OBJECTS { sleEponOltDBAControlRequest, sleEponOltDBAControlTimeStamp, sleEponOltDBAControlReqResult, sleEponOltDBAControlOltIndex }
			STATUS current
			DESCRIPTION 
				"multicast queue sla changed trap"
			::= { sleEponOltDBANotification 7 }

		
		sleEponOnuProfileDBA OBJECT IDENTIFIER ::= { sleEponDBA 2 }

		
		sleEponOnuProfileDBALinkTable OBJECT-TYPE
			SYNTAX SEQUENCE OF SleEponOnuProfileDBALinkEntry
			MAX-ACCESS not-accessible
			STATUS current
			DESCRIPTION
				"Epon onu profile DBA link entry."
			::= { sleEponOnuProfileDBA 1 }

		
		sleEponOnuProfileDBALinkEntry OBJECT-TYPE
			SYNTAX SleEponOnuProfileDBALinkEntry
			MAX-ACCESS not-accessible
			STATUS current
			DESCRIPTION
				"Description."
			INDEX { sleEponProfileIndex }
			::= { sleEponOnuProfileDBALinkTable 1 }

		
		SleEponOnuProfileDBALinkEntry ::=
			SEQUENCE { 
				sleEponOnuProfileDBAProfileName
					OCTET STRING,
				sleEponOnuProfileDBALinkSlaMinShaBandwidth
					INTEGER,
				sleEponOnuProfileDBALinkSlaMinShaBurstSize
					INTEGER,
				sleEponOnuProfileDBALinkSlaMinShaSchedulerLevel
					INTEGER,
				sleEponOnuProfileDBALinkSlaMinShaWeight
					INTEGER,
				sleEponOnuProfileDBALinkSlaMaxShaBandwidth
					INTEGER,
				sleEponOnuProfileDBALinkSlaMaxShaBurstSize
					INTEGER,
				sleEponOnuProfileDBALinkSlaMaxShaSchedulerLevel
					INTEGER,
				sleEponOnuProfileDBALinkSlaMaxShaWeight
					INTEGER,
				sleEponOnuProfileDBALinkSlaOperate
					INTEGER,
				sleEponOnuProfileDBALinkSlaPollingLevel
					INTEGER,
				sleEponOnuProfileDBALinkSlaTDMRate
					INTEGER,
				sleEponOnuProfileDBALinkSlaTDMGrantLength
					INTEGER,
				sleEponOnuProfileDBALinkOAMMaxOAMRate
					INTEGER,
				sleEponOnuProfileDBALinkOAMMinOAMRate
					INTEGER
			 }

		sleEponOnuProfileDBAProfileName OBJECT-TYPE
			SYNTAX OCTET STRING (SIZE (1..64))
			MAX-ACCESS read-only
			STATUS current
			DESCRIPTION
				"Profile name.
				'all' means configure all the onu profile."
			::= { sleEponOnuProfileDBALinkEntry 1 }

		
		sleEponOnuProfileDBALinkSlaMinShaBandwidth OBJECT-TYPE
			SYNTAX INTEGER (0 | 256..1000000)
			MAX-ACCESS read-only
			STATUS current
			DESCRIPTION
				"Guaranteed Bandwidth(Kbps).
				System default: 0
				"
			DEFVAL { 0 }
			::= { sleEponOnuProfileDBALinkEntry 2 }

		
		sleEponOnuProfileDBALinkSlaMinShaBurstSize OBJECT-TYPE
			SYNTAX INTEGER (1..256 | 65535)
			MAX-ACCESS read-only
			STATUS current
			DESCRIPTION
				"Minimum Burst Size.
				System default: 65535"
			DEFVAL { 65535 }
			::= { sleEponOnuProfileDBALinkEntry 3 }

		
		sleEponOnuProfileDBALinkSlaMinShaSchedulerLevel OBJECT-TYPE
			SYNTAX INTEGER (0..7 | 255)
			MAX-ACCESS read-only
			STATUS current
			DESCRIPTION
				"Scheduler Level.
				System default 255."
			DEFVAL { 255 }
			::= { sleEponOnuProfileDBALinkEntry 4 }

		
		sleEponOnuProfileDBALinkSlaMinShaWeight OBJECT-TYPE
			SYNTAX INTEGER (2..32 | 65535)
			MAX-ACCESS read-only
			STATUS current
			DESCRIPTION
				"Weight
				System default: 65535."
			DEFVAL { 65535 }
			::= { sleEponOnuProfileDBALinkEntry 5 }

		
		sleEponOnuProfileDBALinkSlaMaxShaBandwidth OBJECT-TYPE
			SYNTAX INTEGER (0 | 256..1000000)
			MAX-ACCESS read-only
			STATUS current
			DESCRIPTION
				"Guaranteed Bandwidth(Kbps).
				System default: 100000"
			DEFVAL { 100000 }
			::= { sleEponOnuProfileDBALinkEntry 6 }

		
		sleEponOnuProfileDBALinkSlaMaxShaBurstSize OBJECT-TYPE
			SYNTAX INTEGER (1..256)
			MAX-ACCESS read-only
			STATUS current
			DESCRIPTION
				"Maximum Burst Size.
				System default: 255"
			DEFVAL { 255 }
			::= { sleEponOnuProfileDBALinkEntry 7 }

		
		sleEponOnuProfileDBALinkSlaMaxShaSchedulerLevel OBJECT-TYPE
			SYNTAX INTEGER (0..7)
			MAX-ACCESS read-only
			STATUS current
			DESCRIPTION
				"Scheduler Level.
				System default 2."
			DEFVAL { 2 }
			::= { sleEponOnuProfileDBALinkEntry 8 }

		
		sleEponOnuProfileDBALinkSlaMaxShaWeight OBJECT-TYPE
			SYNTAX INTEGER (2..32)
			MAX-ACCESS read-only
			STATUS current
			DESCRIPTION
				"Weight
				System default: 24."
			DEFVAL { 24 }
			::= { sleEponOnuProfileDBALinkEntry 9 }

		
		sleEponOnuProfileDBALinkSlaOperate OBJECT-TYPE
			SYNTAX INTEGER
				{
				none(1),
				forceReport(2),
				disableOamUplift(3)
				}
			MAX-ACCESS read-only
			STATUS current
			DESCRIPTION
				"Onu profile DBA options."
			::= { sleEponOnuProfileDBALinkEntry 10 }

		
		sleEponOnuProfileDBALinkSlaPollingLevel OBJECT-TYPE
			SYNTAX INTEGER (0..7)
			MAX-ACCESS read-only
			STATUS current
			DESCRIPTION
				"Polling Interval Select."
			::= { sleEponOnuProfileDBALinkEntry 11 }

		
		sleEponOnuProfileDBALinkSlaTDMRate OBJECT-TYPE
			SYNTAX INTEGER (0 | 1..4000)
			MAX-ACCESS read-only
			STATUS current
			DESCRIPTION
				"TDM Rate.
				System default 0."
			DEFVAL { 0 }
			::= { sleEponOnuProfileDBALinkEntry 12 }

		
		sleEponOnuProfileDBALinkSlaTDMGrantLength OBJECT-TYPE
			SYNTAX INTEGER (0 | 84..131072)
			MAX-ACCESS read-only
			STATUS current
			DESCRIPTION
				"TDM grant length.
				System default 0."
			DEFVAL { 0 }
			::= { sleEponOnuProfileDBALinkEntry 13 }

		
		sleEponOnuProfileDBALinkOAMMaxOAMRate OBJECT-TYPE
			SYNTAX INTEGER (0..25)
			MAX-ACCESS read-only
			STATUS current
			DESCRIPTION
				"Maximum OAM rate.
				System default 3."
			DEFVAL { 3 }
			::= { sleEponOnuProfileDBALinkEntry 14 }

		
		sleEponOnuProfileDBALinkOAMMinOAMRate OBJECT-TYPE
			SYNTAX INTEGER (0..10)
			MAX-ACCESS read-only
			STATUS current
			DESCRIPTION
				"Minimum OAM rate.
				System default 10."
			DEFVAL { 10 }
			::= { sleEponOnuProfileDBALinkEntry 15 }

		
		sleEponOnuProfileDBAQueueSlaTable OBJECT-TYPE
			SYNTAX SEQUENCE OF SleEponOnuProfileDBAQueueSlaEntry
			MAX-ACCESS not-accessible
			STATUS current
			DESCRIPTION
				"Description."
			::= { sleEponOnuProfileDBA 2 }

		
		sleEponOnuProfileDBAQueueSlaEntry OBJECT-TYPE
			SYNTAX SleEponOnuProfileDBAQueueSlaEntry
			MAX-ACCESS not-accessible
			STATUS current
			DESCRIPTION
				"Epon onu profile DBA queue sla entry."
			INDEX { sleEponProfileIndex, sleEponOnuProfileDBAQueueIndex }
			::= { sleEponOnuProfileDBAQueueSlaTable 1 }

		
		SleEponOnuProfileDBAQueueSlaEntry ::=
			SEQUENCE { 
				sleEponOnuProfileDBAQueueIndex
					INTEGER,
				sleEponOnuProfileDBAQueueSlaDownMinShaBandwidth
					INTEGER,
				sleEponOnuProfileDBAQueueSlaDownMinShaBurstSize
					INTEGER,
				sleEponOnuProfileDBAQueueSlaDownMinShaSchedulerLevel
					INTEGER,
				sleEponOnuProfileDBAQueueSlaDownMinShaWeight
					INTEGER,
				sleEponOnuProfileDBAQueueSlaDownMaxShaBandwidth
					INTEGER,
				sleEponOnuProfileDBAQueueSlaDownMaxShaBurstSize
					INTEGER,
				sleEponOnuProfileDBAQueueSlaDownMaxShaSchedulerLevel
					INTEGER,
				sleEponOnuProfileDBAQueueSlaDownMaxShaWeight
					INTEGER,
				sleEponOnuProfileDBAQueueSlaUpMinShaBandwidth
					INTEGER,
				sleEponOnuProfileDBAQueueSlaUpMinShaBurstSize
					INTEGER,
				sleEponOnuProfileDBAQueueSlaUpMinShaSchedulerLevel
					INTEGER,
				sleEponOnuProfileDBAQueueSlaUpMinShaWeight
					INTEGER,
				sleEponOnuProfileDBAQueueSlaUpMaxShaBandwidth
					INTEGER,
				sleEponOnuProfileDBAQueueSlaUpMaxShaBurstSize
					INTEGER,
				sleEponOnuProfileDBAQueueSlaUpMaxShaSchedulerLevel
					INTEGER,
				sleEponOnuProfileDBAQueueSlaUpMaxShaWeight
					INTEGER
			 }

		sleEponOnuProfileDBAQueueIndex OBJECT-TYPE
			SYNTAX INTEGER (0..3)
			MAX-ACCESS read-only
			STATUS current
			DESCRIPTION
				"Queue index."
			::= { sleEponOnuProfileDBAQueueSlaEntry 1 }

		
		sleEponOnuProfileDBAQueueSlaDownMinShaBandwidth OBJECT-TYPE
			SYNTAX INTEGER (0 | 256..1000000)
			MAX-ACCESS read-only
			STATUS current
			DESCRIPTION
				"Queue sla downstream shaper minimum bandwidth.
				System default 0."
			DEFVAL { 0 }
			::= { sleEponOnuProfileDBAQueueSlaEntry 2 }

		
		sleEponOnuProfileDBAQueueSlaDownMinShaBurstSize OBJECT-TYPE
			SYNTAX INTEGER (1..256 | 65535)
			MAX-ACCESS read-only
			STATUS current
			DESCRIPTION
				"Queue sla downstream shaper minimum burst size.
				System default 65535."
			DEFVAL { 65535 }
			::= { sleEponOnuProfileDBAQueueSlaEntry 3 }

		
		sleEponOnuProfileDBAQueueSlaDownMinShaSchedulerLevel OBJECT-TYPE
			SYNTAX INTEGER (0..7 | 255)
			MAX-ACCESS read-only
			STATUS current
			DESCRIPTION
				"Queue sla downstream shaper minimum scheduer level.
				System default 255."
			DEFVAL { 255 }
			::= { sleEponOnuProfileDBAQueueSlaEntry 4 }

		
		sleEponOnuProfileDBAQueueSlaDownMinShaWeight OBJECT-TYPE
			SYNTAX INTEGER (2..32 | 65535)
			MAX-ACCESS read-only
			STATUS current
			DESCRIPTION
				"Queue sla downstream shaper minimum weight.
				System default 65535."
			DEFVAL { 65535 }
			::= { sleEponOnuProfileDBAQueueSlaEntry 5 }

		
		sleEponOnuProfileDBAQueueSlaDownMaxShaBandwidth OBJECT-TYPE
			SYNTAX INTEGER (256..1000000)
			MAX-ACCESS read-only
			STATUS current
			DESCRIPTION
				"Queue sla downstream shaper maximum bandwidth.
				System default 100000"
			DEFVAL { 100000 }
			::= { sleEponOnuProfileDBAQueueSlaEntry 6 }

		
		sleEponOnuProfileDBAQueueSlaDownMaxShaBurstSize OBJECT-TYPE
			SYNTAX INTEGER (1..256)
			MAX-ACCESS read-only
			STATUS current
			DESCRIPTION
				"Queue sla downstream shaper maximum burst size.
				System default 255."
			DEFVAL { 255 }
			::= { sleEponOnuProfileDBAQueueSlaEntry 7 }

		
		sleEponOnuProfileDBAQueueSlaDownMaxShaSchedulerLevel OBJECT-TYPE
			SYNTAX INTEGER (0..7)
			MAX-ACCESS read-only
			STATUS current
			DESCRIPTION
				"Queue sla downstream shaper maximum scheduler level.
				System default 2."
			DEFVAL { 2 }
			::= { sleEponOnuProfileDBAQueueSlaEntry 8 }

		
		sleEponOnuProfileDBAQueueSlaDownMaxShaWeight OBJECT-TYPE
			SYNTAX INTEGER (2..32)
			MAX-ACCESS read-only
			STATUS current
			DESCRIPTION
				"Queue sla downstream shaper maximum weight.
				System default 24."
			DEFVAL { 24 }
			::= { sleEponOnuProfileDBAQueueSlaEntry 9 }

		
		sleEponOnuProfileDBAQueueSlaUpMinShaBandwidth OBJECT-TYPE
			SYNTAX INTEGER (0 | 256..1000000)
			MAX-ACCESS read-only
			STATUS current
			DESCRIPTION
				"Queue sla upstream shaper minimum bandwidth.
				System default 0."
			DEFVAL { 0 }
			::= { sleEponOnuProfileDBAQueueSlaEntry 10 }

		
		sleEponOnuProfileDBAQueueSlaUpMinShaBurstSize OBJECT-TYPE
			SYNTAX INTEGER (1..256 | 65535)
			MAX-ACCESS read-only
			STATUS current
			DESCRIPTION
				"Queue sla upstream shaper minimum bandwidth.
				System default 65535."
			DEFVAL { 65535 }
			::= { sleEponOnuProfileDBAQueueSlaEntry 11 }

		
		sleEponOnuProfileDBAQueueSlaUpMinShaSchedulerLevel OBJECT-TYPE
			SYNTAX INTEGER (0..7 | 255)
			MAX-ACCESS read-write
			STATUS current
			DESCRIPTION
				"Queue sla upstream shaper minimum scheduler level.
				System default 255."
			DEFVAL { 255 }
			::= { sleEponOnuProfileDBAQueueSlaEntry 12 }

		
		sleEponOnuProfileDBAQueueSlaUpMinShaWeight OBJECT-TYPE
			SYNTAX INTEGER (2..32 | 65535)
			MAX-ACCESS read-only
			STATUS current
			DESCRIPTION
				"Queue sla upstream shaper minimum weight.
				System default 65535."
			DEFVAL { 65535 }
			::= { sleEponOnuProfileDBAQueueSlaEntry 13 }

		
		sleEponOnuProfileDBAQueueSlaUpMaxShaBandwidth OBJECT-TYPE
			SYNTAX INTEGER (256..1000000)
			MAX-ACCESS read-write
			STATUS current
			DESCRIPTION
				"Queue sla upstream shaper maximum bandwidth.
				System default 100000."
			DEFVAL { 100000 }
			::= { sleEponOnuProfileDBAQueueSlaEntry 14 }

		
		sleEponOnuProfileDBAQueueSlaUpMaxShaBurstSize OBJECT-TYPE
			SYNTAX INTEGER (1..256)
			MAX-ACCESS read-only
			STATUS current
			DESCRIPTION
				"Queue sla upstream shaper maximum burst size.
				System default 255."
			DEFVAL { 255 }
			::= { sleEponOnuProfileDBAQueueSlaEntry 15 }

		
		sleEponOnuProfileDBAQueueSlaUpMaxShaSchedulerLevel OBJECT-TYPE
			SYNTAX INTEGER (0..7)
			MAX-ACCESS read-write
			STATUS current
			DESCRIPTION
				"Queue sla upstream shaper maximum scheduler level.
				System default 2."
			DEFVAL { 2 }
			::= { sleEponOnuProfileDBAQueueSlaEntry 16 }

		
		sleEponOnuProfileDBAQueueSlaUpMaxShaWeight OBJECT-TYPE
			SYNTAX INTEGER (2..32)
			MAX-ACCESS read-only
			STATUS current
			DESCRIPTION
				"Queue sla upstream shaper maximum weight.
				System default 24."
			DEFVAL { 24 }
			::= { sleEponOnuProfileDBAQueueSlaEntry 17 }

		
		sleEponOnuProfileDBAControl OBJECT IDENTIFIER ::= { sleEponOnuProfileDBA 3 }

		
		sleEponOnuProfileDBAControlRequest OBJECT-TYPE
			SYNTAX INTEGER
				{
				setPonOnuProfileDBALinkSla(1),
				noPonOnuProfileDBALinkSla(2),
				setPonOnuProfileDBAQueueSla(3),
				noPonOnuProfileDBAQueueSla(4),
				noPonOnuProfileDBAQueueSlaAll(5),
				setPonOnuProfileDBALinkOAMRate(6),
				noPonOnuProfileDBALinkOAMRate(7),
				setPonOnuProfileDBAPollingInterval(8),
				createPonOnuProfileDBA(9),
				setPonOnuProfileDBA(10),
				noPonOnuProfileDBA(11)
				}
			MAX-ACCESS read-write
			STATUS current
			DESCRIPTION
				"The request of a user command."
			::= { sleEponOnuProfileDBAControl 1 }

		
		sleEponOnuProfileDBAControlStatus OBJECT-TYPE
			SYNTAX SleControlStatusType
			MAX-ACCESS read-write
			STATUS current
			DESCRIPTION
				"The status of user command."
			::= { sleEponOnuProfileDBAControl 2 }

		
		sleEponOnuProfileDBAControlTimer OBJECT-TYPE
			SYNTAX Gauge32
			MAX-ACCESS read-write
			STATUS current
			DESCRIPTION
				"The maximum time for the manager for a long running user command."
			::= { sleEponOnuProfileDBAControl 3 }

		
		sleEponOnuProfileDBAControlTimeStamp OBJECT-TYPE
			SYNTAX TimeTicks
			MAX-ACCESS read-write
			STATUS current
			DESCRIPTION
				"The time stamp of the last command(end of command)."
			::= { sleEponOnuProfileDBAControl 4 }

		
		sleEponOnuProfileDBAControlReqResult OBJECT-TYPE
			SYNTAX SleControlRequestResultType
			MAX-ACCESS read-write
			STATUS current
			DESCRIPTION
				"The result of the last user command."
			::= { sleEponOnuProfileDBAControl 5 }

		
		sleEponOnuProfileDBAControlProfileName OBJECT-TYPE
			SYNTAX OCTET STRING (SIZE (1..64))
			MAX-ACCESS read-write
			STATUS current
			DESCRIPTION
				"Profile name.
				'all' means configure all the onu profile."
			::= { sleEponOnuProfileDBAControl 6 }

		
		sleEponOnuProfileDBAControlLinkSlaMinShaBandwidth OBJECT-TYPE
			SYNTAX INTEGER (0 | 256..1000000)
			MAX-ACCESS read-write
			STATUS current
			DESCRIPTION
				"Guaranteed Bandwidth(Kbps).
				0 means that we will use the default value."
			DEFVAL { 0 }
			::= { sleEponOnuProfileDBAControl 7 }

		
		sleEponOnuProfileDBAControlLinkSlaMinShaBurstSize OBJECT-TYPE
			SYNTAX INTEGER (1..256 | 65535)
			MAX-ACCESS read-write
			STATUS current
			DESCRIPTION
				"Minimum Burst Size.
				Default 65535."
			DEFVAL { 65535 }
			::= { sleEponOnuProfileDBAControl 8 }

		
		sleEponOnuProfileDBAControlLinkSlaMinShaSchedulerLevel OBJECT-TYPE
			SYNTAX INTEGER (0..7 | 255)
			MAX-ACCESS read-write
			STATUS current
			DESCRIPTION
				"Scheduler Level.
				Default 255."
			DEFVAL { 255 }
			::= { sleEponOnuProfileDBAControl 9 }

		
		sleEponOnuProfileDBAControlLinkSlaMinShaWeight OBJECT-TYPE
			SYNTAX INTEGER (2..32 | 65535)
			MAX-ACCESS read-write
			STATUS current
			DESCRIPTION
				"Weight.
				Default 65535."
			DEFVAL { 0 }
			::= { sleEponOnuProfileDBAControl 10 }

		
		sleEponOnuProfileDBAControlLinkSlaMaxShaBandwidth OBJECT-TYPE
			SYNTAX INTEGER (256..1000000)
			MAX-ACCESS read-write
			STATUS current
			DESCRIPTION
				"Guaranteed Bandwidth(Kbps)."
			::= { sleEponOnuProfileDBAControl 11 }

		
		sleEponOnuProfileDBAControlLinkSlaMaxShaBurstSize OBJECT-TYPE
			SYNTAX INTEGER (1..256)
			MAX-ACCESS read-write
			STATUS current
			DESCRIPTION
				"Maximum burst size."
			::= { sleEponOnuProfileDBAControl 12 }

		
		sleEponOnuProfileDBAControlLinkSlaMaxShaSchedulerLevel OBJECT-TYPE
			SYNTAX INTEGER (0..7)
			MAX-ACCESS read-write
			STATUS current
			DESCRIPTION
				"Scheduler Level."
			::= { sleEponOnuProfileDBAControl 13 }

		
		sleEponOnuProfileDBAControlLinkSlaMaxShaWeight OBJECT-TYPE
			SYNTAX INTEGER (2..32)
			MAX-ACCESS read-write
			STATUS current
			DESCRIPTION
				"Weight."
			::= { sleEponOnuProfileDBAControl 14 }

		
		sleEponOnuProfileDBAControlLinkSlaOperate OBJECT-TYPE
			SYNTAX INTEGER
				{
				none(1),
				forceReport(2),
				disableOAMUplift(3)
				}
			MAX-ACCESS read-write
			STATUS current
			DESCRIPTION
				"Onu profile DBA options."
			::= { sleEponOnuProfileDBAControl 15 }

		
		sleEponOnuProfileDBAControlLinkSlaPollingLevel OBJECT-TYPE
			SYNTAX INTEGER (0..7)
			MAX-ACCESS read-write
			STATUS current
			DESCRIPTION
				"Polling Interval Select."
			::= { sleEponOnuProfileDBAControl 16 }

		
		sleEponOnuProfileDBAControlLinkSlaTDMRate OBJECT-TYPE
			SYNTAX INTEGER (0 | 1..4000)
			MAX-ACCESS read-write
			STATUS current
			DESCRIPTION
				"TDM Rate.
				0 means that we will use the default value."
			DEFVAL { 0 }
			::= { sleEponOnuProfileDBAControl 17 }

		
		sleEponOnuProfileDBAControlLinkSlaTDMGrantLength OBJECT-TYPE
			SYNTAX INTEGER (0 | 84..131072)
			MAX-ACCESS read-write
			STATUS current
			DESCRIPTION
				"TDM grant length.
				0 means that we will use the default value."
			DEFVAL { 0 }
			::= { sleEponOnuProfileDBAControl 18 }

		
		sleEponOnuProfileDBAControlQueueIndex OBJECT-TYPE
			SYNTAX INTEGER (0..3)
			MAX-ACCESS read-write
			STATUS current
			DESCRIPTION
				"Queue index."
			::= { sleEponOnuProfileDBAControl 19 }

		
		sleEponOnuProfileDBAControlQueueSlaMinShaBandwidth OBJECT-TYPE
			SYNTAX INTEGER (256..1000000)
			MAX-ACCESS read-write
			STATUS current
			DESCRIPTION
				"Guaranteed Bandwidth(Kbps)."
			::= { sleEponOnuProfileDBAControl 20 }

		
		sleEponOnuProfileDBAControlQueueSlaMinShaBurstSize OBJECT-TYPE
			SYNTAX INTEGER (1..256)
			MAX-ACCESS read-write
			STATUS current
			DESCRIPTION
				"Minimum Burst Size."
			::= { sleEponOnuProfileDBAControl 21 }

		
		sleEponOnuProfileDBAControlQueueSlaMinShaSchedulerLevel OBJECT-TYPE
			SYNTAX INTEGER (0..7)
			MAX-ACCESS read-write
			STATUS current
			DESCRIPTION
				"Scheduler Level."
			::= { sleEponOnuProfileDBAControl 22 }

		
		sleEponOnuProfileDBAControlQueueSlaMinShaWeight OBJECT-TYPE
			SYNTAX INTEGER (2..32)
			MAX-ACCESS read-write
			STATUS current
			DESCRIPTION
				"Weight."
			::= { sleEponOnuProfileDBAControl 23 }

		
		sleEponOnuProfileDBAControlQueueSlaMaxShaBandwidth OBJECT-TYPE
			SYNTAX INTEGER (256..1000000)
			MAX-ACCESS read-write
			STATUS current
			DESCRIPTION
				"Guaranteed Bandwidth(Kbps)."
			::= { sleEponOnuProfileDBAControl 24 }

		
		sleEponOnuProfileDBAControlQueueSlaMaxShaBurstSize OBJECT-TYPE
			SYNTAX INTEGER (1..256)
			MAX-ACCESS read-write
			STATUS current
			DESCRIPTION
				"Maximum burst size."
			::= { sleEponOnuProfileDBAControl 25 }

		
		sleEponOnuProfileDBAControlQueueSlaMaxShaSchedulerLevel OBJECT-TYPE
			SYNTAX INTEGER (0..7)
			MAX-ACCESS read-write
			STATUS current
			DESCRIPTION
				"Scheduler Level."
			::= { sleEponOnuProfileDBAControl 26 }

		
		sleEponOnuProfileDBAControlQueueSlaMaxShaWeight OBJECT-TYPE
			SYNTAX INTEGER (2..32)
			MAX-ACCESS read-write
			STATUS current
			DESCRIPTION
				"Weight."
			::= { sleEponOnuProfileDBAControl 27 }

		
		sleEponOnuProfileDBAControlQueueSlaOperate OBJECT-TYPE
			SYNTAX INTEGER
				{
				upstream(1),
				downstream(2)
				}
			MAX-ACCESS read-write
			STATUS current
			DESCRIPTION
				"Direction of Egress Shaping."
			::= { sleEponOnuProfileDBAControl 28 }

		
		sleEponOnuProfileDBAControlLinkOAMMaxRate OBJECT-TYPE
			SYNTAX INTEGER (0..25)
			MAX-ACCESS read-write
			STATUS current
			DESCRIPTION
				"Maximum OAM rate."
			::= { sleEponOnuProfileDBAControl 29 }

		
		sleEponOnuProfileDBAControlLinkOAMMinRate OBJECT-TYPE
			SYNTAX INTEGER (0..10)
			MAX-ACCESS read-write
			STATUS current
			DESCRIPTION
				"Minimum OAM rate."
			::= { sleEponOnuProfileDBAControl 30 }

		
		sleEponOnuProfileDBAControlReport OBJECT-TYPE
			SYNTAX INTEGER
			MAX-ACCESS read-write
			STATUS current
			DESCRIPTION
				"Description."
			::= { sleEponOnuProfileDBAControl 31 }

		
		sleEponOnuProfileDBAControlDirection OBJECT-TYPE
			SYNTAX INTEGER
			MAX-ACCESS read-write
			STATUS current
			DESCRIPTION
				"Description."
			::= { sleEponOnuProfileDBAControl 32 }

		
		sleEponOnuProfileDBAControlIngressEgress OBJECT-TYPE
			SYNTAX INTEGER
			MAX-ACCESS read-write
			STATUS current
			DESCRIPTION
				"Description."
			::= { sleEponOnuProfileDBAControl 33 }

		
		sleEponOnuProfileDBANotification OBJECT IDENTIFIER ::= { sleEponOnuProfileDBA 4 }

		
		sleEponOnuProfileDBALinkSlaChanged NOTIFICATION-TYPE
			OBJECTS { sleEponOnuProfileDBAControlRequest, sleEponOnuProfileDBAControlTimeStamp, sleEponOnuProfileDBAControlReqResult, sleEponOnuProfileDBAControlProfileName }
			STATUS current
			DESCRIPTION 
				"Set ONU profile DBA link sla trap."
			::= { sleEponOnuProfileDBANotification 1 }

		
		sleEponOnuProfileDBAQueueSlaChanged NOTIFICATION-TYPE
			OBJECTS { sleEponOnuProfileDBAControlRequest, sleEponOnuProfileDBAControlTimeStamp, sleEponOnuProfileDBAControlReqResult, sleEponOnuProfileDBAControlProfileName, sleEponOnuProfileDBAControlQueueIndex
				 }
			STATUS current
			DESCRIPTION 
				"Onu profile DBA queue sla changed trap."
			::= { sleEponOnuProfileDBANotification 2 }

		
		sleEponOnuProfileDBALinkOAMRateChanged NOTIFICATION-TYPE
			OBJECTS { sleEponOnuProfileDBAControlRequest, sleEponOnuProfileDBAControlTimeStamp, sleEponOnuProfileDBAControlReqResult, sleEponOnuProfileDBAControlProfileName, sleEponOnuProfileDBAControlLinkOAMMaxRate, 
				sleEponOnuProfileDBAControlLinkOAMMinRate }
			STATUS current
			DESCRIPTION 
				"Onu profile DBA link OAM changed trap."
			::= { sleEponOnuProfileDBANotification 3 }

		
		sleEponOnuProfileDBAMutilLLidLinkTable OBJECT-TYPE
			SYNTAX SEQUENCE OF SleEponOnuProfileDBAMutilLLidLinkEntry
			MAX-ACCESS not-accessible
			STATUS current
			DESCRIPTION
				"Epon onu profile DBA link entry."
			::= { sleEponOnuProfileDBA 5 }

		
		sleEponOnuProfileDBAMutilLLidLinkEntry OBJECT-TYPE
			SYNTAX SleEponOnuProfileDBAMutilLLidLinkEntry
			MAX-ACCESS not-accessible
			STATUS current
			DESCRIPTION
				"Description."
			INDEX { sleEponProfileIndex }
			::= { sleEponOnuProfileDBAMutilLLidLinkTable 1 }

		
		SleEponOnuProfileDBAMutilLLidLinkEntry ::=
			SEQUENCE { 
				sleEponOnuProfileDBAMultiLLidProfileName
					OCTET STRING,
				sleEponOnuProfileDBAMultiLLidLinkSlaMinShaBandwidth
					INTEGER,
				sleEponOnuProfileDBAMultiLLidLinkSlaMinShaBurstSize
					INTEGER,
				sleEponOnuProfileDBAMultiLLidLinkSlaMinShaSchedulerLevel
					INTEGER,
				sleEponOnuProfileDBAMultiLLidLinkSlaMinShaWeight
					INTEGER,
				sleEponOnuProfileDBAMultiLLidLinkSlaMaxShaBandwidth
					INTEGER,
				sleEponOnuProfileDBAMultiLLidLinkSlaMaxShaBurstSize
					INTEGER,
				sleEponOnuProfileDBAMultiLLidLinkSlaMaxShaSchedulerLevel
					INTEGER,
				sleEponOnuProfileDBAMultiLLidLinkSlaMaxShaWeight
					INTEGER,
				sleEponOnuProfileDBAMultiLLidLinkSlaOperate
					INTEGER,
				sleEponOnuProfileDBAMultiLLidLinkSlaPollingLevel
					INTEGER,
				sleEponOnuProfileDBAMultiLLidLinkSlaTDMRate
					INTEGER,
				sleEponOnuProfileDBAMultiLLidLinkSlaTDMGrantLength
					INTEGER,
				sleEponOnuProfileDBAMultiLLidLinkOAMMaxOAMRate
					INTEGER,
				sleEponOnuProfileDBAMultiLLidLinkOAMMinOAMRate
					INTEGER
			 }

		sleEponOnuProfileDBAMultiLLidProfileName OBJECT-TYPE
			SYNTAX OCTET STRING (SIZE (1..64))
			MAX-ACCESS read-only
			STATUS current
			DESCRIPTION
				"Profile name.
				'all' means configure all the onu profile."
			::= { sleEponOnuProfileDBAMutilLLidLinkEntry 1 }

		
		sleEponOnuProfileDBAMultiLLidLinkSlaMinShaBandwidth OBJECT-TYPE
			SYNTAX INTEGER (0 | 256..1000000)
			MAX-ACCESS read-only
			STATUS current
			DESCRIPTION
				"Guaranteed Bandwidth(Kbps).
				System default: 0
				"
			DEFVAL { 0 }
			::= { sleEponOnuProfileDBAMutilLLidLinkEntry 2 }

		
		sleEponOnuProfileDBAMultiLLidLinkSlaMinShaBurstSize OBJECT-TYPE
			SYNTAX INTEGER (1..256 | 65535)
			MAX-ACCESS read-only
			STATUS current
			DESCRIPTION
				"Minimum Burst Size.
				System default: 65535"
			DEFVAL { 65535 }
			::= { sleEponOnuProfileDBAMutilLLidLinkEntry 3 }

		
		sleEponOnuProfileDBAMultiLLidLinkSlaMinShaSchedulerLevel OBJECT-TYPE
			SYNTAX INTEGER (0..7 | 255)
			MAX-ACCESS read-only
			STATUS current
			DESCRIPTION
				"Scheduler Level.
				System default 255."
			DEFVAL { 255 }
			::= { sleEponOnuProfileDBAMutilLLidLinkEntry 4 }

		
		sleEponOnuProfileDBAMultiLLidLinkSlaMinShaWeight OBJECT-TYPE
			SYNTAX INTEGER (2..32 | 65535)
			MAX-ACCESS read-only
			STATUS current
			DESCRIPTION
				"Weight
				System default: 65535."
			DEFVAL { 65535 }
			::= { sleEponOnuProfileDBAMutilLLidLinkEntry 5 }

		
		sleEponOnuProfileDBAMultiLLidLinkSlaMaxShaBandwidth OBJECT-TYPE
			SYNTAX INTEGER (0 | 256..1000000)
			MAX-ACCESS read-only
			STATUS current
			DESCRIPTION
				"Guaranteed Bandwidth(Kbps).
				System default: 100000"
			DEFVAL { 100000 }
			::= { sleEponOnuProfileDBAMutilLLidLinkEntry 6 }

		
		sleEponOnuProfileDBAMultiLLidLinkSlaMaxShaBurstSize OBJECT-TYPE
			SYNTAX INTEGER (1..256)
			MAX-ACCESS read-only
			STATUS current
			DESCRIPTION
				"Maximum Burst Size.
				System default: 255"
			DEFVAL { 255 }
			::= { sleEponOnuProfileDBAMutilLLidLinkEntry 7 }

		
		sleEponOnuProfileDBAMultiLLidLinkSlaMaxShaSchedulerLevel OBJECT-TYPE
			SYNTAX INTEGER (0..7)
			MAX-ACCESS read-only
			STATUS current
			DESCRIPTION
				"Scheduler Level.
				System default 2."
			DEFVAL { 2 }
			::= { sleEponOnuProfileDBAMutilLLidLinkEntry 8 }

		
		sleEponOnuProfileDBAMultiLLidLinkSlaMaxShaWeight OBJECT-TYPE
			SYNTAX INTEGER (2..32)
			MAX-ACCESS read-only
			STATUS current
			DESCRIPTION
				"Weight
				System default: 24."
			DEFVAL { 24 }
			::= { sleEponOnuProfileDBAMutilLLidLinkEntry 9 }

		
		sleEponOnuProfileDBAMultiLLidLinkSlaOperate OBJECT-TYPE
			SYNTAX INTEGER
				{
				none(1),
				forceReport(2),
				disableOamUplift(3)
				}
			MAX-ACCESS read-only
			STATUS current
			DESCRIPTION
				"Onu profile DBA options."
			::= { sleEponOnuProfileDBAMutilLLidLinkEntry 10 }

		
		sleEponOnuProfileDBAMultiLLidLinkSlaPollingLevel OBJECT-TYPE
			SYNTAX INTEGER (0..7)
			MAX-ACCESS read-only
			STATUS current
			DESCRIPTION
				"Polling Interval Select."
			::= { sleEponOnuProfileDBAMutilLLidLinkEntry 11 }

		
		sleEponOnuProfileDBAMultiLLidLinkSlaTDMRate OBJECT-TYPE
			SYNTAX INTEGER (0 | 1..4000)
			MAX-ACCESS read-only
			STATUS current
			DESCRIPTION
				"TDM Rate.
				System default 0."
			DEFVAL { 0 }
			::= { sleEponOnuProfileDBAMutilLLidLinkEntry 12 }

		
		sleEponOnuProfileDBAMultiLLidLinkSlaTDMGrantLength OBJECT-TYPE
			SYNTAX INTEGER (0 | 84..131072)
			MAX-ACCESS read-only
			STATUS current
			DESCRIPTION
				"TDM grant length.
				System default 0."
			DEFVAL { 0 }
			::= { sleEponOnuProfileDBAMutilLLidLinkEntry 13 }

		
		sleEponOnuProfileDBAMultiLLidLinkOAMMaxOAMRate OBJECT-TYPE
			SYNTAX INTEGER (0..25)
			MAX-ACCESS read-only
			STATUS current
			DESCRIPTION
				"Maximum OAM rate.
				System default 3."
			DEFVAL { 3 }
			::= { sleEponOnuProfileDBAMutilLLidLinkEntry 14 }

		
		sleEponOnuProfileDBAMultiLLidLinkOAMMinOAMRate OBJECT-TYPE
			SYNTAX INTEGER (0..10)
			MAX-ACCESS read-only
			STATUS current
			DESCRIPTION
				"Minimum OAM rate.
				System default 10."
			DEFVAL { 10 }
			::= { sleEponOnuProfileDBAMutilLLidLinkEntry 15 }

		
		sleEponOnuProfileDBAMultiLLidQueueSlaTable OBJECT-TYPE
			SYNTAX SEQUENCE OF SleEponOnuProfileDBAMultiLLidQueueSlaEntry
			MAX-ACCESS not-accessible
			STATUS current
			DESCRIPTION
				"Description."
			::= { sleEponOnuProfileDBA 6 }

		
		sleEponOnuProfileDBAMultiLLidQueueSlaEntry OBJECT-TYPE
			SYNTAX SleEponOnuProfileDBAMultiLLidQueueSlaEntry
			MAX-ACCESS not-accessible
			STATUS current
			DESCRIPTION
				"Epon onu profile DBA queue sla entry."
			INDEX { sleEponProfileIndex, sleEponOnuProfileDBAQueueIndex }
			::= { sleEponOnuProfileDBAMultiLLidQueueSlaTable 1 }

		
		SleEponOnuProfileDBAMultiLLidQueueSlaEntry ::=
			SEQUENCE { 
				sleEponOnuProfileDBAMultiLLidQueueIndex
					INTEGER,
				sleEponOnuProfileDBAMultiLLidQueueSlaDownMinShaBandwidth
					INTEGER,
				sleEponOnuProfileDBAMultiLLidQueueSlaDownMinShaBurstSize
					INTEGER,
				sleEponOnuProfileDBAMultiLLidQueueSlaDownMinShaSchedulerLevel
					INTEGER,
				sleEponOnuProfileDBAMultiLLidQueueSlaDownMinShaWeight
					INTEGER,
				sleEponOnuProfileDBAMutiLLidQueueSlaDownMaxShaBandwidth
					INTEGER,
				sleEponOnuProfileDBAMultiLLidQueueSlaDownMaxShaBurstSize
					INTEGER,
				sleEponOnuProfileDBAMultiLLidQueueSlaDownMaxShaSchedulerLevel
					INTEGER,
				sleEponOnuProfileDBAMultiLLidQueueSlaDownMaxShaWeight
					INTEGER,
				sleEponOnuProfileDBAMultiLLidQueueSlaUpMinShaBandwidth
					INTEGER,
				sleEponOnuProfileDBAMultiLLidQueueSlaUpMinShaBurstSize
					INTEGER,
				sleEponOnuProfileDBAMultiLLidQueueSlaUpMinShaSchedulerLevel
					INTEGER,
				sleEponOnuProfileDBAMultiLLidQueueSlaUpMinShaWeight
					INTEGER,
				sleEponOnuProfileDBAMultiLLidQueueSlaUpMaxShaBandwidth
					INTEGER,
				sleEponOnuProfileDBAMultiLLidQueueSlaUpMaxShaBurstSize
					INTEGER,
				sleEponOnuProfileDBAMultiLLidQueueSlaUpMaxShaSchedulerLevel
					INTEGER,
				sleEponOnuProfileDBAMultiLLidQueueSlaUpMaxShaWeight
					INTEGER
			 }

		sleEponOnuProfileDBAMultiLLidQueueIndex OBJECT-TYPE
			SYNTAX INTEGER (0..3)
			MAX-ACCESS read-only
			STATUS current
			DESCRIPTION
				"Queue index."
			::= { sleEponOnuProfileDBAMultiLLidQueueSlaEntry 1 }

		
		sleEponOnuProfileDBAMultiLLidQueueSlaDownMinShaBandwidth OBJECT-TYPE
			SYNTAX INTEGER (0 | 256..1000000)
			MAX-ACCESS read-only
			STATUS current
			DESCRIPTION
				"Queue sla downstream shaper minimum bandwidth.
				System default 0."
			DEFVAL { 0 }
			::= { sleEponOnuProfileDBAMultiLLidQueueSlaEntry 2 }

		
		sleEponOnuProfileDBAMultiLLidQueueSlaDownMinShaBurstSize OBJECT-TYPE
			SYNTAX INTEGER (1..256 | 65535)
			MAX-ACCESS read-only
			STATUS current
			DESCRIPTION
				"Queue sla downstream shaper minimum burst size.
				System default 65535."
			DEFVAL { 65535 }
			::= { sleEponOnuProfileDBAMultiLLidQueueSlaEntry 3 }

		
		sleEponOnuProfileDBAMultiLLidQueueSlaDownMinShaSchedulerLevel OBJECT-TYPE
			SYNTAX INTEGER (0..7 | 255)
			MAX-ACCESS read-only
			STATUS current
			DESCRIPTION
				"Queue sla downstream shaper minimum scheduer level.
				System default 255."
			DEFVAL { 255 }
			::= { sleEponOnuProfileDBAMultiLLidQueueSlaEntry 4 }

		
		sleEponOnuProfileDBAMultiLLidQueueSlaDownMinShaWeight OBJECT-TYPE
			SYNTAX INTEGER (2..32 | 65535)
			MAX-ACCESS read-only
			STATUS current
			DESCRIPTION
				"Queue sla downstream shaper minimum weight.
				System default 65535."
			DEFVAL { 65535 }
			::= { sleEponOnuProfileDBAMultiLLidQueueSlaEntry 5 }

		
		sleEponOnuProfileDBAMutiLLidQueueSlaDownMaxShaBandwidth OBJECT-TYPE
			SYNTAX INTEGER (256..1000000)
			MAX-ACCESS read-only
			STATUS current
			DESCRIPTION
				"Queue sla downstream shaper maximum bandwidth.
				System default 100000"
			DEFVAL { 100000 }
			::= { sleEponOnuProfileDBAMultiLLidQueueSlaEntry 6 }

		
		sleEponOnuProfileDBAMultiLLidQueueSlaDownMaxShaBurstSize OBJECT-TYPE
			SYNTAX INTEGER (1..256)
			MAX-ACCESS read-only
			STATUS current
			DESCRIPTION
				"Queue sla downstream shaper maximum burst size.
				System default 255."
			DEFVAL { 255 }
			::= { sleEponOnuProfileDBAMultiLLidQueueSlaEntry 7 }

		
		sleEponOnuProfileDBAMultiLLidQueueSlaDownMaxShaSchedulerLevel OBJECT-TYPE
			SYNTAX INTEGER (0..7)
			MAX-ACCESS read-only
			STATUS current
			DESCRIPTION
				"Queue sla downstream shaper maximum scheduler level.
				System default 2."
			DEFVAL { 2 }
			::= { sleEponOnuProfileDBAMultiLLidQueueSlaEntry 8 }

		
		sleEponOnuProfileDBAMultiLLidQueueSlaDownMaxShaWeight OBJECT-TYPE
			SYNTAX INTEGER (2..32)
			MAX-ACCESS read-only
			STATUS current
			DESCRIPTION
				"Queue sla downstream shaper maximum weight.
				System default 24."
			DEFVAL { 24 }
			::= { sleEponOnuProfileDBAMultiLLidQueueSlaEntry 9 }

		
		sleEponOnuProfileDBAMultiLLidQueueSlaUpMinShaBandwidth OBJECT-TYPE
			SYNTAX INTEGER (0 | 256..1000000)
			MAX-ACCESS read-only
			STATUS current
			DESCRIPTION
				"Queue sla upstream shaper minimum bandwidth.
				System default 0."
			DEFVAL { 0 }
			::= { sleEponOnuProfileDBAMultiLLidQueueSlaEntry 10 }

		
		sleEponOnuProfileDBAMultiLLidQueueSlaUpMinShaBurstSize OBJECT-TYPE
			SYNTAX INTEGER (1..256 | 65535)
			MAX-ACCESS read-only
			STATUS current
			DESCRIPTION
				"Queue sla upstream shaper minimum bandwidth.
				System default 65535."
			DEFVAL { 65535 }
			::= { sleEponOnuProfileDBAMultiLLidQueueSlaEntry 11 }

		
		sleEponOnuProfileDBAMultiLLidQueueSlaUpMinShaSchedulerLevel OBJECT-TYPE
			SYNTAX INTEGER (0..7 | 255)
			MAX-ACCESS read-write
			STATUS current
			DESCRIPTION
				"Queue sla upstream shaper minimum scheduler level.
				System default 255."
			DEFVAL { 255 }
			::= { sleEponOnuProfileDBAMultiLLidQueueSlaEntry 12 }

		
		sleEponOnuProfileDBAMultiLLidQueueSlaUpMinShaWeight OBJECT-TYPE
			SYNTAX INTEGER (2..32 | 65535)
			MAX-ACCESS read-only
			STATUS current
			DESCRIPTION
				"Queue sla upstream shaper minimum weight.
				System default 65535."
			DEFVAL { 65535 }
			::= { sleEponOnuProfileDBAMultiLLidQueueSlaEntry 13 }

		
		sleEponOnuProfileDBAMultiLLidQueueSlaUpMaxShaBandwidth OBJECT-TYPE
			SYNTAX INTEGER (256..1000000)
			MAX-ACCESS read-write
			STATUS current
			DESCRIPTION
				"Queue sla upstream shaper maximum bandwidth.
				System default 100000."
			DEFVAL { 100000 }
			::= { sleEponOnuProfileDBAMultiLLidQueueSlaEntry 14 }

		
		sleEponOnuProfileDBAMultiLLidQueueSlaUpMaxShaBurstSize OBJECT-TYPE
			SYNTAX INTEGER (1..256)
			MAX-ACCESS read-only
			STATUS current
			DESCRIPTION
				"Queue sla upstream shaper maximum burst size.
				System default 255."
			DEFVAL { 255 }
			::= { sleEponOnuProfileDBAMultiLLidQueueSlaEntry 15 }

		
		sleEponOnuProfileDBAMultiLLidQueueSlaUpMaxShaSchedulerLevel OBJECT-TYPE
			SYNTAX INTEGER (0..7)
			MAX-ACCESS read-write
			STATUS current
			DESCRIPTION
				"Queue sla upstream shaper maximum scheduler level.
				System default 2."
			DEFVAL { 2 }
			::= { sleEponOnuProfileDBAMultiLLidQueueSlaEntry 16 }

		
		sleEponOnuProfileDBAMultiLLidQueueSlaUpMaxShaWeight OBJECT-TYPE
			SYNTAX INTEGER (2..32)
			MAX-ACCESS read-only
			STATUS current
			DESCRIPTION
				"Queue sla upstream shaper maximum weight.
				System default 24."
			DEFVAL { 24 }
			::= { sleEponOnuProfileDBAMultiLLidQueueSlaEntry 17 }

		
		sleEponOnuProfileDBAMultiLLidControl OBJECT IDENTIFIER ::= { sleEponOnuProfileDBA 7 }

		
		sleEponOnuProfileDBAMultiLLidControlRequest OBJECT-TYPE
			SYNTAX INTEGER
				{
				setPonOnuProfileDBAMultillidLinkSla(1),
				noPonOnuProfileDBAMultillidLinkSla(2),
				setPonOnuProfileDBAMultillidQueueSla(3),
				noPonOnuProfileDBAMultillidQueueSla(4),
				noPonOnuProfileDBAMultillidQueueSlaAll(5),
				setPonOnuProfileDBAMultillidLinkOAMRate(6),
				noPonOnuProfileDBAMultillidLinkOAMRate(7)
				}
			MAX-ACCESS read-write
			STATUS current
			DESCRIPTION
				"The request of a user command."
			::= { sleEponOnuProfileDBAMultiLLidControl 1 }

		
		sleEponOnuProfileDBAMultiLLidControlStatus OBJECT-TYPE
			SYNTAX SleControlStatusType
			MAX-ACCESS read-write
			STATUS current
			DESCRIPTION
				"The status of user command."
			::= { sleEponOnuProfileDBAMultiLLidControl 2 }

		
		sleEponOnuProfileDBAMultiLLidControlTimer OBJECT-TYPE
			SYNTAX Gauge32
			MAX-ACCESS read-write
			STATUS current
			DESCRIPTION
				"The maximum time for the manager for a long running user command."
			::= { sleEponOnuProfileDBAMultiLLidControl 3 }

		
		sleEponOnuProfileDBAMultiLLidControlTimeStamp OBJECT-TYPE
			SYNTAX TimeTicks
			MAX-ACCESS read-write
			STATUS current
			DESCRIPTION
				"The time stamp of the last command(end of command)."
			::= { sleEponOnuProfileDBAMultiLLidControl 4 }

		
		sleEponOnuProfileDBAMultiLLidControlReqResult OBJECT-TYPE
			SYNTAX SleControlRequestResultType
			MAX-ACCESS read-write
			STATUS current
			DESCRIPTION
				"The result of the last user command."
			::= { sleEponOnuProfileDBAMultiLLidControl 5 }

		
		sleEponOnuProfileDBAMultiLLidControlProfileName OBJECT-TYPE
			SYNTAX OCTET STRING (SIZE (1..64))
			MAX-ACCESS read-write
			STATUS current
			DESCRIPTION
				"Profile name.
				'all' means configure all the onu profile."
			::= { sleEponOnuProfileDBAMultiLLidControl 6 }

		
		sleEponOnuProfileDBAMultiLLidControlLinkSlaMinShaBandwidth OBJECT-TYPE
			SYNTAX INTEGER (0 | 256..1000000)
			MAX-ACCESS read-write
			STATUS current
			DESCRIPTION
				"Guaranteed Bandwidth(Kbps).
				0 means that we will use the default value."
			DEFVAL { 0 }
			::= { sleEponOnuProfileDBAMultiLLidControl 7 }

		
		sleEponOnuProfileDBAMultiLLidControlLinkSlaMinShaBurstSize OBJECT-TYPE
			SYNTAX INTEGER (1..256 | 65535)
			MAX-ACCESS read-write
			STATUS current
			DESCRIPTION
				"Minimum Burst Size.
				Default 65535."
			DEFVAL { 65535 }
			::= { sleEponOnuProfileDBAMultiLLidControl 8 }

		
		sleEponOnuProfileDBAMultiLLidControlLinkSlaMinShaSchedulerLevel OBJECT-TYPE
			SYNTAX INTEGER (0..7 | 255)
			MAX-ACCESS read-write
			STATUS current
			DESCRIPTION
				"Scheduler Level.
				Default 255."
			DEFVAL { 255 }
			::= { sleEponOnuProfileDBAMultiLLidControl 9 }

		
		sleEponOnuProfileDBAMultiLLidControlLinkSlaMinShaWeight OBJECT-TYPE
			SYNTAX INTEGER (2..32 | 65535)
			MAX-ACCESS read-write
			STATUS current
			DESCRIPTION
				"Weight.
				Default 65535."
			DEFVAL { 0 }
			::= { sleEponOnuProfileDBAMultiLLidControl 10 }

		
		sleEponOnuProfileDBAMultiLLidControlLinkSlaMaxShaBandwidth OBJECT-TYPE
			SYNTAX INTEGER (256..1000000)
			MAX-ACCESS read-write
			STATUS current
			DESCRIPTION
				"Guaranteed Bandwidth(Kbps)."
			::= { sleEponOnuProfileDBAMultiLLidControl 11 }

		
		sleEponOnuProfileDBAMultiLLidControlLinkSlaMaxShaBurstSize OBJECT-TYPE
			SYNTAX INTEGER (1..256)
			MAX-ACCESS read-write
			STATUS current
			DESCRIPTION
				"Maximum burst size."
			::= { sleEponOnuProfileDBAMultiLLidControl 12 }

		
		sleEponOnuProfileDBAMultiLLidControlLinkSlaMaxShaSchedulerLevel OBJECT-TYPE
			SYNTAX INTEGER (0..7)
			MAX-ACCESS read-write
			STATUS current
			DESCRIPTION
				"Scheduler Level."
			::= { sleEponOnuProfileDBAMultiLLidControl 13 }

		
		sleEponOnuProfileDBAMultiLLidControlLinkSlaMaxShaWeight OBJECT-TYPE
			SYNTAX INTEGER (2..32)
			MAX-ACCESS read-write
			STATUS current
			DESCRIPTION
				"Weight."
			::= { sleEponOnuProfileDBAMultiLLidControl 14 }

		
		sleEponOnuProfileDBAMultiLLidControlLinkSlaOperate OBJECT-TYPE
			SYNTAX INTEGER
				{
				none(1),
				forceReport(2),
				disableOAMUplift(3)
				}
			MAX-ACCESS read-write
			STATUS current
			DESCRIPTION
				"Onu profile DBA options."
			::= { sleEponOnuProfileDBAMultiLLidControl 15 }

		
		sleEponOnuProfileDBAMultiLLIdControlLinkSlaPollingLevel OBJECT-TYPE
			SYNTAX INTEGER (0..7)
			MAX-ACCESS read-write
			STATUS current
			DESCRIPTION
				"Polling Interval Select."
			::= { sleEponOnuProfileDBAMultiLLidControl 16 }

		
		sleEponOnuProfileDBAlMultiLLidControLinkSlaTDMRate OBJECT-TYPE
			SYNTAX INTEGER (0 | 1..4000)
			MAX-ACCESS read-write
			STATUS current
			DESCRIPTION
				"TDM Rate.
				0 means that we will use the default value."
			DEFVAL { 0 }
			::= { sleEponOnuProfileDBAMultiLLidControl 17 }

		
		sleEponOnuProfileDBAMultiLLidControlLinkSlaTDMGrantLength OBJECT-TYPE
			SYNTAX INTEGER (0 | 84..131072)
			MAX-ACCESS read-write
			STATUS current
			DESCRIPTION
				"TDM grant length.
				0 means that we will use the default value."
			DEFVAL { 0 }
			::= { sleEponOnuProfileDBAMultiLLidControl 18 }

		
		sleEponOnuProfileDBAMultiLLidControlQueueIndex OBJECT-TYPE
			SYNTAX INTEGER (0..3)
			MAX-ACCESS read-write
			STATUS current
			DESCRIPTION
				"Queue index."
			::= { sleEponOnuProfileDBAMultiLLidControl 19 }

		
		sleEponOnuProfileDBAMultiLLidControlQueueSlaMinShaBandwidth OBJECT-TYPE
			SYNTAX INTEGER (256..1000000)
			MAX-ACCESS read-write
			STATUS current
			DESCRIPTION
				"Guaranteed Bandwidth(Kbps)."
			::= { sleEponOnuProfileDBAMultiLLidControl 20 }

		
		sleEponOnuProfileDBAMultiLLidControlQueueSlaMinShaBurstSize OBJECT-TYPE
			SYNTAX INTEGER (1..256)
			MAX-ACCESS read-write
			STATUS current
			DESCRIPTION
				"Minimum Burst Size."
			::= { sleEponOnuProfileDBAMultiLLidControl 21 }

		
		sleEponOnuProfileDBAMultiLLidControlQueueSlaMinShaSchedulerLevel OBJECT-TYPE
			SYNTAX INTEGER (0..7)
			MAX-ACCESS read-write
			STATUS current
			DESCRIPTION
				"Scheduler Level."
			::= { sleEponOnuProfileDBAMultiLLidControl 22 }

		
		sleEponOnuProfileDBAMultiLLidControlQueueSlaMinShaWeight OBJECT-TYPE
			SYNTAX INTEGER (2..32)
			MAX-ACCESS read-write
			STATUS current
			DESCRIPTION
				"Weight."
			::= { sleEponOnuProfileDBAMultiLLidControl 23 }

		
		sleEponOnuProfileDBAMultiLLidControlQueueSlaMaxShaBandwidth OBJECT-TYPE
			SYNTAX INTEGER (256..1000000)
			MAX-ACCESS read-write
			STATUS current
			DESCRIPTION
				"Guaranteed Bandwidth(Kbps)."
			::= { sleEponOnuProfileDBAMultiLLidControl 24 }

		
		sleEponOnuProfileDBAMultiLLidControlQueueSlaMaxShaBurstSize OBJECT-TYPE
			SYNTAX INTEGER (1..256)
			MAX-ACCESS read-write
			STATUS current
			DESCRIPTION
				"Maximum burst size."
			::= { sleEponOnuProfileDBAMultiLLidControl 25 }

		
		sleEponOnuProfileDBAMultiLLidControlQueueSlaMaxShaSchedulerLevel OBJECT-TYPE
			SYNTAX INTEGER (0..7)
			MAX-ACCESS read-write
			STATUS current
			DESCRIPTION
				"Scheduler Level."
			::= { sleEponOnuProfileDBAMultiLLidControl 26 }

		
		sleEponOnuProfileDBAMultiLLidControlQueueSlaMaxShaWeight OBJECT-TYPE
			SYNTAX INTEGER (2..32)
			MAX-ACCESS read-write
			STATUS current
			DESCRIPTION
				"Weight."
			::= { sleEponOnuProfileDBAMultiLLidControl 27 }

		
		sleEponOnuProfileDBAMultiLLIdControlQueueSlaOperate OBJECT-TYPE
			SYNTAX INTEGER
				{
				upstream(1),
				downstream(2)
				}
			MAX-ACCESS read-write
			STATUS current
			DESCRIPTION
				"Direction of Egress Shaping."
			::= { sleEponOnuProfileDBAMultiLLidControl 28 }

		
		sleEponOnuProfileDBAMultiLLidControlLinkOAMMaxRate OBJECT-TYPE
			SYNTAX INTEGER (0..25)
			MAX-ACCESS read-write
			STATUS current
			DESCRIPTION
				"Maximum OAM rate."
			::= { sleEponOnuProfileDBAMultiLLidControl 29 }

		
		sleEponOnuProfileDBAMultiLLidControlLinkOAMMinRate OBJECT-TYPE
			SYNTAX INTEGER (0..10)
			MAX-ACCESS read-write
			STATUS current
			DESCRIPTION
				"Minimum OAM rate."
			::= { sleEponOnuProfileDBAMultiLLidControl 30 }

		
		sleEponOnuProfileDBAMultiLLidNotification OBJECT IDENTIFIER ::= { sleEponOnuProfileDBA 8 }

		
		sleEponOnuProfileDBAMultiLLidLinkSlaChanged NOTIFICATION-TYPE
			OBJECTS { sleEponOnuProfileDBAMultiLLidControlRequest, sleEponOnuProfileDBAMultiLLidControlTimeStamp, sleEponOnuProfileDBAMultiLLidControlReqResult, sleEponOnuProfileDBAMultiLLidControlProfileName }
			STATUS current
			DESCRIPTION 
				"Set ONU profile DBA link sla trap."
			::= { sleEponOnuProfileDBAMultiLLidNotification 1 }

		
		sleEponOnuProfileDBAMultiLLidQueueSlaChanged NOTIFICATION-TYPE
			OBJECTS { sleEponOnuProfileDBAMultiLLidControlRequest, sleEponOnuProfileDBAMultiLLidControlTimeStamp, sleEponOnuProfileDBAMultiLLidControlReqResult, sleEponOnuProfileDBAMultiLLidControlProfileName, sleEponOnuProfileDBAMultiLLidControlQueueIndex
				 }
			STATUS current
			DESCRIPTION 
				"Onu profile DBA queue sla changed trap."
			::= { sleEponOnuProfileDBAMultiLLidNotification 2 }

		
		sleEponOnuProfileDBAMultiLLidLinkOAMRateChanged NOTIFICATION-TYPE
			OBJECTS { sleEponOnuProfileDBAMultiLLidControlRequest, sleEponOnuProfileDBAMultiLLidControlTimeStamp, sleEponOnuProfileDBAMultiLLidControlReqResult, sleEponOnuProfileDBAMultiLLidControlProfileName, sleEponOnuProfileDBAMultiLLidControlLinkOAMMaxRate, 
				sleEponOnuProfileDBAMultiLLidControlLinkOAMMinRate }
			STATUS current
			DESCRIPTION 
				"Onu profile DBA link OAM changed trap."
			::= { sleEponOnuProfileDBAMultiLLidNotification 3 }

		
		sleEponDomain OBJECT IDENTIFIER ::= { sleEpon 15 }

		
		sleEponDomainTable OBJECT-TYPE
			SYNTAX SEQUENCE OF SleEponDomainEntry
			MAX-ACCESS not-accessible
			STATUS current
			DESCRIPTION
				"Description."
			::= { sleEponDomain 1 }

		
		sleEponDomainEntry OBJECT-TYPE
			SYNTAX SleEponDomainEntry
			MAX-ACCESS not-accessible
			STATUS current
			DESCRIPTION
				"Description."
			INDEX { sleEponOltIndex, sleEponDomainVlanID }
			::= { sleEponDomainTable 1 }

		
		SleEponDomainEntry ::=
			SEQUENCE { 
				sleEponDomainVlanID
					INTEGER,
				sleEponDomainUnTaggedPorts
					OCTET STRING,
				sleEponDomainMultiUnTaggedPorts
					OCTET STRING
			 }

		sleEponDomainVlanID OBJECT-TYPE
			SYNTAX INTEGER (1..4094 | 4098)
			MAX-ACCESS read-only
			STATUS current
			DESCRIPTION
				"Pon olt/onu vlan index,4098 is the default vlanid."
			::= { sleEponDomainEntry 1 }

		
		sleEponDomainUnTaggedPorts OBJECT-TYPE
			SYNTAX OCTET STRING
			MAX-ACCESS read-only
			STATUS current
			DESCRIPTION
				"the port map of vlan ,'.' is not add in vlan,'u' is untagged port,'t' is tagged port.
				"
			::= { sleEponDomainEntry 2 }

		
		sleEponDomainMultiUnTaggedPorts OBJECT-TYPE
			SYNTAX OCTET STRING
			MAX-ACCESS read-only
			STATUS current
			DESCRIPTION
				"the port map of vlan ,'.' is not add in vlan,'u' is untagged port,'t' is tagged port.
				"
			::= { sleEponDomainEntry 3 }

		
		sleEponDomainControl OBJECT IDENTIFIER ::= { sleEponDomain 2 }

		
		sleEponDomainControlRequest OBJECT-TYPE
			SYNTAX INTEGER
				{
				setEponCreateVlan(1),
				setEponDestroyVlan(2),
				setEponVlanAdd(3),
				setEponDefaultVlanAdd(4),
				setEponVlanDel(5),
				setEponDefaultVlanDel(6),
				setEponVlanMultiAdd(7),
				setEponDefaultVlanMultiAdd(8),
				setEponVlanMultiDel(9),
				setEponDefaultVlanMultiDel(10)
				}
			MAX-ACCESS read-write
			STATUS current
			DESCRIPTION
				"The request of a user command."
			::= { sleEponDomainControl 1 }

		
		sleEponDomainControlStatus OBJECT-TYPE
			SYNTAX SleControlStatusType
			MAX-ACCESS read-only
			STATUS current
			DESCRIPTION
				"The status of user command."
			::= { sleEponDomainControl 2 }

		
		sleEponDomainControlTimer OBJECT-TYPE
			SYNTAX Gauge32
			MAX-ACCESS read-write
			STATUS current
			DESCRIPTION
				"The maximum time for the manager for a long running user command."
			::= { sleEponDomainControl 3 }

		
		sleEponDomainControlTimeStamp OBJECT-TYPE
			SYNTAX TimeTicks
			MAX-ACCESS read-only
			STATUS current
			DESCRIPTION
				"The time stamp of the last command(end of command)."
			::= { sleEponDomainControl 4 }

		
		sleEponDomainControlReqResult OBJECT-TYPE
			SYNTAX SleControlRequestResultType
			MAX-ACCESS read-only
			STATUS current
			DESCRIPTION
				"The result of the last user command."
			::= { sleEponDomainControl 5 }

		
		sleEponDomainControlOltIndex OBJECT-TYPE
			SYNTAX INTEGER (1..64)
			MAX-ACCESS read-write
			STATUS current
			DESCRIPTION
				"OLT index."
			::= { sleEponDomainControl 6 }

		
		sleEponDomainControlOnuIndex OBJECT-TYPE
			SYNTAX INTEGER (1..64)
			MAX-ACCESS read-write
			STATUS current
			DESCRIPTION
				"ONU index"
			::= { sleEponDomainControl 7 }

		
		sleEponDomainControlVlanID OBJECT-TYPE
			SYNTAX INTEGER (1..4096)
			MAX-ACCESS read-write
			STATUS current
			DESCRIPTION
				"OLT vlan index,default vlan ID 4098."
			::= { sleEponDomainControl 8 }

		
		sleEponDomainControlUnTaggedPorts OBJECT-TYPE
			SYNTAX INTEGER
				{
				tag(0),
				untag(1)
				}
			MAX-ACCESS read-write
			STATUS current
			DESCRIPTION
				"Portlist for members of this Vlan they will send only untagged frames.
				The octet string is a list of pairs of octets each identify
				an sleBridgePortIndex. The least significant byte is the second
				octet.
				"
			::= { sleEponDomainControl 9 }

		
		sleEponDomainNotification OBJECT IDENTIFIER ::= { sleEponDomain 3 }

		
		sleEponDomainVlanCreate NOTIFICATION-TYPE
			OBJECTS { sleEponDomainControlReqResult, sleEponDomainControlRequest, sleEponDomainControlTimeStamp, sleEponDomainControlVlanID }
			STATUS current
			DESCRIPTION 
				"Description."
			::= { sleEponDomainNotification 1 }

		
		sleEponDomainDestroyVlan NOTIFICATION-TYPE
			OBJECTS { sleEponDomainControlReqResult, sleEponDomainControlRequest, sleEponDomainControlTimeStamp, sleEponDomainControlVlanID }
			STATUS current
			DESCRIPTION 
				"Description."
			::= { sleEponDomainNotification 2 }

		
		sleEponDomainVlanAdd NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 3 }

		
		sleEponDomainDefaultVlanAdd NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 4 }

		
		sleEponDomainVlanDel NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 5 }

		
		sleEponDomainDefaultVlanDel NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 6 }

		
		sleEponDomainVlanMultiAdd NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 7 }

		
		sleEponDomainDefaultVlanMultiAdd NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 8 }

		
		sleEponDomainVlanMultiDel NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 9 }

		
		sleEponDomainDefaultVlanMultiDel NOTIFICATION-TYPE
			OBJECTS { sleEponDomainControlReqResult, sleEponDomainControlRequest, sleEponDomainControlTimeStamp, sleEponDomainControlOnuIndex, sleEponDomainControlVlanID
				 }
			STATUS current
			DESCRIPTION 
				"Description."
			::= { sleEponDomainNotification 10 }

		
		sleEponOltRedundancy OBJECT IDENTIFIER ::= { sleEpon 16 }

		
		sleEponOltRedundancyTable OBJECT-TYPE
			SYNTAX SEQUENCE OF SleEponOltRedundancyEntry
			MAX-ACCESS not-accessible
			STATUS current
			DESCRIPTION
				"Description."
			::= { sleEponOltRedundancy 1 }

		
		sleEponOltRedundancyEntry OBJECT-TYPE
			SYNTAX SleEponOltRedundancyEntry
			MAX-ACCESS not-accessible
			STATUS current
			DESCRIPTION
				"Description."
			INDEX { sleEponOltRedundancyMaster }
			::= { sleEponOltRedundancyTable 1 }

		
		SleEponOltRedundancyEntry ::=
			SEQUENCE { 
				sleEponOltRedundancyMaster
					Integer32,
				sleEponOltRedundancyGroupID
					INTEGER,
				sleEponOltRedundancyTrunkID
					Integer32,
				sleEponOltRedundancyMasteStatus
					INTEGER,
				sleEponOltRedundancySlave
					Integer32,
				sleEponOltRedundancySlaveStatus
					INTEGER,
				sleEponOltRedundancyWtrValue
					Integer32,
				sleEponOltRedundancyRemainTime
					Integer32,
				sleEponOltRedundancyLastReason
					INTEGER,
				sleEponOltRedundancyHoldOffTime
					Integer32,
				sleEponOltRedundancyMasterAdminStatus
					INTEGER,
				sleEponOltRedundancySlaveAdminStatus
					INTEGER,
				sleEponOltRedundancyStandbyRxSignal
					INTEGER,
				sleEponOltRedundancyTriggerLos
					INTEGER,
				sleEponOltRedundancyTriggerManual
					INTEGER,
				sleEponOltRedundancyTriggerSlot
					INTEGER,
				sleEponOltRedundancyTriggerEponMac
					INTEGER,
				sleEponOltRedundancyChagneStatus
					INTEGER
			 }

		sleEponOltRedundancyMaster OBJECT-TYPE
			SYNTAX Integer32 (1..24)
			MAX-ACCESS read-only
			STATUS current
			DESCRIPTION
				"Redundancy Master OLT_ID."
			::= { sleEponOltRedundancyEntry 1 }

		
		sleEponOltRedundancyGroupID OBJECT-TYPE
			SYNTAX INTEGER (1..4)
			MAX-ACCESS read-only
			STATUS current
			DESCRIPTION
				"Redundancy Group ID (1-4)."
			::= { sleEponOltRedundancyEntry 2 }

		
		sleEponOltRedundancyTrunkID OBJECT-TYPE
			SYNTAX Integer32 (0..13 | 255)
			MAX-ACCESS read-only
			STATUS current
			DESCRIPTION
				"Redundancy trunk ID 0-13,disable is 255."
			::= { sleEponOltRedundancyEntry 3 }

		
		sleEponOltRedundancyMasteStatus OBJECT-TYPE
			SYNTAX INTEGER
				{
				none(0),
				active(1),
				standby(2),
				pending(3),
				unknown(4),
				active_los(5),
				standby_los(6),
				workingStatus(10),
				standbyStatus(11),
				wPendingStatus(12),
				sPendingStatus(13),
				waitingStatus(14),
				unknownStatus(15)
				}
			MAX-ACCESS read-only
			STATUS current
			DESCRIPTION
				"Redundancy Master status."
			::= { sleEponOltRedundancyEntry 4 }

		
		sleEponOltRedundancySlave OBJECT-TYPE
			SYNTAX Integer32
			MAX-ACCESS read-only
			STATUS current
			DESCRIPTION
				"Redundancy Slave OLT_ID."
			::= { sleEponOltRedundancyEntry 5 }

		
		sleEponOltRedundancySlaveStatus OBJECT-TYPE
			SYNTAX INTEGER
				{
				none(0),
				active(1),
				standby(2),
				pending(3),
				unknown(4),
				active_los(5),
				standby_los(6),
				workingStatus(10),
				standbyStatus(11),
				wPendingStatus(12),
				sPendingStatus(13),
				waitingStatus(14),
				unknownStatus(15)
				}
			MAX-ACCESS read-only
			STATUS current
			DESCRIPTION
				"Redundancy Slave status."
			::= { sleEponOltRedundancyEntry 6 }

		
		sleEponOltRedundancyWtrValue OBJECT-TYPE
			SYNTAX Integer32 (1..60)
			MAX-ACCESS read-only
			STATUS current
			DESCRIPTION
				"WTR Value(Unit:min,1-60), -1 is invalid value."
			::= { sleEponOltRedundancyEntry 7 }

		
		sleEponOltRedundancyRemainTime OBJECT-TYPE
			SYNTAX Integer32
			MAX-ACCESS read-only
			STATUS current
			DESCRIPTION
				"Remain time Value(Unit:sec)"
			::= { sleEponOltRedundancyEntry 8 }

		
		sleEponOltRedundancyLastReason OBJECT-TYPE
			SYNTAX INTEGER
				{
				none(0),
				manualSwitch(1),
				losOfActive(2),
				slotRemoved(3),
				slotRestart(4),
				autoDetect(5),
				unknown(6),
				noneStatus(10),
				manualSwitchOverStatus(11),
				losOfWorkingPortStatus(12),
				slotRemovedStatus(13),
				slotLockStatus(14),
				slotRestartStatus(15),
				slotDisableStatus(16),
				slotResetStatus(17),
				slotPowerDownStatus(18),
				ponMacCrashStatus(19),
				daemonCrashStatus(20),
				unknownStatus(21)
				}
			MAX-ACCESS read-only
			STATUS current
			DESCRIPTION
				"Olt Redundancy Last Reason."
			::= { sleEponOltRedundancyEntry 9 }

		
		sleEponOltRedundancyHoldOffTime OBJECT-TYPE
			SYNTAX Integer32 (0..10)
			MAX-ACCESS read-only
			STATUS current
			DESCRIPTION
				"Holdoff time range:0-10(default:0ms)."
			::= { sleEponOltRedundancyEntry 10 }

		
		sleEponOltRedundancyMasterAdminStatus OBJECT-TYPE
			SYNTAX INTEGER
				{
				activate(0),
				deactivate(1)
				}
			MAX-ACCESS read-only
			STATUS current
			DESCRIPTION
				"Description."
			::= { sleEponOltRedundancyEntry 11 }

		
		sleEponOltRedundancySlaveAdminStatus OBJECT-TYPE
			SYNTAX INTEGER
				{
				activate(0),
				deactivate(1)
				}
			MAX-ACCESS read-only
			STATUS current
			DESCRIPTION
				"Description."
			::= { sleEponOltRedundancyEntry 12 }

		
		sleEponOltRedundancyStandbyRxSignal OBJECT-TYPE
			SYNTAX INTEGER
				{
				none(0),
				detect(1)
				}
			MAX-ACCESS read-only
			STATUS current
			DESCRIPTION
				"Description."
			::= { sleEponOltRedundancyEntry 13 }

		
		sleEponOltRedundancyTriggerLos OBJECT-TYPE
			SYNTAX INTEGER
				{
				enable(1),
				disable(2)
				}
			MAX-ACCESS read-only
			STATUS current
			DESCRIPTION
				"Description."
			::= { sleEponOltRedundancyEntry 14 }

		
		sleEponOltRedundancyTriggerManual OBJECT-TYPE
			SYNTAX INTEGER
				{
				enable(1),
				disable(2)
				}
			MAX-ACCESS read-only
			STATUS current
			DESCRIPTION
				"Description."
			::= { sleEponOltRedundancyEntry 15 }

		
		sleEponOltRedundancyTriggerSlot OBJECT-TYPE
			SYNTAX INTEGER
				{
				enable(1),
				disable(2)
				}
			MAX-ACCESS read-only
			STATUS current
			DESCRIPTION
				"Description."
			::= { sleEponOltRedundancyEntry 16 }

		
		sleEponOltRedundancyTriggerEponMac OBJECT-TYPE
			SYNTAX INTEGER
				{
				enable(1),
				disable(2)
				}
			MAX-ACCESS read-only
			STATUS current
			DESCRIPTION
				"Description."
			::= { sleEponOltRedundancyEntry 17 }

		
		sleEponOltRedundancyChagneStatus OBJECT-TYPE
			SYNTAX INTEGER
				{
				protectionWorkingMode(0),
				protectionStandbyMode(1),
				protectionWorkingPendingMode(2),
				protectionStandbyPendingMode(3)
				}
			MAX-ACCESS read-only
			STATUS current
			DESCRIPTION
				"The EPON OLT redundancy switchover change status. (only used for switchover trap)"
			::= { sleEponOltRedundancyEntry 18 }

		
		sleEponOltRedundancyControl OBJECT IDENTIFIER ::= { sleEponOltRedundancy 2 }

		
		sleEponOltRedundancyControlRequest OBJECT-TYPE
			SYNTAX INTEGER
				{
				setEponOltRedundancy(1),
				noEponOltRedundancy(2),
				setEponOltSwitchoverForceGroup(3),
				setEponOltRedundancyHoldOffTime(4),
				setEponOltRedundancyDbsyncCheck(5),
				setEponOltRedundancyDbResyn(6),
				setEponOltRedundancyTrigger(7)
				}
			MAX-ACCESS read-write
			STATUS current
			DESCRIPTION
				"The request of a user command."
			::= { sleEponOltRedundancyControl 1 }

		
		sleEponOltRedundancyControlStatus OBJECT-TYPE
			SYNTAX SleControlStatusType
			MAX-ACCESS read-only
			STATUS current
			DESCRIPTION
				"The status of user command."
			::= { sleEponOltRedundancyControl 2 }

		
		sleEponOltRedundancyControlTimer OBJECT-TYPE
			SYNTAX Gauge32
			MAX-ACCESS read-write
			STATUS current
			DESCRIPTION
				"The maximum time for the manager for a long running user command."
			::= { sleEponOltRedundancyControl 3 }

		
		sleEponOltRedundancyControlTimeStamp OBJECT-TYPE
			SYNTAX TimeTicks
			MAX-ACCESS read-only
			STATUS current
			DESCRIPTION
				"The time stamp of the last command(end of command)."
			::= { sleEponOltRedundancyControl 4 }

		
		sleEponOltRedundancyControlReqResult OBJECT-TYPE
			SYNTAX SleControlRequestResultType
			MAX-ACCESS read-only
			STATUS current
			DESCRIPTION
				"The result of the last user command."
			::= { sleEponOltRedundancyControl 5 }

		
		sleEponOltRedundancyControlGroupID OBJECT-TYPE
			SYNTAX INTEGER (1..4)
			MAX-ACCESS read-write
			STATUS current
			DESCRIPTION
				"Redundancy Group ID (1-4)."
			::= { sleEponOltRedundancyControl 6 }

		
		sleEponOltRedundancyControlTrunkID OBJECT-TYPE
			SYNTAX INTEGER (0..13 | 255)
			MAX-ACCESS read-write
			STATUS current
			DESCRIPTION
				"Redundancy trunk ID 0-13,disable is 255."
			::= { sleEponOltRedundancyControl 7 }

		
		sleEponOltRedundancyControlMaster OBJECT-TYPE
			SYNTAX INTEGER
			MAX-ACCESS read-write
			STATUS current
			DESCRIPTION
				"Redundancy Master OLT_ID."
			::= { sleEponOltRedundancyControl 8 }

		
		sleEponOltRedundancyControlSlave OBJECT-TYPE
			SYNTAX INTEGER
			MAX-ACCESS read-write
			STATUS current
			DESCRIPTION
				"Redundancy Slave OLT_ID."
			::= { sleEponOltRedundancyControl 9 }

		
		sleEponOltRedundancyControlWtrValue OBJECT-TYPE
			SYNTAX INTEGER (1..60)
			MAX-ACCESS read-write
			STATUS current
			DESCRIPTION
				"WTR value."
			::= { sleEponOltRedundancyControl 10 }

		
		sleEponOltRedundancyControlHoldOffTime OBJECT-TYPE
			SYNTAX Integer32 (0..10)
			MAX-ACCESS read-write
			STATUS current
			DESCRIPTION
				"Holdoff time range:0-10(default:0ms)."
			::= { sleEponOltRedundancyControl 11 }

		
		sleEponOltRedundancyControlOltType OBJECT-TYPE
			SYNTAX INTEGER
				{
				oltTypeEpon(1),
				oltTypeXepon(2)
				}
			MAX-ACCESS read-write
			STATUS current
			DESCRIPTION
				"Description."
			::= { sleEponOltRedundancyControl 12 }

		
		sleEponOltRedundancyControlSwitchOver OBJECT-TYPE
			SYNTAX INTEGER
				{
				force(1),
				noForce(2)
				}
			MAX-ACCESS read-write
			STATUS current
			DESCRIPTION
				"Description."
			::= { sleEponOltRedundancyControl 13 }

		
		sleEponOltRedundancyControlTriggerMask OBJECT-TYPE
			SYNTAX INTEGER
				{
				triggerLos(1),
				triggerManual(2),
				triggerSlot(3),
				triggerEponMac(4)
				}
			MAX-ACCESS read-write
			STATUS current
			DESCRIPTION
				"Description."
			::= { sleEponOltRedundancyControl 14 }

		
		sleEponOltRedundancyControlTriggerMode OBJECT-TYPE
			SYNTAX INTEGER
				{
				off(0),
				on(1)
				}
			MAX-ACCESS read-write
			STATUS current
			DESCRIPTION
				"Description."
			::= { sleEponOltRedundancyControl 15 }

		
		sleEponOltRedundancyNotification OBJECT IDENTIFIER ::= { sleEponOltRedundancy 3 }

		
		sleEponOltRedundancyChanged NOTIFICATION-TYPE
			OBJECTS { sleEponOltRedundancyControlRequest, sleEponOltRedundancyControlReqResult, sleEponOltRedundancyControlTimeStamp, sleEponOltRedundancyControlMaster, sleEponOltRedundancyControlSlave, 
				sleEponOltRedundancyControlGroupID, sleEponOltRedundancyControlTrunkID, sleEponOltRedundancyControlWtrValue }
			STATUS current
			DESCRIPTION 
				"Description."
			::= { sleEponOltRedundancyNotification 1 }

		
		sleEponOltRedundancySwitchoverForceGroup NOTIFICATION-TYPE
			OBJECTS { sleEponOltRedundancyControlRequest, sleEponOltRedundancyControlReqResult, sleEponOltRedundancyControlTimeStamp, sleEponOltRedundancyControlGroupID }
			STATUS current
			DESCRIPTION 
				"Description."
			::= { sleEponOltRedundancyNotification 2 }

		
		sleEponOltRedundancyHoldOffTimeChanged NOTIFICATION-TYPE
			OBJECTS { sleEponOltRedundancyControlRequest, sleEponOltRedundancyControlTimeStamp, sleEponOltRedundancyControlReqResult, sleEponOltRedundancyControlGroupID, sleEponOltRedundancyControlHoldOffTime
				 }
			STATUS current
			DESCRIPTION 
				"Description."
			::= { sleEponOltRedundancyNotification 3 }

		
		sleEponOltRedundancyDbsyncCheckChanged NOTIFICATION-TYPE
			OBJECTS { sleEponOltRedundancyControlRequest, sleEponOltRedundancyControlStatus, sleEponOltRedundancyControlTimer, sleEponOltRedundancyControlTimeStamp, sleEponOltRedundancyControlReqResult, 
				sleEponOltRedundancyControlGroupID }
			STATUS current
			DESCRIPTION 
				"Description."
			::= { sleEponOltRedundancyNotification 4 }

		
		sleEponOltRedundancyDbResyncChanged NOTIFICATION-TYPE
			OBJECTS { sleEponOltRedundancyControlRequest, sleEponOltRedundancyControlStatus, sleEponOltRedundancyControlTimer, sleEponOltRedundancyControlTimeStamp, sleEponOltRedundancyControlReqResult, 
				sleEponOltRedundancyControlGroupID }
			STATUS current
			DESCRIPTION 
				"Description."
			::= { sleEponOltRedundancyNotification 5 }

		
		sleEponOltRedundancyTriggerChanged NOTIFICATION-TYPE
			OBJECTS { sleEponOltRedundancyControlRequest, sleEponOltRedundancyControlStatus, sleEponOltRedundancyControlTimer, sleEponOltRedundancyControlTimeStamp, sleEponOltRedundancyControlReqResult, 
				sleEponOltRedundancyControlGroupID, sleEponOltRedundancyControlTriggerMask, sleEponOltRedundancyControlTriggerMode }
			STATUS current
			DESCRIPTION 
				"Description."
			::= { sleEponOltRedundancyNotification 6 }

		
		sleEponGroup OBJECT-GROUP
			OBJECTS { sleEponOltControlRequest, sleEponOltControlStatus, sleEponOltControlTimer, sleEponOltControlTimeStamp, sleEponOltControlReqResult, 
				sleEponOltControlOltIndex, sleEponOltControlRegMode, sleEponOltControlEncryptionPolicy, sleEponOltControlP2pAccessControl, sleEponOltControlDbaInternal, 
				sleEponOltControlDbaCycle, sleEponOltControlDbaDiscoveryFrequency, sleEponOltControlDbaDiscoveryLength, sleEponOnuControlRequest, sleEponOnuControlStatus, 
				sleEponOnuControlTimer, sleEponOnuControlTimeStamp, sleEponOnuControlReqResult, sleEponOnuControlOltIndex, sleEponOnuControlMacAddress, 
				sleEponOnuControlRegMode, sleEponOnuControlDescription, sleEponOnuControlProfile, sleEponProfileControlRequest, sleEponProfileControlStatus, 
				sleEponProfileControlTimer, sleEponProfileControlTimeStamp, sleEponProfileControlReqResult, sleEponProfileControlName, sleEponProfileControlDPDownMaxBandwidth, 
				sleEponProfileControlDPDownMaxBurstSize, sleEponProfileControlDPP2pMaxBandwidth, sleEponProfileControlDPP2pMaxBurstSize, sleEponProfileControlSlaGuaranteedBandwidth, sleEponProfileControlSlaPlatoClass, 
				sleEponProfileControlSlaPlatoGuaranteedBandwidth1m, sleEponProfileControlSlaPlatoGuaranteedBandwdith64k, sleEponProfileControlSlaPlatoBestEffortBandwidth1m, sleEponProfileControlSlaPlatoBestEffortBandwidth64k, sleEponProfileControlSlaPlatoDelayLevel, 
				sleEponAlarmControlRequest, sleEponAlarmControlStatus, sleEponAlarmControlTimer, sleEponAlarmControlTimeStamp, sleEponAlarmControlReqResult, 
				sleEponAlarmControlOltIndex, sleEponAlarmControlBadEncryption, sleEponAlarmControlDyingGasp, sleEponAlarmControlLlidMismatch, sleEponAlarmControlOnuRegistrationError, 
				sleEponOnuControlOnuIndex, sleEponOnuControlOnuStatus, sleEponStatsOltControlRequest, sleEponStatsOltControlStatus, sleEponStatsOltControlTimer, 
				sleEponStatsOltControlTimeStamp, sleEponStatsOltControlReqResult, sleEponStatsOltControlOltIndex, sleEponStatsOltControlChannelIndex, sleEponOnuControlLoopbackProvision, 
				sleEponAlarmControlTooManyOnuRegistration, sleEponProfileQueueControlRequest, sleEponProfileQueueControlStatus, sleEponProfileQueueControlTimer, sleEponProfileQueueControlTimeStamp, 
				sleEponProfileQueueControlReqResult, sleEponProfileQueueControlProfileIndex, sleEponProfileQueueControlQueueIndex, sleEponProfileQueueControlQPUpQueue, sleEponProfileQueueControlQPUpMaxBandwidth, 
				sleEponProfileQueueControlQPUpMAxBurstSize, sleEponProfileQueueControlQPDownQueue, sleEponProfileQueueControlQPDownMaxBandwidth, sleEponProfileQueueControlQPDownMAxBurstSize, sleEponOltControlProfile, 
				sleEponProfilePortControlRequest, sleEponProfilePortControlStatus, sleEponProfilePortControlTimer, sleEponProfilePortControlTimeStamp, sleEponProfilePortControlReqResult, 
				sleEponProfilePortControlAdminStatus, sleEponProfilePortControlNego, sleEponProfilePortControlSpeed, sleEponProfilePortControlMaxHost, sleEponProfileVlanControlRequest, 
				sleEponProfileVlanControlStatus, sleEponProfileVlanControlTimer, sleEponProfileVlanControlTimeStamp, sleEponProfileVlanControlReqResult, sleEponProfileVlanControlVlanIndex, 
				sleEponProfileVlanControlVlanEgressPorts, sleEponProfileVlanControlVlanUntaggedPorts, sleEponProfilePortControlPvid, sleEponProfilePortControlEgressRateLimit, sleEponProfilePortControlIngressRateLimit, 
				sleEponProfilePortControlIngressRateLimitMode, sleEponOnuPortControlReqResult, sleEponOnuPortControlOltIndex, sleEponOnuPortControlOnuIndex, sleEponOnuPortControlPortIndex, 
				sleEponOnuPortControlRequest, sleEponOnuPortControlStatus, sleEponOnuPortControlTimer, sleEponOnuPortControlTimeStamp, sleEponOnuClassificationControlRequest, 
				sleEponOnuClassificationControlStatus, sleEponOnuClassificationControlTimer, sleEponOnuClassificationControlTimeStamp, sleEponOnuClassificationControlProtoTypeNum, sleEponOnuClassificationControlL3Addr, 
				sleEponOnuClassificationControlReqResult, sleEponOnuClassificationControlName, sleEponOnuClassificationControlTrafficDirection, sleEponOnuClassificationControlLayer, sleEponOnuClassificationControlEtherType, 
				sleEponProfileVlanControlProfileIndex, sleEponProfileClassificationControlQueue, sleEponProfileClassificationControlReqResult, sleEponProfileClassificationControlProfileIndex, sleEponProfileClassificationControlClassificationIndex, 
				sleEponProfileClassificationControlMatchAction, sleEponProfileClassificationControlRequest, sleEponProfileClassificationControlStatus, sleEponProfileClassificationControlTimer, sleEponProfileClassificationControlTimeStamp, 
				sleEponOltIndex, sleEponOltRegMode, sleEponOltStatus, sleEponOltEncryptionPolicy, sleEponOltP2pAccessControl, 
				sleEponOltDbaInternal, sleEponOltDbaCycle, sleEponOltDbaDiscoveryFrequency, sleEponOltDbaDiscoveryLength, sleEponOltProfile, 
				sleEponOltTxFault, sleEponOltLossOfSignal, sleEponOltAdminRegMode, sleEponOltSC, sleEponOltSCAutoOnuBlock, 
				sleEponOltControlSC, sleEponOltControlSCAutoOnuBlock, sleEponOltControlUpgradeFilename, sleEponOnuIndex, sleEponOnuLlid, 
				sleEponOnuRegMode, sleEponOnuStatus, sleEponOnuMacAddress, sleEponOnuRtt, sleEponOnuDescription, 
				sleEponOnuProfile, sleEponOnuLoopbackProvision, sleEponOnuVendor, sleEponOnuFirmwareRev, sleEponOnuControlTxPowerOffTimer, 
				sleEponOnuVlanIndex, sleEponOnuVlanEgressPorts, sleEponOnuVlanUntaggedPorts, sleEponOnuPortIndex, sleEponOnuPortAdminStatus, 
				sleEponOnuPortOperStatus, sleEponOnuPortNego, sleEponOnuPortSpeed, sleEponOnuPortDuplex, sleEponOnuPortMaxHost, 
				sleEponOnuPortPvid, sleEponOnuPortIngressRateLimitMode, sleEponOnuPortIngressRateLimit, sleEponOnuPortEgressRateLimit, sleEponOnuPortFlowControl, 
				sleEponOnuFdbMacAddress, sleEponOnuFdbType, sleEponOnuFdbPermission, sleEponOnuFdbControlRequest, sleEponOnuFdbControlStatus, 
				sleEponOnuFdbControlTimer, sleEponOnuFdbControlTimeStamp, sleEponOnuFdbControlReqResult, sleEponOnuFdbControlOltIndex, sleEponOnuFdbControlOnuIndex, 
				sleEponOnuFdbControlType, sleEponOnuUserMacIndex, sleEponOnuUserMacMacAddress, sleEponOnuUserMacUsedTime, sleEponProfileIndex, 
				sleEponProfileName, sleEponProfileDPDownMaxBandwidth, sleEponProfileDPDownMaxBurstSize, sleEponProfileDPP2pMaxBandwidth, sleEponProfileDPP2pMaxBurstSize, 
				sleEponProfileSlaGuaranteedBandwidth, sleEponProfileSlaBestEffortBandwidth, sleEponProfileSlaPlatoClass, sleEponProfileSlaPlatoMinBandwidth1m, sleEponProfileSlaPlatoMinBandwdith64k, 
				sleEponProfileSlaPlatoMaxBandwidth1m, sleEponProfileSlaPlatoMaxBandwidth64k, sleEponProfileSlaPlatoDelayLevel, sleEponProfileIgmpFilter, sleEponProfileIgmpSnooping, 
				sleEponProfileSTPenable, sleEponProfileControlExtendMtu, sleEponProfileControlIgmpFilter, sleEponProfileControlSnooping, sleEponProfileControlSTPenable, 
				sleEponProfileQueueIndex, sleEponProfileQueueQPUpQueue, sleEponProfileQueueQPUpMaxBandwidth, sleEponProfileQueueQPUpMAxBurstSize, sleEponProfileQueueQPDownQueue, 
				sleEponProfileQueueQPDownMaxBandwidth, sleEponProfileQueueQPDownMAxBurstSize, sleEponProfileQueueQLimitUpBlockSize, sleEponProfileQueueQLimitDownBlockSize, sleEponProfileQueueControlLimitFlag, 
				sleEponProfileQueueControlBlockSize0, sleEponProfileQueueControlBlockSize1, sleEponProfileQueueControlBlockSize2, sleEponProfileQueueControlBlockSize3, sleEponProfileVlanIndex, 
				sleEponProfileVlanEgressPorts, sleEponProfileVlanUntaggedPorts, sleEponProfilePortIndex, sleEponProfilePortAdminStatus, sleEponProfilePortNego, 
				sleEponProfilePortSpeed, sleEponProfilePortduplex, sleEponProfilePortMaxHost, sleEponProfilePortPvid, sleEponProfilePortIngressRateLimitMode, 
				sleEponProfilePortIngressRateLimit, sleEponProfilePortEgressRateLimit, sleEponProfilePortFlowControl, sleEponProfilePortControlFlowControl, sleEponProfileClassificationIndex, 
				sleEponProfileClassificationMatchAction, sleEponProfileClassificationQueue, sleEponAlarmBadEncryption, sleEponAlarmDyingGasp, sleEponAlarmLlidMismatch, 
				sleEponAlarmOnuRegistrationError, sleEponAlarmTooManyOnuRegistration, sleEponStatsOltInOctets, sleEponStatsOltInPkts, sleEponStatsOltInPause, 
				sleEponStatsOltInErroredFrame, sleEponStatsOltInUnicastPkts, sleEponstatsOltInBroadcastPkts, sleEponStatsOltInMulticastPkts, sleEponStatsOltOutOctets, 
				sleEponStatsOltOutPkts, sleEponStatsOltOutPause, sleEponStatsOltOutDropped, sleEponStatsOltOutUnicastPkts, sleEponstatsOltOutBroadcastPkts, 
				sleEponStatsOltOutMulticastPkts, sleEponStatsOltPonInOctets, sleEponStatsOltPonInPkts, sleEponStatsOltPonInPause, sleEponStatsOltPonInErroredFrame, 
				sleEponStatsOltPonInUnicastPkts, sleEponstatsOltPonInBroadcastPkts, sleEponStatsOltPonInMulticastPkts, sleEponStatsOltPonOutOctets, sleEponStatsOltPonOutPkts, 
				sleEponStatsOltPonOutPause, sleEponStatsOltPonOutDropped, sleEponStatsOltPonOutUnicastPkts, sleEponstatsOltPonOutBroadcastPkts, sleEponStatsOltPonOutMulticastPkts, 
				sleEponStatsOltChannelInOctets, sleEponStatsOltChannelInDataOctets, sleEponStatsOltChannelInPkts, sleEponStatsOltChannelInMulticastPkts, sleEponStatsOltChannelInBroadcastPkts, 
				sleEponStatsOltChannelInErrorOctets, sleEponStatsOltChannelInErrorPkts, sleEponStatsOltChannelOutOctets, sleEponStatsOltChannelOutPkts, sleEponStatsOltChannelOutPolicerDroppedPkts, 
				sleEponStatsOltChannelOutMismatchDroppedPkts, sleEponStatsOltChannelOutMulticastPkts, sleEponStatsOltChannelOutBroadcastPkts, sleEponStatsOltChannelFCS, sleEponStatsOltChannelInRangeLengthErrors, 
				sleEponStatsOltChannelFrameTooLongErrors, sleEponStatsOltChannelInUnicastPkts, sleEponStatsOltChannelOutUnicastPkts, sleEponStatsOnuPortInOctets, sleEponStatsOnuPortInPkts, 
				sleEponStatsOnuPortInUcastPkts, sleEponStatsOnuPortInBcastPkts, sleEponStatsOnuPortInMcastPkts, sleEponStatsOnuPortOutOctets, sleEponStatsOnuPortOutPkts, 
				sleEponStatsOnuPortOutUcastPkts, sleEponStatsOnuPortOutBcastPkts, sleEponStatsOnuPortOutMcastPkts, sleEponOnuClassificationIndex, sleEponOnuClassificationName, 
				sleEponOnuClassificationTrafficDirection, sleEponOnuClassificationLayer, sleEponOnuClassificationEtherType, sleEponOnuClassificationProtoTypeNum, sleEponOnuClassificationL3Addr, 
				sleEponOnuClassificationL4Num, sleEponVlanOltVlanMode, sleEponVlanOltVlanNestedStack, sleEponVlanOltVlanPrefix, sleEponVlanOltVlanSuffix, 
				sleEponVlanOltVlanTag, sleEponVlanOltVlanEtherType, sleEponVlanOltVlanControlRequest, sleEponVlanOltVlanControlStatus, sleEponVlanOltVlanControlTimer, 
				sleEponVlanOltVlanControlTimeStamp, sleEponVlanOltVlanControlReqResult, sleEponVlanOltVlanControlOltIndex, sleEponVlanOltVlanControlOnuIndex, sleEponVlanOltVlanControlMode, 
				sleEponVlanOltVlanControlNestedStack, sleEponVlanOltVlanControlPrefix, sleEponVlanOltVlanControlSuffix, sleEponVlanOltVlanControlVlanTag, sleEponVlanOltVlanControlEtherType, 
				sleEponVlanOnuVlanUpVlanTag, sleEponVlanOnuVlanUpEtherType, sleEponVlanOnuVlanUpPriority, sleEponVlanOnuVlanDownVlanTag, sleEponVlanOnuVlanDownPriority, 
				sleEponVlanOnuVlanControlRequest, sleEponVlanOnuVlanControlStatus, sleEponVlanOnuVlanControlTimer, sleEponVlanOnuVlanControlTimeStamp, sleEponVlanOnuVlanControlReqResult, 
				sleEponVlanOnuVlanControlOltIndex, sleEponVlanOnuVlanControlOnuIndex, sleEponVlanOnuVlanControlUpVlanTag, sleEponVlanOnuVlanControlUpEtherType, sleEponVlanOnuVlanControlUpPriority, 
				sleEponVlanOnuVlanControlDownPriority, sleEponProfileControlIndex, sleEponOnuControlUpgradePath, sleEponProfileControlSlaBestEffortBandwidth, sleEponProfilePortControlProfileIndex, 
				sleEponProfilePortControlPortIndex, sleEponProfilePortControlDuplex, sleEponOnuClassificationControlL4Num, sleEponVlanOnuVlanControlDownVlanTag, sleEponVlanOnuVlanUpMode, 
				sleEponVlanOnuVlanDownMode, sleEponVlanOnuVlanControlUpMode, sleEponProfileQueueControlBlockSize4, sleEponProfileQueueControlBlockSize5, sleEponProfileQueueControlBlockSize6, 
				sleEponProfileQueueControlBlockSize7, sleEponVlanOnuVlanControlDownMode, sleEponProfileUNIQueueUpMaxBandwidth, sleEponProfileUNIQueueUpMaxBurstSize, sleEponProfileUNIQueueDownMaxBandwidth, 
				sleEponProfileUNIQueueDownMaxBurstSize, sleEponProfileUNIQueueControlRequest, sleEponProfileUNIQueueControlStatus, sleEponProfileUNIQueueControlTimer, sleEponProfileUNIQueueControlTimeStamp, 
				sleEponProfileUNIQueueControlReqResult, sleEponProfileUNIQueueControlProfileIndex, sleEponProfileUNIQueueControlUpMaxBandwidth, sleEponProfileUNIQueueControlUpMaxBurstSize, sleEponProfileUNIQueueControlDownMaxBandwidth, 
				sleEponProfileUNIQueueControlDownMaxBurstSize, sleEponPTimeStatsPortSaveTime, sleEponPTimeStatsPortHourInOctets, sleEponPTimeStatsPortHourOutOctets, sleEponPTimeStatsPortDayInOctets, 
				sleEponPTimeStatsPortDayOutOctets, sleEponPTimeStatsOltSaveTime, sleEponPTimeStatsOltHourInOctets, sleEponPTimeStatsOltHourOutOctets, sleEponPTimeStatsOltDayInOctets, 
				sleEponPTimeStatsOltDayOutOctets, sleEponPTimeStatsOnuSaveTime, sleEponPTimeStatsOnuHourInOctets, sleEponPTimeStatsOnuHourOutOctets, sleEponPTimeStatsOnuDayInOctets, 
				sleEponPTimeStatsOnuDayOutOctets, sleEponPTimeStatsControlRequest, sleEponPTimeStatsControlStatus, sleEponPTimeStatsControlTimer, sleEponPTimeStatsControlTimeStamp, 
				sleEponPTimeStatsControlReqResult, sleEponPTimeStatsServiceActivity, sleEponPTimeStatsControlServiceActivity, sleEponOnuSubscriberCurrentIpAddress, sleEponOnuSubscriberCurrentMacAddress, 
				sleEponOnuSubscriberControlRequest, sleEponOnuSubscriberControlStatus, sleEponOnuSubscriberControlTimer, sleEponOnuSubscriberControlTimeStamp, sleEponOnuSubscriberControlReqResult, 
				sleEponOnuSubscriberControlOltIndex, sleEponOnuSubscriberControlOnuIndex, sleEponOnuSubscriberCurrentPort, sleEponOnuSubscriberHistoryTime, sleEponOnuSubscriberHistoryIpAddress, 
				sleEponOnuSubscriberHistoryMacAddress, sleEponOnuSubscriberHistoryPort, sleEponProfileSubscriberInfoCollection, sleEponProfileControlSubscriberInfoCollection, sleEponOnuSubscriberCurrentTime, 
				sleEponOltOperStatus, sleEponProfileLoopDetectStatus, sleEponProfileLoopDetectBlockTimer, sleEponProfileLoopDetectSendingpacket, sleEponProfileControlLoopDetectStatus, 
				sleEponProfileControlLoopDetectBlockTimer, sleEponProfileControlLoopDetectSendingpacket, sleEponBaseSlaPlatoMaxBandwdith, sleEponBaseDPShapingMaxBandwidth, sleEponBasePortMaxHost, 
				sleEponBaseControlRequest, sleEponBaseControlStatus, sleEponBaseControlTimer, sleEponBaseControlTimeStamp, sleEponBaseControlReqResult, 
				sleEponBaseControlSlaPlatoMaxBandwdith, sleEponBaseControlDPShapingMaxBandwidth, sleEponBaseControlPortMaxHost, sleEponBaseOnuAutoUpgrade, sleEponBaseOnuAutoUpgradeRebootTime, 
				sleEponBaseControlOnuAutoUpgrade, sleEponBaseControlOnuAutoUpgradeRebootTime, sleEponOltFirmwareRev, sleEponFirmwareType, sleEponFirmwareName, 
				sleEponFirmwareControlRequest, sleEponFirmwareControlStatus, sleEponFirmwareControlTimer, sleEponFirmwareControlTimeStamp, sleEponFirmwareControlReqResult, 
				sleEponFirmwareControlName, sleEponFirmwareControlUpgradeMethod, sleEponFirmwareControlUpgradeMode, sleEponFirmwareControlServerAddress, sleEponFirmwareControlUser, 
				sleEponFirmwareControlPasswd, sleEponOnuSipGlobalConfigIp, sleEponOnuSipGlobalConfigNetmask, sleEponOnuSipGlobalConfigGateway, sleEponOnuSipGlobalConfigVid, 
				sleEponOnuControlSipGlobalConfigIp, sleEponOnuControlSipGlobalConfigNetmask, sleEponOnuControlSipGlobalConfigGateway, sleEponOnuControlSipGlobalConfigVid, sleEponProfileSipMgPort, 
				sleEponProfileSipProxyServer, sleEponProfileSipProxyServerPort, sleEponProfileSipBackupProxyServer, sleEponProfileSipBackupProxyServerPort, sleEponProfileSipActiveServer, 
				sleEponProfileSipRegisterServer, sleEponProfileSipRegisterServerPort, sleEponProfileSipBackupRegisterServer, sleEponProfileSipBackupRegisterServerPort, sleEponProfileSipOutBindServer, 
				sleEponProfileSipOutBindServerPort, sleEponProfileSipRegisterInterval, sleEponProfileSipHeartBeatSwitch, sleEponProfileSipHeartBeatCycle, sleEponProfileSipHeartBeatCount, 
				sleEponProfileVoiceT38enable, sleEponProfileModemControl, sleEponProfileControlSipMgPort, sleEponProfileControlSipProxyServer, sleEponProfileControlSipProxyServerPort, 
				sleEponProfileControlSipBackupProxyServer, sleEponProfileControlSipBackupProxyServerPort, sleEponProfileControlSipActiveServer, sleEponProfileControlSipRegisterServer, sleEponProfileControlSipRegisterServerPort, 
				sleEponProfileControlSipBackupRegisterServer, sleEponProfileControlSipBackupRegisterServerPort, sleEponProfileControlSipOutBindServer, sleEponProfileControlSipOutBindServerPort, sleEponProfileControlSipRegisterInterval, 
				sleEponProfileControlSipHeartBeatSwitch, sleEponProfileControlSipHeartBeatCycle, sleEponProfileControlSipHeartBeatCount, sleEponProfileControlVoiceT38enable, sleEponProfileControlModemControl, 
				sleEponOnuSipUserConfigControlTimer, sleEponOnuSipUserConfigPots, sleEponOnuSipUserConfigAccount, sleEponOnuSipUserConfigName, sleEponOnuSipUserConfigPasswd, 
				sleEponOnuSipUserConfigControlRequest, sleEponOnuSipUserConfigControlStatus, sleEponOnuSipUserConfigControlTimeStamp, sleEponOnuSipUserConfigControlReqResult, sleEponOnuSipUserConfigControlOltIndex, 
				sleEponOnuSipUserConfigControlOnuIndex, sleEponOnuSipUserConfigControlPots, sleEponOnuSipUserConfigControlAccount, sleEponOnuSipUserConfigControlName, sleEponOnuSipUserConfigControlPasswd, 
				sysDescr, ifIndex, sleEponBaseOnuAgingTime, sleEponBaseAlarmStatus, sleEponBaseAlarmMode, 
				sleEponBaseControlOnuAgingTime, sleEponBaseControlAlarmStatus, sleEponBaseControlAlarmMode, sleEponOltKeyExchangeTimeout, sleEponOltRssiStatus, 
				sleEponOltOnuRegisterCount, sleEponOltControlKeyExchangeTimeout, sleEponOltControlRssiStatus, sleEponOltP2PIndex, sleEponOltP2PEnable, 
				sleEponOltP2POnuID1, sleEponOltP2POnuID2, sleEponOltP2PControlRequest, sleEponOltP2PControlStatus, sleEponOltP2PControlTimer, 
				sleEponOltP2PControlTimeStamp, sleEponOltP2PControlReqResult, sleEponOltP2PControlOltIndex, sleEponOltP2PControlEnable, sleEponOltP2PControlOnuID1, 
				sleEponOltP2PControlOnuID2, sleEponOltDMITemper, sleEponOltDMIVoltage, sleEponOltDMITxBias, sleEponOltDMITxPower, 
				sleEponOltDMIRxPower, sleEponOnuLgPathStatus, sleEponOnuModelType, sleEponOnuSipGlobalConfigMode, sleEponOnuSipGlobalUserName, 
				sleEponOnuSipGlobalPasswd, sleEponOnuRxPower, sleEponOnuRxPowerAlarmStatus, sleEponOnuRssiInfo, sleEponOnuLoopDetectUnblockStatus, 
				sleEponOnuUpgradeStatus, sleEponOnuOltRssiStatus, sleEponOnuOltRssiInfo, sleEponOnuMultiLlid, sleEponOnuMultiMacAddress, 
				sleEponOltDBAMutilLLidLinkOperate, sleEponOnuControlSipGlobalConfigMode, sleEponOnuControlSipGlobalConfigUserName, sleEponOnuControlSipGlobalConfigUserPasswd, sleEponOnuControlPingCount, 
				sleEponOnuDMITemper, sleEponOnuDMIVoltage, sleEponOnuDMITxBias, sleEponOnuDMITxPower, sleEponOnuDMIRxPower, 
				sleEponOnuDMIThresholdWarnTemperLow, sleEponOnuDMIThresholdWarnTemperHigh, sleEponOnuDMIThresholdAlarmTemperLow, sleEponOnuDMIThresholdAlarmTemperHigh, sleEponOnuDMIThresholdWarnVoltageLow, 
				sleEponOnuDMIThresholdWarnVoltageHigh, sleEponOnuDMIThresholdAlarmVoltageLow, sleEponOnuDMIThresholdAlarmVoltageHigh, sleEponOnuDMIThresholdWarnTxbiasLow, sleEponOnuDMIThresholdWarnTxbiasHigh, 
				sleEponOnuDMIThresholdAlarmTxbiasLow, sleEponOnuDMIThresholdAlarmTxbiasHigh, sleEponOnuDMIThresholdWarnTxPowerLow, sleEponOnuDMIThresholdWarnTxPowerHigh, sleEponOnuDMIThresholdAlarmTxPowerLow, 
				sleEponOnuDMIThresholdAlarmTxPowerHigh, sleEponOnuDMIThresholdWarnRxPowerLow, sleEponOnuDMIThresholdWarnRxPowerHigh, sleEponOnuDMIThresholdAlarmRxPowerLow, sleEponOnuDMIThresholdAlarmRxPowerHigh, 
				sleEponOnuDMIThresholdControlRequest, sleEponOnuDMIThresholdControlStatus, sleEponOnuDMIThresholdControlTimer, sleEponOnuDMIThresholdControlTimeStamp, sleEponOnuDMIThresholdControlReqResult, 
				sleEponOnuDMIThresholdControlOltIndex, sleEponOnuDMIThresholdControlOnuIndex, sleEponOnuDMIThresholdControlMonitorType, sleEponOnuDMIThresholdControlMode, sleEponOnuDMIThresholdControlLowThreshold, 
				sleEponOnuDMIThresholdControlHighThreshold, sleEponOnuPortAgingTime, sleEponOnuPortForwardMode, sleEponOnuMacTableDynamicMacAddress, sleEponOnuMacTableStaticMacAddress, 
				sleEponProfileSipDNS1Server, sleEponProfileSipDNS2Server, sleEponProfileDHCPEnable, sleEponProfileMacLearnStatus, sleEponProfileControlSipDNS1Server, 
				sleEponProfileControlSipDNS2Server, sleEponProfileControlDHCPEnable, sleEponProfileControlMacLearnStatus, sleEponProfileIgmpSnoopingIndex, sleEponProfileIgmpSnoopingState, 
				sleEponProfileIgmpSnoopingMaxch, sleEponProfileIgmpSnoopingTagVlan, sleEponProfileIgmpSnoopingControlRequest, sleEponProfileIgmpSnoopingControlStatus, sleEponProfileIgmpSnoopingControlTimer, 
				sleEponProfileIgmpSnoopingControlTimeStamp, sleEponProfileIgmpSnoopingControlReqResult, sleEponProfileIgmpSnoopingControlProfileIndex, sleEponProfileIgmpSnoopingControlState, sleEponProfileIgmpSnoopingControlMaxch, 
				sleEponProfileIgmpSnoopingControlTagVlan, sleEponOnuProfileOnuRuleIndex, sleEponProfileOnuRuleName, sleEponProfileOnuRuleControlRequest, sleEponProfileOnuRuleControlStatus, 
				sleEponProfileOnuRuleControlTimer, sleEponProfileOnuRuleControlTimeStamp, sleEponProfleOnuRuleControlReqResult, sleEponProfileOnuRuleControlProfileIndex, sleEponProfileOnuRuleControlName, 
				sleEponProfilePortIsolationStatus, sleEponProfilePortMaxHostAgingTime, sleEponProfilePortControlIsolationStatus, sleEponProfilePortControlMaxHostAgingTime, sleEponAlarmOpticSignalError, 
				sleEponAlarmStandardLinkFault, sleEponAlarmLossOfSignal, sleEponAlarmTransmitFail, sleEponAlarmMacLearningOverflow, sleEponAlarmLoopback, 
				sleEponAlarmStandardDyingGasp, sleEponAlarmExternalDyingGasp, sleEponAlarmStandardCriticalEvent, sleEponAlarmExternalCriticalEvent, sleEponAlarmEponStandbyLos, 
				sleEponAlarmControlOpticSignalError, sleEponAlarmControlStandardLinkFault, sleEponAlarmControlLossOfSignal, sleEponAlarmControlTransmitFail, sleEponAlarmControlMacLearningOverflow, 
				sleEponAlarmControlLoopback, sleEponAlarmControlStandardDyingGasp, sleEponAlarmControlExternalDyingGasp, sleEponAlarmControlStandardCriticalevent, sleEponAlarmControlExternalCriticalEvent, 
				sleEponAlarmControlEponStandbyLos, sleEponStatsOltHostFrame, sleEponStatsOltInTooLongFrame, sleEponStatsOltHostFrameDropped, sleEponStatsOltPonInHostFrame, 
				sleEponStatsOltPonInTooLongFrame, sleEponStatsOltPonInHostFrameDropped, sleEponStatsOltPonInHECErrorFrame, sleEponStatsOltFromOnuInFrame, sleEponStatsOltFromOnuInErrorFrame, 
				sleEponStatsOltFromOnuInMulticastFrame, sleEponStatsOltFromOnuInBroadcastFrame, sleEponStatsOltFromOnuInReportFrame, sleEponStatsOltFromOnuInCheckSeqErrorFrame, sleEponStatsOltFromOnuInRangeLenErrors, 
				sleEponStatsOltFromOnuInTooLongFrame, sleEponStatsOltFromOnuOutFrame, sleEponStatsOltFromOnuOutFrameBytes, sleEponStatsOltFromOnuOutMulticastFrame, sleEponStatsOltFromOnuOutBroadcastFrame, 
				sleEponStatsOltFromOnuOutDBAGrantFrame, sleEponStatsOltFromOnuOutControlGrantFrame, sleEponStatsOnuPortInUndersize, sleEponStatsOnuPortInOversize, sleEponStatsOnuPortInJabber, 
				sleEponStatsOnuPortInRxError, sleEponStatsOnuPortInRxFcsError, sleEponStatsOnuUniInPkts, sleEponStatsOnuUniInBytes, sleEponStatsOnuUniInErrPkts, 
				sleEponStatsOnuUniInErrBytes, sleEponStatsOnuUniInPause, sleEponStatsOnuUniFrameLongError, sleEponStatsOnuUniOutPkts, sleEponStatsOnuUniOutBytes, 
				sleEponStatsOnuUniOutPause, sleEponStatsOnuUniOutDropPkts, sleEponStatsOnuUnInMcastPkts, sleEponStatsOnuUnInBcastPkts, sleEponStatsOnuUniInDropPkts, 
				sleEponStatsOnuUniOutMcastPkts, sleEponStatsOnuUniOutBcastPkts, sleEponStatsOnuPonInPkts, sleEponStatsOnuPonInBytes, sleEponStatsOnuPonInMcastPkts, 
				sleEponStatsOnuPonIntBcastPkts, sleEponStatsOnuPonInErrPkts, sleEponStatsOnuPonInErrBytes, sleEponStatsOnuPonInPause, sleEponStatsOnuPonInHostPkts, 
				sleEponStatsOnuPonInDropHostPkts, sleEponStatsOnuPonFrameLongError, sleEponStatsOnuPonOutPkts, sleEponStatsOnuPonOutBytes, sleEponStatsOnuPonOutMcastPkts, 
				sleEponStatsOnuPonOutBcastPkts, sleEponStatsOnuPonOutPause, sleEponStatsOnuPonOutDropPkts, sleEponStatsOnuPonOutHostPkts, sleEponStatsOnuPonOutChipErrPkts, 
				sleEponStatsOnuPonInDropPkts, sleEponOnuVoipPortStatus, sleEponOnuSipPortServiceState, sleEponOnuSipPortCodecMode, sleEponRuleClauseQueue, 
				sleEponRuleClauseQueueValue, sleEponRuleClauseLayerOperation, sleEponRuleClauseLayerValue, sleEponRuleClauseL2Mac, sleEponRuleClauseL2EthertypeValue, 
				sleEponRuleClauseNetmask, sleEponRuleClauseL3Addr, sleEponRuleClauseTcpUdpPort, sleEponRuleClauseTcpUdpPortNum, sleEponRuleClauseProtoType, 
				sleEponRuleClauseProtoTypeNum, sleEponRuleClauseVlanType, sleEponRuleClauseVlanValue, sleEponRuleClauseLinkIndexValue, sleEponRuleClauseMatchMode, 
				sleEponRuleClauseControlRequest, sleEponRuleClauseControlStatus, sleEponRuleClauseControlTimer, sleEponRuleClauseControlTimeStamp, sleEponRuleClauseControlReqResult, 
				sleEponRuleClauseControlClauseIndex, sleEponRuleClauseControlClauseMatch, sleEponRuleClauseControlQueue, sleEponRuleClauseControlQueueValue, sleEponRuleClauseControlLayerOperation, 
				sleEponRuleClauseControlLayerValue, sleEponRuleClauseControlL2Mac, sleEponRuleClauseControlL2EtherType, sleEponRuleClauseControlNetmask, sleEponRuleClauseControlL3Addr, 
				sleEponRuleClauseControlTcpUdpPort, sleEponRuleClauseControlTcpUdpPortNum, sleEponRuleClauseControlProtoType, sleEponRuleClauseControlProtoTypeNum, sleEponRuleClauseControlVlanType, 
				sleEponRuleClauseControlVlanValue, sleEponRuleClauseControlLinkIndexValue, sleEponRuleActionVlanOperate, sleEponRuleActionVlanMap, sleEponRuleActionEtherType, 
				sleEponRuleActionVlanID, sleEponRuleActionDiscardOperate, sleEponRuleActionDiscardOperateValue, sleEponRuleActionCaptureHostOperate, sleEponRuleActionCaptureHostFlexibleOperate, 
				sleEponRuleActionQueueId, sleEponRuleActionUnicastLinkDestID, sleEponRuleActionUnicastLinkDestOffset, sleEponRuleActionMulticastLinkDomID, sleEponRuleActionMulticastLinkDomOffset, 
				sleEponRuleActionCosOperate, sleEponRuleActionCosValue, sleEponRuleActionTosOperate, sleEponRuleActionTosValue, sleEponRuleActionOutputOperate, 
				sleEponRuleActionOutputValue, sleEponRuleActionOutputVlanContent, sleEponRuleActionOutputSourceFiledCopy, sleEponRuleActionQueuePendingOperate, sleEponRuleActionControlRequest, 
				sleEponRuleActionControlStatus, sleEponRuleActionControlTimer, sleEponRuleActionControlTimeStamp, sleEponRuleActionControlReqResult, sleEponRuleActionControlIndex, 
				sleEponRuleActionControlVlanOperate, sleEponRuleActionControlVlanMap, sleEponRuleActionControlEtherType, sleEponRuleActionControlVlanID, sleEponRuleActionControlDiscardOperate, 
				sleEponRuleActionControlDiscardOperateValue, sleEponRuleActionControlCaptureHostOperate, sleEponRuleActionControlCaptureHostFlexibleOperate, sleEponRuleActionControlQueueId, sleEponRuleActionControlQueuependingOperate, 
				sleEponRuleActionControlUnicastLinkDestID, sleEponRuleActionControlUnicastLinkDestOffset, sleEponRuleActionControlMulticastLinkDomID, sleEponRuleActionControlMulticastLinkDomOffset, sleEponRuleActionControlCosOperate, 
				sleEponRuleActionControlCosValue, sleEponRuleActionControlTosOperate, sleEponRuleActionControlTosValue, sleEponRuleActionControlOutputOperate, sleEponRuleActionControlOutputValue, 
				sleEponRuleActionControlOutputVlanContent, sleEponRuleActionControlOutputSourceFiledCopy, sleEponRuleModifyRuleName, sleEponRuleModifyTrafficDirection, sleEponRuleModifyPriorityValue, 
				sleEponRuleModifyCIndex, sleEponRuleModifyAIndex, sleEponRuleModifyControlRequest, sleEponRuleModifyControlStatus, sleEponRuleModifyControlTimer, 
				sleEponRuleModifyControlTimeStamp, sleEponRuleModifyControlReqResult, sleEponRuleModifyControlOltId, sleEponRuleModifyControlRuleName, sleEponRuleModifyControlTrafficDirection, 
				sleEponRuleModifyControlPriorityValue, sleEponRuleModifyControlCIndex, sleEponRuleModifyControlAIndex, sleEponOnuRuleName, sleEponOnuRuleIndex, 
				sleEponOnuRuleDirection, sleEponOnuRulePriority, sleEponOnuRuleDscp, sleEponOnuRuleLinkIndex, sleEponOnuRuleQueueIndex, 
				sleEponOnuRuleControlRequest, sleEponOnuRuleControlStatus, sleEponOnuRuleControlTimer, sleEponOnuRuleControlTimeStamp, sleEponOnuRuleControlReqResult, 
				sleEponOnuRuleControlRuleName, sleEponOnuRuleControlDscp, sleEponOnuRuleControlLinkIndex, sleEponOnuRuleControlQueueIndex, sleEponOltDBAGlobalOltLinkOperate, 
				sleEponOltDBAOverGrantMonConfMonitoringInterval, sleEponOltDBAOverGrantMonConfMaxDBAGrantSize, sleEponOltDBAOverGrantMonConfMinGrantUtilization, sleEponOltDBAOverGrantMonConfLeakyBucketCounterValue, sleEponOltDBAMinShaperBandwidth, 
				sleEponOltDBAMinShaperBurstSize, sleEponOltDBAMinShaperScheduleLevel, sleEponOltDBAMinShaperWeight, sleEponOltDBAMaxShaperBandwidth, sleEponOltDBAMaxShaperBurstSize, 
				sleEponOltDBAMaxShaperScheduleLevel, sleEponOltDBAMaxShaperWeight, sleEponOltDBADBAPollingRateLevel, sleEponOltDBADBAPollingRateRate, eEponOltDBADropDownLevel, 
				sleEponOltDBAShaDropDownWeights, sleEponOltDBADropDownWeights, sleEponOltDBAControlRequest, sleEponOltDBAControlStatus, sleEponOltDBAControlTimer, 
				sleEponOltDBAControlTimeStamp, sleEponOltDBAControlReqResult, sleEponOltDBAControlOltIndex, sleEponOltDBAControlOnuIndex, sleEponOltDBAControlDBAPollingRateLevel, 
				sleEponOltDBAControlDBAPollingRateRate, sleEponOltDBAControlShaDropDownWeightsLevel, sleEponOltDBAControlShaDropDownWeights, sleEponOltDBAControlDropDownWeightsLevel, sleEponOltDBAControlDropDownWeightsl, 
				sleEponOltDBAControlGlobalOltLinkOperate, sleEponOltDBAControlOverGrantMonConfMonitoringInterval, sleEponOltDBAControlOverGrantMonConfMaxDBAGrantSize, sleEponOltDBAControlOverGrantMonConfMinGrantUtilization, sleEponOltDBAControlOverGrantMonConfLeakyBucketCounterValue, 
				sleEponOltDBAControlMinShaperBandwidth, sleEponOltDBAControlMinShaperBurstSize, sleEponOltDBAControlMinShaperScheduleLevel, sleEponOltDBAControlMinShaperWeight, sleEponOltDBAControlMaxShaperBandwidth, 
				sleEponOltDBAControlMaxShaperBurstSize, sleEponOltDBAControlMaxShaperScheduleLevel, sleEponOltDBAControlMaxShaperWeight, sleEponOnuProfileDBAProfileName, sleEponOnuProfileDBALinkSlaMinShaBandwidth, 
				sleEponOnuProfileDBALinkSlaMinShaBurstSize, sleEponOnuProfileDBALinkSlaMinShaSchedulerLevel, sleEponOnuProfileDBALinkSlaMinShaWeight, sleEponOnuProfileDBALinkSlaMaxShaBandwidth, sleEponOnuProfileDBALinkSlaMaxShaBurstSize, 
				sleEponOnuProfileDBALinkSlaMaxShaSchedulerLevel, sleEponOnuProfileDBALinkSlaMaxShaWeight, sleEponOnuProfileDBALinkSlaOperate, sleEponOnuProfileDBALinkSlaPollingLevel, sleEponOnuProfileDBALinkSlaTDMRate, 
				sleEponOnuProfileDBALinkSlaTDMGrantLength, sleEponOnuProfileDBALinkOAMMaxOAMRate, sleEponOnuProfileDBALinkOAMMinOAMRate, sleEponOnuProfileDBAQueueIndex, sleEponOnuProfileDBAQueueSlaDownMinShaBandwidth, 
				sleEponOnuProfileDBAQueueSlaDownMinShaBurstSize, sleEponOnuProfileDBAQueueSlaDownMinShaSchedulerLevel, sleEponOnuProfileDBAQueueSlaDownMinShaWeight, sleEponOnuProfileDBAQueueSlaDownMaxShaBandwidth, sleEponOnuProfileDBAQueueSlaDownMaxShaBurstSize, 
				sleEponOnuProfileDBAQueueSlaDownMaxShaSchedulerLevel, sleEponOnuProfileDBAQueueSlaDownMaxShaWeight, sleEponOnuProfileDBAQueueSlaUpMinShaBandwidth, sleEponOnuProfileDBAQueueSlaUpMinShaBurstSize, sleEponOnuProfileDBAQueueSlaUpMinShaSchedulerLevel, 
				sleEponOnuProfileDBAQueueSlaUpMinShaWeight, sleEponOnuProfileDBAQueueSlaUpMaxShaBandwidth, sleEponOnuProfileDBAQueueSlaUpMaxShaBurstSize, sleEponOnuProfileDBAQueueSlaUpMaxShaSchedulerLevel, sleEponOnuProfileDBAQueueSlaUpMaxShaWeight, 
				sleEponOnuProfileDBAControlRequest, sleEponOnuProfileDBAControlStatus, sleEponOnuProfileDBAControlTimer, sleEponOnuProfileDBAControlTimeStamp, sleEponOnuProfileDBAControlReqResult, 
				sleEponOnuProfileDBAControlProfileName, sleEponOnuProfileDBAControlLinkSlaMinShaBandwidth, sleEponOnuProfileDBAControlLinkSlaMinShaBurstSize, sleEponOnuProfileDBAControlLinkSlaMinShaSchedulerLevel, sleEponOnuProfileDBAControlLinkSlaMinShaWeight, 
				sleEponOnuProfileDBAControlLinkSlaMaxShaBandwidth, sleEponOnuProfileDBAControlLinkSlaMaxShaBurstSize, sleEponOnuProfileDBAControlLinkSlaMaxShaSchedulerLevel, sleEponOnuProfileDBAControlLinkSlaMaxShaWeight, sleEponOnuProfileDBAControlLinkSlaOperate, 
				sleEponOnuProfileDBAControlLinkSlaPollingLevel, sleEponOnuProfileDBAControlLinkSlaTDMRate, sleEponOnuProfileDBAControlLinkSlaTDMGrantLength, sleEponOnuProfileDBAControlQueueIndex, sleEponOnuProfileDBAControlQueueSlaMinShaBandwidth, 
				sleEponOnuProfileDBAControlQueueSlaMinShaBurstSize, sleEponOnuProfileDBAControlQueueSlaMinShaSchedulerLevel, sleEponOnuProfileDBAControlQueueSlaMinShaWeight, sleEponOnuProfileDBAControlQueueSlaMaxShaBandwidth, sleEponOnuProfileDBAControlQueueSlaMaxShaBurstSize, 
				sleEponOnuProfileDBAControlQueueSlaMaxShaSchedulerLevel, sleEponOnuProfileDBAControlQueueSlaMaxShaWeight, sleEponOnuProfileDBAControlQueueSlaOperate, sleEponOnuProfileDBAControlLinkOAMMaxRate, sleEponOnuProfileDBAControlLinkOAMMinRate, 
				sleEponOnuProfileDBAMultiLLidProfileName, sleEponOnuProfileDBAMultiLLidLinkSlaMinShaBandwidth, sleEponOnuProfileDBAMultiLLidLinkSlaMinShaBurstSize, sleEponOnuProfileDBAMultiLLidLinkSlaMinShaSchedulerLevel, sleEponOnuProfileDBAMultiLLidLinkSlaMinShaWeight, 
				sleEponOnuProfileDBAMultiLLidLinkSlaMaxShaBandwidth, sleEponOnuProfileDBAMultiLLidLinkSlaMaxShaBurstSize, sleEponOnuProfileDBAMultiLLidLinkSlaMaxShaSchedulerLevel, sleEponOnuProfileDBAMultiLLidLinkSlaMaxShaWeight, sleEponOnuProfileDBAMultiLLidLinkSlaOperate, 
				sleEponOnuProfileDBAMultiLLidLinkSlaPollingLevel, sleEponOnuProfileDBAMultiLLidLinkSlaTDMRate, sleEponOnuProfileDBAMultiLLidLinkSlaTDMGrantLength, sleEponOnuProfileDBAMultiLLidLinkOAMMaxOAMRate, sleEponOnuProfileDBAMultiLLidLinkOAMMinOAMRate, 
				sleEponOnuProfileDBAMultiLLidQueueIndex, sleEponOnuProfileDBAMultiLLidQueueSlaDownMinShaBandwidth, sleEponOnuProfileDBAMultiLLidQueueSlaDownMinShaBurstSize, sleEponOnuProfileDBAMultiLLidQueueSlaDownMinShaSchedulerLevel, sleEponOnuProfileDBAMultiLLidQueueSlaDownMinShaWeight, 
				sleEponOnuProfileDBAMutiLLidQueueSlaDownMaxShaBandwidth, sleEponOnuProfileDBAMultiLLidQueueSlaDownMaxShaBurstSize, sleEponOnuProfileDBAMultiLLidQueueSlaDownMaxShaSchedulerLevel, sleEponOnuProfileDBAMultiLLidQueueSlaDownMaxShaWeight, sleEponOnuProfileDBAMultiLLidQueueSlaUpMinShaBandwidth, 
				sleEponOnuProfileDBAMultiLLidQueueSlaUpMinShaBurstSize, sleEponOnuProfileDBAMultiLLidQueueSlaUpMinShaSchedulerLevel, sleEponOnuProfileDBAMultiLLidQueueSlaUpMinShaWeight, sleEponOnuProfileDBAMultiLLidQueueSlaUpMaxShaBandwidth, sleEponOnuProfileDBAMultiLLidQueueSlaUpMaxShaBurstSize, 
				sleEponOnuProfileDBAMultiLLidQueueSlaUpMaxShaSchedulerLevel, sleEponOnuProfileDBAMultiLLidQueueSlaUpMaxShaWeight, sleEponOnuProfileDBAMultiLLidControlRequest, sleEponOnuProfileDBAMultiLLidControlStatus, sleEponOnuProfileDBAMultiLLidControlTimer, 
				sleEponOnuProfileDBAMultiLLidControlTimeStamp, sleEponOnuProfileDBAMultiLLidControlReqResult, sleEponOnuProfileDBAMultiLLidControlProfileName, sleEponOnuProfileDBAMultiLLidControlLinkSlaMinShaBandwidth, sleEponOnuProfileDBAMultiLLidControlLinkSlaMinShaBurstSize, 
				sleEponOnuProfileDBAMultiLLidControlLinkSlaMinShaSchedulerLevel, sleEponOnuProfileDBAMultiLLidControlLinkSlaMinShaWeight, sleEponOnuProfileDBAMultiLLidControlLinkSlaMaxShaBandwidth, sleEponOnuProfileDBAMultiLLidControlLinkSlaMaxShaBurstSize, sleEponOnuProfileDBAMultiLLidControlLinkSlaMaxShaSchedulerLevel, 
				sleEponOnuProfileDBAMultiLLidControlLinkSlaMaxShaWeight, sleEponOnuProfileDBAMultiLLidControlLinkSlaOperate, sleEponOnuProfileDBAMultiLLIdControlLinkSlaPollingLevel, sleEponOnuProfileDBAlMultiLLidControLinkSlaTDMRate, sleEponOnuProfileDBAMultiLLidControlLinkSlaTDMGrantLength, 
				sleEponOnuProfileDBAMultiLLidControlQueueIndex, sleEponOnuProfileDBAMultiLLidControlQueueSlaMinShaBandwidth, sleEponOnuProfileDBAMultiLLidControlQueueSlaMinShaBurstSize, sleEponOnuProfileDBAMultiLLidControlQueueSlaMinShaSchedulerLevel, sleEponOnuProfileDBAMultiLLidControlQueueSlaMinShaWeight, 
				sleEponOnuProfileDBAMultiLLidControlQueueSlaMaxShaBandwidth, sleEponOnuProfileDBAMultiLLidControlQueueSlaMaxShaBurstSize, sleEponOnuProfileDBAMultiLLidControlQueueSlaMaxShaSchedulerLevel, sleEponOnuProfileDBAMultiLLidControlQueueSlaMaxShaWeight, sleEponOnuProfileDBAMultiLLIdControlQueueSlaOperate, 
				sleEponOnuProfileDBAMultiLLidControlLinkOAMMaxRate, sleEponOnuProfileDBAMultiLLidControlLinkOAMMinRate, sleEponDomainVlanID, sleEponDomainUnTaggedPorts, sleEponDomainMultiUnTaggedPorts, 
				sleEponDomainControlRequest, sleEponDomainControlStatus, sleEponDomainControlTimer, sleEponDomainControlTimeStamp, sleEponDomainControlReqResult, 
				sleEponDomainControlOltIndex, sleEponDomainControlOnuIndex, sleEponDomainControlVlanID, sleEponDomainControlUnTaggedPorts, sleEponOltRedundancyGroupID, 
				sleEponOltRedundancyTrunkID, sleEponOltRedundancyMasteStatus, sleEponOltRedundancySlave, sleEponOltRedundancySlaveStatus, sleEponOltRedundancyWtrValue, 
				sleEponOltRedundancyRemainTime, sleEponOltRedundancyLastReason, sleEponOltRedundancyHoldOffTime, sleEponOltRedundancyControlRequest, sleEponOltRedundancyControlStatus, 
				sleEponOltRedundancyControlTimer, sleEponOltRedundancyControlTimeStamp, sleEponOltRedundancyControlReqResult, sleEponOltRedundancyControlGroupID, sleEponOltRedundancyControlTrunkID, 
				sleEponOltRedundancyControlMaster, sleEponOltRedundancyControlSlave, sleEponOltRedundancyControlWtrValue, sleEponOltRedundancyControlHoldOffTime, sleEponBaseLGPAuthServer, 
				sleEponBaseLGPAuthMode, sleEponBaseCableDownStatus, sleEponBaseCableDownReferenceCount, sleEponBaseOnuAutoUpgradeVersionMatchStatus, sleEponBaseOltAutoUpgradeVersionMatchStatus, 
				sleEponBaseOltMacAgingTime, sleEponBaseRogueOnuDetectThreshold, sleEponBaseRogueOnuTxPowerOffDuration, sleEponBaseRogueOnuDetectMaxTurnLimit, sleEponBaseControlLGPAuthServer, 
				sleEponBaseControlLGPAuthMode, sleEponBaseControlCableDownStatus, sleEponBaseControlCableDownReferenceCount, sleEponBaseControlOnuAutoUpgradeVersionMatchStatus, sleEponBaseControlOltAutoUpgradeVersionMatchStatus, 
				sleEponBaseControlOltMacAgingTime, sleEponBaseControlRogueOnuDetectThreshold, sleEponBaseControlRogueOnuTxPowerOffDuration, sleEponBaseControlRogueOnuDetectMaxTurnLimit, sleEponOltAdminStatus, 
				sleEponOltMaxDistance, sleEponOltDhcpOption254Status, sleEponOltPonMode, sleEponOltDiscardDlfMode, sleEponOltProtectionMode, 
				sleEponOltDSFecMode, sleEponOltUSFecMode, sleEponOltSfpInsertMode, sleEponOltSfpFaultMode, sleEponOltRogueOnuMac, 
				sleEponOltRogueDetectStatus, sleEponOltMaxOnuCount, sleEponOltActiveOnuCount, sleEponOltInactiveOnuCount, sleEponOltInactiveAgingTime, 
				sleEponOltControlAdminStatus, sleEponOltControlMaxDistance, sleEponOltControlDhcpOption254Status, sleEponOltControlPonMode, sleEponOltControlDiscardDlfMode, 
				sleEponOltControlFecConfigDirection, sleEponOltControlFecConfigStatus, sleEponOltControlInactiveAgingTime, sleEponOltDMIModuleName, sleEponOltDMIThresholdType, 
				sleEponOltDMIThresholdAlarmLow, sleEponOltDMIThresholdAlarmHigh, sleEponOltDMIThresholdWarnLow, sleEponOltDMIThresholdWarnHigh, sleEponOltDMIThresholdControlRequest, 
				sleEponOltDMIThresholdControlStatus, sleEponOltDMIThresholdControlTimer, sleEponOltDMIThresholdControlTimeStamp, sleEponOltDMIThresholdControlReqResult, sleEponOltDMIThresholdControlModuleName, 
				sleEponOltDMIThresholdControlValueType, sleEponOltDMIThresholdControlLowValue, sleEponOltDMIThresholdControlHighValue, sleEponOltSlotIndex, sleEponOltSlotChip1UpgradeStatus, 
				sleEponOltSlotControlRequest, sleEponOltSlotControlStatus, sleEponOltSlotControlTimer, sleEponOltSlotControlTimeStamp, sleEponOltSlotControlReqResult, 
				sleEponOltSlotControlIndex, sleEponOltSlotControlUpgradePath, sleEponOnuPonMode, sleEponOnuFecConfigDirection, sleEponOnuFecConfigStatus, 
				sleEponOnuFWVerInteger, sleEponOnuOltIndex, sleEponOnuMaxHost, sleEponOnuDcVoltage, sleEponOnuBlockStatus, 
				sleEponOnuDistance, sleEponOnuChipId, sleEponOnu10GMpcpRate, sleEponOnu10GMpcpLlid, sleEponOnu10GMpcpDiscover, 
				sleEponOnu10GMpcpUpTunnelID, sleEponOnu10GMpcpDnTunnelID, sleEponOnu10GOAMDiscoverStatus, sleEponOnu10GOAMOUI, sleEponOnu10GOAMFWVersion, 
				sleEponOnu10GOAMProductID, sleEponOnu10GOAMChipID, sleEponOnu10GOAMChipVersion, sleEponOnuRstpBridgePri, sleEponOnuRstpBridgeMode, 
				sleEponOnuRstpRootMaxAge, sleEponOnuRootHelloTime, sleEponOnuRootForwardDelay, sleEponOnuPortsCount, sleEponOnuLoopbackFrameSend, 
				sleEponOnuLoopbackFrameRec, sleEponOnuLoopbackFrameCorrupt, sleEponOnuLoopbackMinDelay, sleEponOnuLoopbackMaxDelay, sleEponOnuLoopbackAvrDelay, 
				sleEponOnuPortAlarm, sleEponOnuControlFecConfigDirection, sleEponOnuControlFecConfigStatus, sleEponOnuControlMacOperation, sleEponOnuControlMaxHost, 
				sleEponOnuControlUpgradeTTY, sleEponOnuControlUpgradeForce, sleEponOnuAutoUpgradeOnuId, sleEponOnuAutoUpgradeOnuMac, sleEponOnuAutoUpgradeStatus, 
				sleEponIopOnuIndex, sleEponIopOnuVendorName, sleEponIopOnuVendorModel, sleEponIopOnuPonMode, sleEponIopOnuControlRequest, 
				sleEponIopOnuControlStatus, sleEponIopOnuControlTimer, sleEponIopOnuControlTimeStamp, sleEponIopOnuControlReqResult, sleEponIopOnuControlVendorName, 
				sleEponIopOnuControlVendorOui, sleEponIopOnuControlModelName, sleEponIopOnuControlMaxPortNum, sleEponIopOnuControlPortSpeed, sleEponIopOnuControlChipVendorName, 
				sleEponIopOnuControlChipVendorID, sleEponIopOnuControlPonMode, sleEponOnuPortConfigEnable, sleEponOnuPortLink, sleEponOnuPortControlConfigEnable, 
				sleEponOnuFdbOnuId, sleEponOnuFdbIPAddress, sleEponOnuIGMPAddress, sleEponProfileMaxHostEnable, sleEponProfileDbaProfile, 
				sleEponProfileOnuListOltID, sleEponProfileOnuListOnuID, sleEponProfileControlMaxHostEnable, sleEponProfileControlDbaName, sleEponProfileVlanControlVlanPort, 
				sleEponProfileVlanControlVlanTagged, sleEponProfileVlanControlVlanPvid, sleEponProfilePortEgressRateLimitMode, sleEponProfilePortControlEgressRateLimitMode, sleEponProfilePortControlRateLimitDirection, 
				sleEponProfileOltServiceProfileName, sleEponProfileOltServiceModelName, sleEponProfileOltServiceRequest, sleEponProfileOltServiceStatus, sleEponProfileOltServiceTimer, 
				sleEponProfileOltServiceTimerStamp, sleEponProfileOltServiceReqResult, sleEponProfileOltServiceOnuModelName, sleEponProfileOltServiceOnuProfileName, sleEponAlarmOpitcalPower, 
				sleEponAlarmOverVoltage, sleEponAlarmControlOpticalPower, sleEponAlarmControlOverVoltage, sleEponStatsOltTxOkBytes64, sleEponStatsOltTxOkFrames64, 
				sleEponStatsOltTxUniFrames64, sleEponStatsOltTxMulFrames64, sleEponStatsOltTxBroFrames64, sleEponStatsOltRxOkBytes64, sleEponStatsOltRxOkFrames64, 
				sleEponStatsOltRxUniFrames64, sleEponStatsOltRxMulFrames64, sleEponStatsOltRxBroFrames64, sleEponStatsOltRxUnderSizeFrames64, sleEponStatsOltRxOverSizeFrames64, 
				sleEponStatsOltPonTxOkBytes64, sleEponStatsOltPonTxOkFrames64, sleEponStatsOltPonTxUniFrames64, sleEponStatsOltPonTxMulFrames64, sleEponStatsOltPonTxBroFrames64, 
				sleEponStatsOltPonTxCrcGen64, sleEponStatsOltPonTxPauseFrames64, sleEponStatsOltPonTxErrBytes64, sleEponStatsOltPonRxOkBytes64, sleEponStatsOltPonRxOkFrames64, 
				sleEponStatsOltPonRxUniFrames64, sleEponStatsOltPonRxMulFrames64, sleEponStatsOltPonRxBroFrames64, sleEponStatsOltPonRxUndersizeFrames64, sleEponStatsOltPonRxOverSizeFrames64, 
				sleEponStatsOltPonRxPauseFrames64, sleEponStatsOltPonRxAlignErrFrames64, sleEponStatsOltPonRxErrBytes64, sleEponStatsOltPonRxCodeErr64, sleEponStatsOnuPortTxOkBytes64, 
				sleEponStatsOnuPortTxOkFrames64, sleEponStatsOnuPortTxUniFrames64, sleEponStatsOnuPortTxMulFrames64, sleEponStatsOnuPortTxBroFrames64, sleEponStatsOnuPortTxPauseFrames64, 
				sleEponStatsOnuPortTxDropBytes64, sleEponStatsOnuPortTxDropFrames64, sleEponStatsOnuPortRxOkBytes64, sleEponStatsOnuPortRxOkFrames64, sleEponStatsOnuPortRxUniFrames64, 
				sleEponStatsOnuPortRxMulFrames64, sleEponStatsOnuPortRxBroFrames64, sleEponStatsOnuPortRxUndersizeFrames64, sleEponStatsOnuPortRxOverSizeFrames64, sleEponStatsOnuPortRxPauseFrames64, 
				sleEponStatsOnuPortRxLengthErrFrames64, sleEponStatsOnuPortRxAlignErrFrames64, sleEponStatsOnuPortRxCrcErrFrames64, sleEponStatsOnuUniTxOkBytes64, sleEponStatsOnuUniTxOkFrames64, 
				sleEponStatsOnuUniTxUniFrames64, sleEponStatsOnuUniTxMulFrames64, sleEponStatsOnuUniTxBroFrames64, sleEponStatsOnuUniTxPauseFrames64, sleEponStatsOnuUniTxDropBytes64, 
				sleEponStatsOnuUniTxDropFrames64, sleEponStatsOnuUniRxOkBytes64, sleEponStatsOnuUniRxOkFrames64, sleEponStatsOnuUniRxUniFrames64, sleEponStatsOnuUniRxMulFrames64, 
				sleEponStatsOnuUniRxBroFrames64, sleEponStatsOnuUniRxUnderSizeFrames64, sleEponStatsOnuUniRxOverSizeFrames64, sleEponStatsOnuUniRxPauseFrames64, sleEponStatsOnuUniRxLengthErrFrames64, 
				sleEponStatsOnuUniRxAlignErrFrames64, sleEponStatsOnuUniRxCrcErrFrames64, sleEponStatsOnuPonTxOkBytes64, sleEponStatsOnuPonTxOkFrames64, sleEponStatsOnuPonTxUniFrames64, 
				sleEponStatsOnuPonTxMulFrames64, sleEponStatsOnuPonTxBroFrames64, sleEponStatsOnuPonTxDropBytes64, sleEponStatsOnuPonTxUnusedBytes64, sleEponStatsOnuPonTxLaserPower64, 
				sleEponStatsOnuPonTxLaserVcc64, sleEponStatsOnuPonTxLaserBias64, sleEponStatsOnuPonTxLaserTemp64, sleEponStatsOnuPonRxOkBytes64, sleEponStatsOnuPonRxOkFrames64, 
				sleEponStatsOnuPonRxUniFrames64, sleEponStatsOnuPonRxMulFrames64, sleEponStatsOnuPonRxBroFrames64, sleEponStatsOnuPonRxUnderSizeFrames64, sleEponStatsOnuPonFcsErrFrames64, 
				sleEponStatsOnuPonRxCrc8ErrFrames64, sleEponStatsOnuPonRxDropFrames64, sleEponStatsOnuPonRxDelayedBytes64, sleEponStatsOnuPonRxDelayMax64, sleEponStatsOnuPonRxDelayThresh64, 
				sleEponStatsOnuPonRxErrFrames64, sleEponStatsOnuPonRxLaserPower64, sleEponOnuFirmwareVender, sleEponOnuFirmwareChip, sleEponOnuFirmwareMaxPort, 
				sleEponOnuFirmwareMajor, sleEponOnuFirmwareMinor, sleEponOnuFirmwareBuild, sleEponOnuFirmwareFileName, sleEponOnuRuleProfileName, 
				sleEponRuleOnuProfilePolicyCount, sleEponRuleOnuProfileRefCount, sleEponOnuRuleRefProfileNameList, sleEponOnuRulePolicyIndex, sleEponOnuRulePolicyDirection, 
				sleEponOnuRulePolicyPriority, sleEponOnuRulePolicyFlowCount, sleEponOnuRulePolicyFlowString, sleEponOnuRulePolicyActionCount, sleEponOnuRulePolicyActionString, 
				sleEponOnuRuleProfileControlRequest, sleEponOnuRuleProfileControlStatus, sleEponOnuRuleProfileControlTimer, sleEponOnuRuleProfileControlTimeStamp, sleEponOnuRuleProfileControlReqResult, 
				sleEponOnuRuleProfileControlName, sleEponOnuRuleProfileControlPolicyIndex, sleEponOnuRuleProfileControlPolicyDirection, sleEponOnuRuleProfileControlPolicyPriority, sleEponOnuRuleProfileControlPolicyFlowList, 
				sleEponOnuRuleProfileControlPolicyActionList, sleEponOnuRuleFlowIndex, sleEponOnuRuleFlowType, sleEponOnuRuleFlowRefCount, sleEponOnuRuleFlowOP, 
				sleEponOnuRuleFlowEthType, sleEponOnuRuleFlowPort, sleEponOnuRuleFlowMacAddress, sleEponOnuRuleFlowIpAddress, sleEponOnuRuleFlowMacMask, 
				sleEponOnuRuleFlowIpMask, sleEponOnuRuleFlowControlRequest, sleEponOnuRuleFlowControlStatus, sleEponOnuRuleFlowControlTimer, sleEponOnuRuleFlowControlTimeStamp, 
				sleEponOnuRuleFlowControlReqResult, sleEponOnuRuleFlowControlIndex, sleEponOnuRuleFlowControlType, sleEponOnuRuleFlowControlOP, sleEponOnuRuleFlowControlEthType, 
				sleEponOnuRuleFlowControlPort, sleEponOnuRuleFlowControlMacAddress, sleEponOnuRuleFlowControlIpAddress, sleEponOnuRuleFlowControlMacMask, sleEponOnuRuleFlowControlIpMask, 
				sleEponOnuRuleActionIndex, sleEponOnuRuleActionType, sleEponOnuRuleActionRefCount, sleEponOnuRuleActionControlRequest, sleEponOnuRuleActionControlStatus, 
				sleEponOnuRuleActionControlTimer, sleEponOnuRuleActionControlTimeStamp, sleEponOnuRuleActionControlReqResult, sleEponOnuRuleActionControlIndex, sleEponOnuRuleActionControlType, 
				selEponOltDBAControlDirection, sleEponOnuProfileDBAControlReport, sleEponOnuProfileDBAControlDirection, sleEponOnuProfileDBAControlIngressEgress, sleEponOltRedundancyMasterAdminStatus, 
				sleEponOltRedundancySlaveAdminStatus, sleEponOltRedundancyStandbyRxSignal, sleEponOltRedundancyTriggerLos, sleEponOltRedundancyTriggerManual, sleEponOltRedundancyTriggerSlot, 
				sleEponOltRedundancyTriggerEponMac, sleEponOltRedundancyControlOltType, sleEponOltRedundancyControlSwitchOver, sleEponOltRedundancyControlTriggerMask, sleEponOltRedundancyControlTriggerMode, 
				sleEponOltSlotChip0UpgradeStatus, sleEponOltSlotConnectionFlag, sleEponOltSlotStatus, sleEponOltSlotNOSVer, sleEponOltSlotType, 
				sleEponBaseRogueOnuDetectShutdownStartThreshold, sleEponBaseRogueOnuDetectShutdownInterval, sleEponBaseRogueOnuDetectverify, sleEponBaseOnuDailyRxPowerThresholdCount, sleEponBaseOnuDailyRxPowerThresholdDBM, 
				sleEponBaseOnuDailyRxPowerThresholdChecktime, sleEponBaseOnuDailyRxPowerThresholdSerious, sleEponBaseControlRogueOnuDetectShutdownStartThreshold, sleEponBaseControlRogueOnuDetectShutdownInterval, sleEponBaseControlRogueOnuDetectverify, 
				sleEponBaseControlOnuDailyRxPowerThresholdCount, sleEponBaseControlOnuDailyRxPowerThresholdDBM, sleEponBaseControlOnuDailyRxPowerThresholdChecktime, sleEponBaseControlOnuDailyRxPowerThresholdSerious, sleEponOltDMIThresholdPortRxPowerAlarmLow, 
				sleEponOltDMIThresholdPortRxPowerAlarmHigh, sleEponOltDMIThresholdPortRxPowerWarnLow, sleEponOltDMIThresholdPortRxPowerWarnHigh, sleEponOltDMIThresholdPortControlRequest, sleEponOltDMIThresholdPortControlStatus, 
				sleEponOltDMIThresholdPortControlTimer, sleEponOltDMIThresholdPortControlTimeStamp, sleEponOltDMIThresholdPortControlReqResult, sleEponOltDMIThresholdPortControlOltIndex, sleEponOltDMIThresholdPortControlType, 
				sleEponOltDMIThresholdPortControlMode, sleEponOltDMIThresholdPortControlLowValue, sleEponOltDMIThresholdPortControlHighValue, sleEponOnuThresholdMacAddress, sleEponOnuThresholdCrcUpCount, 
				sleEponOnuThresholdCrcDownCount, sleEponOnuThresholdCrcUpDownCount, sleEponOnuThresholdCrcRaisedCount, sleEponOnuThresholdCrcReleasedCount, sleEponOnuThresholdRegisteredEventCount, 
				sleEponOnuThresholdRegisteredAlarmCount, sleEponOnuThresholdRegisteredFirstEventTime, sleEponOnuThresholdRegisteredLastEventTime, sleEponOnuThresholdRegisteredDuration, sleEponOnuThresholdOpticPowerEventCount, 
				sleEponOnuThresholdOpticPowerAlarmCount, sleEponOnuThresholdOpticPowerFirstEventTime, sleEponOnuThresholdOpticPowerLastEventTime, sleEponOnuThresholdOpticPowerDuration, sleEponOnuThresholdDcVoltateEventCount, 
				sleEponOnuThresholdDcVoltateAlarmCount, sleEponOnuThresholdDcVoltateFirstEventTime, sleEponOnuThresholdDcVoltateLastEventTime, sleEponOnuThresholdDcVoltateDuration, sleEponOnuThresholdLoopingEventCount, 
				sleEponOnuThresholdLoopingAlarmCount, sleEponOnuThresholdLoopingFirstEventTime, sleEponOnuThresholdLoopingLastEventTime, sleEponOnuThresholdLoopingDuration, sleEponOnuThresholdCrcValue, 
				sleEponOnuThresholdCrcCheckInterval, sleEponOnuThresholdRegisterValue, sleEponOnuThresholdRegisterCheckInterval, sleEponOnuThresholdOpticPowerValue, sleEponOnuThresholdOpticPowerCheckInterval, 
				sleEponOnuThresholdDcVoltageValue, sleEponOnuThresholdDcVoltageCheckInterval, sleEponOnuThresholdLoopingValue, sleEponOnuThresholdLoopingCheckInterval, sleEponOnuThresholdControlRequest, 
				sleEponOnuThresholdControlStatus, sleEponOnuThresholdControlTimer, sleEponOnuThresholdControlTimeStamp, sleEponOnuThresholdControlReqResult, sleEponOnuThresholdControlType, 
				sleEponOnuThresholdControlValue, sleEponOnuThresholdControlCheckInterval, sleEponStatsOnuPortSumTxOkBytes64, sleEponStatsOnuPortSumTxUniFrames64, sleEponStatsOnuPortSumTxMulFrames64, 
				sleEponStatsOnuPortSumTxBroFrames64, sleEponStatsOnuPortSumRxOkBytes64, sleEponStatsOnuPortSumRxUniFrames64, sleEponStatsOnuPortSumRxMulFrames64, sleEponStatsOnuPortSumRxBroFrames64, 
				sleEponOnuModelName, sleEponOnuProfilePortIndex, sleEponProfileOnuPortAdminStatus, sleEponOnuProfilePortMaxHost, sleEponOnuProfileUniPortMaxHost, 
				sleEponOnuProfilePortIngressRateLimitMode, sleEponOnuProfilePortIngressRateLimit, sleEponOnuProfilePortEgressRateLimit, sleEponOnuProfilePortControlRequest, sleEponOnuProfilePortControlStatus, 
				sleEponOnuProfilePortControlTimer, sleEponOnuProfilePortControlTimeStamp, sleEponOnuProfilePortControlReqResult, sleEponOnuProfilePortControlOltIndex, sleEponOnuProfilePortControlOnuIndex, 
				sleEponOnuProfilePortControlPortIndex, sleEponOnuProfilePortControlAdminStatus, sleEponOnuProfilePortControlMaxHost, sleEponOnuProfileUniPortControlMaxHost, sleEponOnuProfilePortControlIngressRateLimitMode, 
				sleEponOnuProfilePortControlIngressRateLimit, sleEponOnuProfilePortControlEgressRateLimit, sleEponOltRedundancyChagneStatus, sleEponStatsOnuLlidIndex, sleEponStatsOnuLlidTxOkBytes64, 
				sleEponStatsOnuLlidTxOkFrames64, sleEponStatsOnuLlidTxUniFrames64, sleEponStatsOnuLlidTxMulFrames64, sleEponStatsOnuLlidTxBroFrames64, sleEponStatsOnuLlidTxTx64Byte64, 
				sleEponStatsOnuLlidTxTx65To127Byte64, sleEponStatsOnuLlidTxTx128To255Byte64, sleEponStatsOnuLlidTxTx256To511Byte64, sleEponStatsOnuLlidTxTx512To1023Byte64, sleEponStatsOnuLlidTxTx1024To1518Byte64, 
				sleEponStatsOnuLlidTxGreater1518Byte64, sleEponStatsOnuLlidTxDropBytes64, sleEponStatsOnuLlidTxDropFrames64, sleEponStatsOnuLlidTxDelayedBytes64, sleEponStatsOnuLlidTxDelayMax64, 
				sleEponStatsOnuLlidTxDelayThresh64, sleEponStatsOnuLlidTxUnusedBytes64, sleEponStatsOnuLlidTxOamFrames64, sleEponStatsOnuLlidTxErrFrames64, sleEponStatsOnuLlidTxMpcpReports64, 
				sleEponStatsOnuLlidTxMpcpRequests64, sleEponStatsOnuLlidTxMpcpRegAck64, sleEponStatsOnuLlidRxOkBytes64, sleEponStatsOnuLlidRxOkFrames64, sleEponStatsOnuLlidRxUniFrames64, 
				sleEponStatsOnuLlidRxMulFrames64, sleEponStatsOnuLlidRxBroFrames64, sleEponStatsOnuLlidRxRx64Byte64, sleEponStatsOnuLlidRxRx65To127Byte64, sleEponStatsOnuLlidRxRx128To255Byte64, 
				sleEponStatsOnuLlidRxRx256To511Byte64, sleEponStatsOnuLlidRxRx512To1023Byte64, sleEponStatsOnuLlidRxRx1024To1518Byte64, sleEponStatsOnuLlidRxGreater1518Byte64, sleEponStatsOnuLlidRxUnderSizeFrames64, 
				sleEponStatsOnuLlidRxFcsErrFrames64, sleEponStatsOnuLlidRxDropBytes64, sleEponStatsOnuLlidRxDropFrames64, sleEponStatsOnuLlidRxDelayedBytes64, sleEponStatsOnuLlidRxDelayMax64, 
				sleEponStatsOnuLlidRxDelayThresh64, sleEponStatsOnuLlidRxOamFrames64, sleEponStatsOnuLlidRxErrFrames64, sleEponStatsOnuLlidRxErrFramePeriod64, sleEponStatsOnuLlidRxErrFrameSummary64, 
				sleEponStatsOnuLlidRxMpcpGates64, sleEponStatsOnuLlidRxMpcpRegister64, sleEponStatsOnuLlidRxLineCodeErr64, sleEponStatsOltFromOnuOutHostFrame, sleEponStatsOltFromOnuPolicerDropP2PFrame, 
				sleEponStatsOltFromOnuAccessCtrlDropP2PFrame, sleEponStatsOltFromOnuTxbuffFullDropP2PFrame, sleEponStatsOltFromOnuInHostFrame, sleEponStatsOltFromOnuInErrorBytes, sleEponStatsOltFromOnuInP2PFrame, 
				sleEponStatsOltFromOnuOutUniFrame, sleEponStatsOltFromOnuOutPolicerDroppedFrame, sleEponStatsOltFromOnuOutMismatchDroppedFrame, sleEponOnuUserMacControlReqResult, sleEponOnuUserMacControlOltIndex, 
				sleEponOnuUserMacControlOnuIndex, sleEponOnuUserMacControlStaticMac, sleEponStatsOltFromOnuInUsedBytes, sleEponStatsOltFromOnuInGoodBytes, sleEponOnuUserUniDynamicMacAddress, 
				sleEponOnuUserUniStaticMacAddress, sleEponOnuUserMacControlRequest, sleEponOnuUserMacControlStatus, sleEponOnuUserMacControlTimer, sleEponOnuUserMacControlTimeStamp, 
				sleEponOnuClassificationL3Mask, sleEponOnuClassificationCos, sleEponOnuClassificationVid, sleEponOnuClassificationControlL3Mask, sleEponOnuClassificationControlCos, 
				sleEponOnuClassificationControlVid, sleEponProfileControlStormControlUnknownUnicast, sleEponProfileControlStormControlMulticast, sleEponProfileControlStormControlBroadcast, sleEponProfileControlStormControlEnable, 
				sleEponProfileStormControlUnknownUnicast, sleEponProfileStormControlMulticast, sleEponProfileStormControlBroadcast, sleEponProfileStormControlEnable, sleEponOnuControlStormControlUnknownUnicast, 
				sleEponOnuControlStormControlMulticast, sleEponOnuControlStormControlBroadcast, sleEponOnuControlStormControlEnable, sleEponOnuStormControlUnknownUnicast, sleEponOnuStormControlMulticast, 
				sleEponOnuStormControlBroadcast, sleEponOnuStormControlEnable, sleEponOnuThresholdRegisteredCount, sleEponOnuAuthOltIndex, sleEponOnuAuthOnuIndex, 
				sleEponOnuAuthMac, sleEponOnuAuthId, sleEponOnuAuthPw, sleEponOnuAuthControlRequest, sleEponOnuAuthControlStatus, 
				sleEponOnuAuthControlTimer, sleEponOnuAuthControlTimeStamp, sleEponOnuAuthControlReqResult, sleEponOnuAuthControlOltIndex, sleEponOnuAuthControlOnuIndex, 
				sleEponOnuAuthControlMac, sleEponOnuAuthControlId, sleEponOnuAuthControlPw, sleEponOnuLlidIndex, sleEponOnuDistanceInitial, 
				sleEponOnuDistanceDiff, sleEponProfileExtendMtu, sleEponOnuTxPowerOffTimer, sleEponOltRedundancyMaster, sleEponOnuRegisterTime
				 }
			STATUS current
			DESCRIPTION 
				"Description."
			::= { sleEpon 17 }

		
		sleEponNotificationGroup NOTIFICATION-GROUP
			NOTIFICATIONS { sleEponOltRegModeChanged, sleEponOnuRegModeChanged, sleEponOnuStatusChanged, sleEponOnuRegistered, sleEponOnuUpgraded, 
				sleEponProfileCreated, sleEponProfileDestroyed, sleEponstatsOltCleared, sleEponStatsOltChannelCleared, sleEponAlarmProfileChanged, 
				sleEponOnuDeregistered, sleEponOnuProfileChanged, sleEponOnuLoopbackProvisioned, sleEponOltProfileChanged, sleEponStatsAllCleared, 
				sleEponProfileVlanCreated, sleEponProfileVlanDestroyed, sleEponProfileVlanProfileChanged, sleEponProfilePortAdminStatusChanged, sleEponProfilePortNegoChanged, 
				sleEponProfilePortSpeedChanged, sleEponProfilePortMaxHostChanged, sleEponProfilePortPvidChanged, sleEponProfilePortRateLimitChanged, sleEponOnuPortReset, 
				sleEponOnuClassificationCreated, sleEponOnuClassificationDestroyed, sleEponProfileClassificationCreated, sleEponProfileClassificationDestroyed, sleEponOltSCChanged, 
				sleEponOltUpgraded, sleEponOltReset, sleEponOnuTxPowerOffChanged, sleEponOnuFdbMacCleared, sleEponProfileExtendMtuChanged, 
				sleEponProfileIgmpChanged, sleEponProfileSTPChanged, sleEponProfileQueueModifyQueueLimit, sleEponProfilePortFlowControlChanged, sleEponVlanOltVlanPrefixChanged, 
				sleEponVlanOltVlanProfileChanged, sleEponProfileDefaultProfileCreated, sleEponProfileUNIQueueModifyQueuePolicy, sleEponPTimeStatsCleared, sleEponPTimeStatsServiceActivityChanged, 
				sleEponOnuSubscriberHistoryOltCleared, sleEponOnuSubscriberHistroyOnuCleared, sleEponProfileQueueModifyQueuePolicy, sleEponOltAttributesChanged, sleEponOnuAttibutesChanged, 
				sleEponProfileModified, sleEponProfilePortDuplexChanged, sleEponProfileLoopDetectChanged, sleEponBaseDefaultBandwidthChanged, sleEponBaseDefaultMaxHost, 
				sleEponVlanOnuVlanProfileChanged, sleEponFirmwareUpgradeProfileChanged, sleEponFirmwareDeleted, sleEponOnuSipGlobalConfigDestroyed, sleEponProfileSipConfigChanged, 
				sleEponProfileModemConfigChanged, sleEponOnuSipUserConfigDestroyed, sleEponBaseOnuAgingTimeChanged, sleEponBaseAlarmStatusChanged, sleEponBaseAlarmModeChanged, 
				sleEponOltRssiStatusChanged, sleEponOltP2PAccessControlChanged, sleEponOnuFristRegisteredOnAutoToManual, sleEponOnuProfileChangedByMac, sleEponOnuDeregisteredByMac, 
				sleEponOnuLgpauthStatusChanged, sleEponOnuSipGlobalConfigIpChanged, sleEponOnuSipGlobalConfigDhcpChanged, sleEponOnuSipGlobalConfigPPPoEChanged, sleEponOnuPingTest, 
				sleEponOnuLoopDectectUnblock, setEponOnuOltRssiOnuSingle, sleEponOnuDBAMultiLLidLink, sleEponOnuDMIMonitorThresholdChanged, sleEponProfileDHCPChanged, 
				sleEponProfileModemMacLearnChanged, sleEponProfileIgmpSnoopingChanged, sleEponProfileOnuRuleChanged, sleEponProfilePortIsolationChanged, sleEponAlarmChanged, 
				sleEponRuleClauseQueueChanged, sleEponRuleClauseLayer2Changed, sleEponRuleClauseVlanChanged, sleEponRuleClauseLayer3Changed, sleEponRuleClauseTcpUdpChanged, 
				sleEponRuleClauseProtocolChanged, sleEponRuleClauseLinkIndexChanged, sleEponRuleClauseDel, sleEponRuleActionVlanChanged, sleEponRuleActionDiscardChanged, 
				sleEponRuleActionCaptureHostChanged, sleEponRuleActionCaptureHostFlexibleChanged, sleEponRuleActionQueueChanged, sleEponRuleActionUnicastLinkChanged, sleEponRuleActionMulticastLinkChanged, 
				sleEponRuleActionNoOperation, sleEponRuleActionCosChanged, sleEponRuleActionTosChanged, sleEponRuleActionOutputChanged, sleEponRuleActionQueuePendingChanged, 
				sleEponRuleActionSleChanged, sleEponRuleActionNoRuleAction, sleEponRuleOltRuleCreate, sleEponRuleModifyPriorityChange, sleEponRuleModifyTrafficDirChange, 
				sleEponRuleModifyClauseAdd, sleEponRuleModifyActionAdd, sleEponRuleModifyClauseDel, sleEponRuleModifyActionDel, sleEponRuleOltRuleDelete, 
				sleEponRuleOltRuleAddApply, sleEponRuleOltRuleDelApply, sleEponOnuRuleChanged, sleEponOLtDBAShaperDropDownWeightsChanged, sleEponOLtDBADropDownWeightsChanged, 
				sleEponOltDBALinkChanged, sleEponOLtDBADGlobalOltLinkChanged, sleEponOLtDBADOverGrantMonConfChanged, sleEponOltDBAPollingRateChanged, sleEponOltDBAMultiQueueSlaChanged, 
				sleEponOnuProfileDBALinkSlaChanged, sleEponOnuProfileDBAQueueSlaChanged, sleEponOnuProfileDBALinkOAMRateChanged, sleEponOnuProfileDBAMultiLLidLinkSlaChanged, sleEponOnuProfileDBAMultiLLidQueueSlaChanged, 
				sleEponOnuProfileDBAMultiLLidLinkOAMRateChanged, sleEponDomainVlanCreate, sleEponDomainDestroyVlan, sleEponDomainVlanAdd, sleEponDomainDefaultVlanAdd, 
				sleEponDomainVlanDel, sleEponDomainDefaultVlanDel, sleEponDomainVlanMultiAdd, sleEponDomainDefaultVlanMultiAdd, sleEponDomainVlanMultiDel, 
				sleEponDomainDefaultVlanMultiDel, sleEponOltRedundancyChanged, sleEponOltRedundancySwitchoverForceGroup, sleEponOltRedundancyHoldOffTimeChanged, sleEponProfileSubscriberChanged, 
				sleEponBaseOnuAutoUpgradeChanged, sleEponBaseCableDownStatusChanged, sleEponBaseCableDownReferenceCountChanged, sleEponBaseOnuAutoUpgradeVersionMatchChanged, sleEponBaseOltAutoUpgradeVersionMatchChanged, 
				sleEponBaseOltMacAgingTimeChanged, sleEponBaseOltMacAgingTimeGlobalReset, sleEponBaseRogueOnuDetectThresholdChanged, sleEponBaseNoRogueOnuDetectThreshold, sleEponBaseRogueOnuTxPowerOffDurationChanged, 
				sleEponBaseNoRogueOnuTxPowerOffDuration, sleEponBaseRogueOnuDetectMaxTurnLimitChanged, sleEponBaseNoRogueOnuDetectMaxTurnLimit, sleEponOltMaxDistanceChanged, sleEponOltDhcpOpt254Changed, 
				sleEponOltPonModeChanged, sleEponOltDiscardDlfModeChanged, sleEponOltFecConfigChanged, sleEponOltInactiveAgingTimeChanged, sleEponOltDMIThresholdChanged, 
				sleEponOltSlotFWUpgrade, sleEponOnuFecChanged, sleEponOnuMacChanged, sleEponOnuRebootHybridOnu, sleEponOnuRestoreOnu, 
				sleEponOnuSetMaxHost, sleEponOnuFix, sleEponIopOnuAdd, sleEponIopOnuDel, sleEponOnuPortEnableChanged, 
				sleEponProfileMaxHostChanged, sleEponProfileDBAChanged, sleEponProfilePortUnsetRatelimitChanged, sleEponProfileOltServiceDefaultChanged, sleEponProfileOltServiceModelChanged, 
				sleEponOnuRuleProfileChanged, sleEponOnuRuleFlowChanged, sleEponOnuRuleActionChanged, sleEponOltRedundancyDbsyncCheckChanged, sleEponOltRedundancyDbResyncChanged, 
				sleEponOltRedundancyTriggerChanged, sleEponBaseOnuDailyRxPowerThreshold, sleEponOltDMIThresholdPortChanged, sleEponOnuThresholdChanged, sleEponBaseRogueOnuDetectShutdownStartThresholdChanged, 
				sleEponBaseNoRogueOnuDetectShutdownStartThreshold, sleEponBaseRogueOnuDetectShutdownIntervalChanged, sleEponBaseNoRogueOnuDetectShutdownInterval, sleEponBaseRogueOnuDetectVerifyChanged, sleEponBaseNoRogueOnuDetectVerify, 
				sleEponOnuProfilePortAdminStatusChanged, sleEponOnuProfilePortMaxHostChanged, sleEponOnuProfileUniPortMaxHostChanged, sleEponOnuProfilePortIngressRateLimitChanged, sleEponOnuProfilePortEgressRateLimitChanged, 
				sleEponOnuProfilePorResetOnuPortStatus, sleEponOnuUserMacStaticMacSet, sleEponOnuUserMacStaticMacCleared, sleEponOnuUserMacDynamicMacCleared, sleEponOltSignalCheckStatusChanged, 
				sleEponOltPonMacReset, sleEponOnuSipUserConfigChanged, sleEponOltAdminStatusChanged, sleEponOnuAuthChanged, sleEponOnuAuthDeleted, 
				sleEponProfileStormControlChanged, sleEponOnuStormControlConfigChanged }
			STATUS current
			DESCRIPTION 
				"Description."
			::= { sleEpon 18 }

		
	
	END

--
-- sle-epon-mib.mib
--
