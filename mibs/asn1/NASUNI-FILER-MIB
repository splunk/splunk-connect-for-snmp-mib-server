NASUNI-FILER-MIB DEFINITIONS ::= BEGIN

------------------------------------------------------------------------
-- Nasuni Filer MIB object definitions
-- Copyright (c) 2010-2013 Nasuni Corporation, all rights reserved
------------------------------------------------------------------------

-- Imports
IMPORTS
    MODULE-IDENTITY, OBJECT-TYPE, NOTIFICATION-TYPE,
    enterprises, Counter64, Integer32, TimeTicks
        FROM SNMPv2-SMI
    DisplayString
        FROM SNMPv2-TC;

-- Module Identification
nasuni MODULE-IDENTITY
    LAST-UPDATED  "201307130000Z"
    ORGANIZATION  "Nasuni Corporation"
    CONTACT-INFO  "support@nasuni.com"
    DESCRIPTION   "Nasuni Filer MIB object definitions"
    REVISION      "201307130000Z"
    DESCRIPTION   "First Revision"
    ::= { enterprises 42040 }


------------------------------------------------------------------------
-- Filer Stats (.1)
------------------------------------------------------------------------

filer  OBJECT IDENTIFIER ::= { nasuni 1 }

filerIdentifier OBJECT-TYPE
    SYNTAX       DisplayString
    MAX-ACCESS   read-only
    STATUS       current
    DESCRIPTION  "Identity of this management system."
    DEFVAL       { "Nasuni Filer" }
    ::= { filer 1 }

filerVersion OBJECT-TYPE
    SYNTAX       DisplayString
    MAX-ACCESS   read-only
    STATUS       current
    DESCRIPTION  "Current Filer version"
    ::= { filer 2 }

filerSerialNumber OBJECT-TYPE
    SYNTAX       DisplayString
    MAX-ACCESS   read-only
    STATUS       current
    DESCRIPTION  "Current Filer version"
    ::= { filer 3 }

filerUptime OBJECT-TYPE
    SYNTAX       TimeTicks
    MAX-ACCESS   read-only
    STATUS       current
    DESCRIPTION  "Current uptime of the Filer"
    ::= { filer 4 }

filerUpdateAvailable OBJECT-TYPE
    SYNTAX       DisplayString
    MAX-ACCESS   read-only
    STATUS       current
    DESCRIPTION  "Blank if no updates available, otherwise the version of the update."
    ::= { filer 5 }

filerTotalUnprotectedData OBJECT-TYPE
    SYNTAX       Counter64
    UNITS        "bytes"
    MAX-ACCESS   read-only
    STATUS       current
    DESCRIPTION  "Total data not yet protected."
    ::= { filer 6 }

filerPushesCompleted OBJECT-TYPE
    SYNTAX       Counter64
    MAX-ACCESS   read-only
    STATUS       current
    DESCRIPTION  "Total number of pushes to the cloud"
    ::= { filer 7 }

filerTotalPushed OBJECT-TYPE
    SYNTAX       Counter64
    UNITS        "bytes"
    MAX-ACCESS   read-only
    STATUS       current
    DESCRIPTION  "Total compressed bytes pushed to the cloud"
    ::= { filer 8 }

filerTotalRead OBJECT-TYPE
    SYNTAX       Counter64
    UNITS        "bytes"
    MAX-ACCESS   read-only
    STATUS       current
    DESCRIPTION  "Total bytes read from the cloud"
    ::= { filer 9 }

filerOpensForRead OBJECT-TYPE
    SYNTAX       Counter64
    MAX-ACCESS   read-only
    STATUS       current
    DESCRIPTION  "Total number of opens for read"
    ::= { filer 10 }

filerOpensForWrite OBJECT-TYPE
    SYNTAX       Counter64
    MAX-ACCESS   read-only
    STATUS       current
    DESCRIPTION  "Total number of opens for write"
    ::= { filer 11 }

filerMergeConflicts OBJECT-TYPE
    SYNTAX       Counter64
    MAX-ACCESS   read-only
    STATUS       current
    DESCRIPTION  "Total number of merge conflicts"
    ::= { filer 12 }

filerReadHits OBJECT-TYPE
    SYNTAX       Counter64
    MAX-ACCESS   read-only
    STATUS       current
    DESCRIPTION  "Total read cache hits"
    ::= { filer 13 }

filerReadMisses OBJECT-TYPE
    SYNTAX       Counter64
    MAX-ACCESS   read-only
    STATUS       current
    DESCRIPTION  "Total read cache misses"
    ::= { filer 14 }

filerNextFsckAfter OBJECT-TYPE
    SYNTAX       DisplayString
    MAX-ACCESS   read-only
    STATUS       current
    DESCRIPTION  "Date for the next scheduled fsck"
    ::= { filer 15 }


------------------------------------------------------------------------
-- Cache Stats (.1.100)
------------------------------------------------------------------------

filerCache  OBJECT IDENTIFIER ::= { filer 100 }

filerCacheTotal OBJECT-TYPE
    SYNTAX       Counter64
    UNITS        "bytes"
    MAX-ACCESS   read-only
    STATUS       current
    DESCRIPTION  "Total available disk cache available"
    ::= { filerCache 1 }

filerCacheUsed OBJECT-TYPE
    SYNTAX       Counter64
    UNITS        "bytes"
    MAX-ACCESS   read-only
    STATUS       current
    DESCRIPTION  "Current used disk cache"
    ::= { filerCache 2 }

filerCacheFree OBJECT-TYPE
    SYNTAX       Counter64
    UNITS        "bytes"
    MAX-ACCESS   read-only
    STATUS       current
    DESCRIPTION  "Current free disk cache"
    ::= { filerCache 3 }


------------------------------------------------------------------------
-- Platform Stats (.1.101)
------------------------------------------------------------------------

filerPlatform  OBJECT IDENTIFIER ::= { filer 101 }

filerPlatformName OBJECT-TYPE
    SYNTAX       DisplayString
    MAX-ACCESS   read-only
    STATUS       current
    DESCRIPTION  "Filer platform name"
    ::= { filerPlatform 1 }

filerPlatformType OBJECT-TYPE
    SYNTAX       DisplayString
    MAX-ACCESS   read-only
    STATUS       current
    DESCRIPTION  "Filer platform type"
    ::= { filerPlatform 2 }

filerPackageFormat OBJECT-TYPE
    SYNTAX       DisplayString
    MAX-ACCESS   read-only
    STATUS       current
    DESCRIPTION  "Filer package format"
    ::= { filerPlatform 3 }

filerBiosVersion OBJECT-TYPE
    SYNTAX       DisplayString
    MAX-ACCESS   read-only
    STATUS       current
    DESCRIPTION  "Current bios version"
    ::= { filerPlatform 4 }

filerCpuModel OBJECT-TYPE
    SYNTAX       DisplayString
    MAX-ACCESS   read-only
    STATUS       current
    DESCRIPTION  "CPU model long description"
    ::= { filerPlatform 5 }

filerPhysCpuCount OBJECT-TYPE
    SYNTAX       Integer32
    MAX-ACCESS   read-only
    STATUS       current
    DESCRIPTION  "Number of physical CPUs in the Filer"
    ::= { filerPlatform 6 }

filerCoreCount OBJECT-TYPE
    SYNTAX       Integer32
    MAX-ACCESS   read-only
    STATUS       current
    DESCRIPTION  "Number of cores per physical CPU"
    ::= { filerPlatform 7 }

filerCpuArch OBJECT-TYPE
    SYNTAX       DisplayString
    MAX-ACCESS   read-only
    STATUS       current
    DESCRIPTION  "CPU architecture"
    ::= { filerPlatform 8 }

filerCpuFreq OBJECT-TYPE
    SYNTAX       Counter64
    UNITS        "hertz"
    MAX-ACCESS   read-only
    STATUS       current
    DESCRIPTION  "CPU frequency"
    ::= { filerPlatform 9 }

filerDiskCount OBJECT-TYPE
    SYNTAX       Integer32
    MAX-ACCESS   read-only
    STATUS       current
    DESCRIPTION  "Number of disks in the Filer"
    ::= { filerPlatform 10 }

filerTotalMemory OBJECT-TYPE
    SYNTAX       Counter64
    UNITS        "bytes"
    MAX-ACCESS   read-only
    STATUS       current
    DESCRIPTION  "Total amount of memory in the Filer"
    ::= { filerPlatform 11 }

filerDeviceCache OBJECT-TYPE
    SYNTAX       DisplayString
    MAX-ACCESS   read-only
    STATUS       current
    DESCRIPTION  "Filesystem device name for the cache disk"
    ::= { filerCache 12 }

filerDeviceVar OBJECT-TYPE
    SYNTAX       DisplayString
    MAX-ACCESS   read-only
    STATUS       current
    DESCRIPTION  "Filesystem device name for the var disk"
    ::= { filerCache 13 }

filerDeviceRoot OBJECT-TYPE
    SYNTAX       DisplayString
    MAX-ACCESS   read-only
    STATUS       current
    DESCRIPTION  "Filesystem device name for the root disk"
    ::= { filerCache 14 }

filerDeviceNasuni OBJECT-TYPE
    SYNTAX       DisplayString
    MAX-ACCESS   read-only
    STATUS       current
    DESCRIPTION  "Filesystem device name for the nasuni disk"
    ::= { filerCache 15 }

------------------------------------------------------------------------
-- Health Stats (.1.102)
------------------------------------------------------------------------

filerHealth  OBJECT IDENTIFIER ::= { filer 102 }

filerAmbientTemp OBJECT-TYPE
    SYNTAX       Integer32
    UNITS        "degrees celsius"
    MAX-ACCESS   read-only
    STATUS       current
    DESCRIPTION  "Filer ambient temperature (0 if not available)"
    ::= { filerHealth 1 }

filerInletTemp OBJECT-TYPE
    SYNTAX       Integer32
    UNITS        "degrees celsius"
    MAX-ACCESS   read-only
    STATUS       current
    DESCRIPTION  "Filer inlet temperature (0 if not available)"
    ::= { filerHealth 2 }

filerExhaustTemp OBJECT-TYPE
    SYNTAX       Integer32
    UNITS        "degrees celsius"
    MAX-ACCESS   read-only
    STATUS       current
    DESCRIPTION  "Filer exhaust temperature (0 if not available)"
    ::= { filerHealth 3 }

filerNumPowerSupplies OBJECT-TYPE
    SYNTAX       Integer32
    MAX-ACCESS   read-only
    STATUS       current
    DESCRIPTION  "Number of power supplys detected"
    ::= { filerHealth 4 }

filerPowerSupplyErrors OBJECT-TYPE
    SYNTAX       Integer32
    MAX-ACCESS   read-only
    STATUS       current
    DESCRIPTION  "Number of power supply errors detected"
    ::= { filerHealth 5 }

filerNumRaidArrays OBJECT-TYPE
    SYNTAX       Integer32
    MAX-ACCESS   read-only
    STATUS       current
    DESCRIPTION  "Number of RAID arrays detected"
    ::= { filerHealth 6 }

filerRaidArrayErrors OBJECT-TYPE
    SYNTAX       Integer32
    MAX-ACCESS   read-only
    STATUS       current
    DESCRIPTION  "Number of RAID array errors detected"
    ::= { filerHealth 7 }

filerNumRaidDisks OBJECT-TYPE
    SYNTAX       Integer32
    MAX-ACCESS   read-only
    STATUS       current
    DESCRIPTION  "Number of RAID disks detected"
    ::= { filerHealth 8 }

filerRaidDiskErrors OBJECT-TYPE
    SYNTAX       Integer32
    MAX-ACCESS   read-only
    STATUS       current
    DESCRIPTION  "Number of RAID disk errors detected"
    ::= { filerHealth 9 }


------------------------------------------------------------------------
-- CIFS,NFS,FTP,ISCSI Stats (.1.103, .1.104, .1.105, .1.109)
------------------------------------------------------------------------

filerCifs   OBJECT IDENTIFIER ::= { filer 103 }
filerNfs    OBJECT IDENTIFIER ::= { filer 104 }
filerFtp    OBJECT IDENTIFIER ::= { filer 109 }
filerIscsi  OBJECT IDENTIFIER ::= { filer 105 }

filerTotalShares OBJECT-TYPE
    SYNTAX       Integer32
    MAX-ACCESS   read-only
    STATUS       current
    DESCRIPTION  "Total number of shares available on this Filer"
    ::= { filerCifs 1 }

filerTotalShareLocks OBJECT-TYPE
    SYNTAX       Integer32
    MAX-ACCESS   read-only
    STATUS       current
    DESCRIPTION  "Total number shares locks on this Filer"
    ::= { filerCifs 2 }

filerTotalShareClients OBJECT-TYPE
    SYNTAX       Integer32
    MAX-ACCESS   read-only
    STATUS       current
    DESCRIPTION  "Total number share clients connected to this Filer"
    ::= { filerCifs 3 }

filerTotalExports OBJECT-TYPE
    SYNTAX       Integer32
    MAX-ACCESS   read-only
    STATUS       current
    DESCRIPTION  "Total number of exports available on this Filer"
    ::= { filerNfs 1 }

filerTotalFtpdirs OBJECT-TYPE
    SYNTAX       Integer32
    MAX-ACCESS   read-only
    STATUS       current
    DESCRIPTION  "Total number of ftp directories available on this Filer"
    ::= { filerFtp 1 }

filerTotalIscsiTargets OBJECT-TYPE
    SYNTAX       Integer32
    MAX-ACCESS   read-only
    STATUS       current
    DESCRIPTION  "Total number of ISCSI targets available on this Filer"
    ::= { filerIscsi 1 }

filerTotalIscsiClients OBJECT-TYPE
    SYNTAX       Integer32
    MAX-ACCESS   read-only
    STATUS       current
    DESCRIPTION  "Total number of ISCSI clients connected to this Filer"
    ::= { filerIscsi 2 }


------------------------------------------------------------------------
-- Mobile License Stats (.1.106)
------------------------------------------------------------------------

filerMobile   OBJECT IDENTIFIER ::= { filer 106 }

filerTotalMobileLicenses OBJECT-TYPE
    SYNTAX       Integer32
    MAX-ACCESS   read-only
    STATUS       current
    DESCRIPTION  "Total number of mobile clients registered on the Filer"
    ::= { filerMobile 1 }

filerNumIOSLicenses OBJECT-TYPE
    SYNTAX       Integer32
    MAX-ACCESS   read-only
    STATUS       current
    DESCRIPTION  "Total number of iOS mobile clients registered on the Filer"
    ::= { filerMobile 2 }

filerNumAndroidLicenses OBJECT-TYPE
    SYNTAX       Integer32
    MAX-ACCESS   read-only
    STATUS       current
    DESCRIPTION  "Total number of Android mobile clients registered on the Filer"
    ::= { filerMobile 3 }


------------------------------------------------------------------------
-- Services (.1.107)
------------------------------------------------------------------------

filerServices   OBJECT IDENTIFIER ::= { filer 107 }

filerSupportServiceEnabled OBJECT-TYPE
    SYNTAX       Integer32
    MAX-ACCESS   read-only
    STATUS       current
    DESCRIPTION  "True if support service is enabled (0=false; 1=true)"
    ::= { filerServices 1 }

filerSupportServiceConnected OBJECT-TYPE
    SYNTAX       Integer32
    MAX-ACCESS   read-only
    STATUS       current
    DESCRIPTION  "True if a service rep is connect to the support portal (0=false; 1=true)"
    ::= { filerServices 2 }

filerSupportServiceRunning OBJECT-TYPE
    SYNTAX       Integer32
    MAX-ACCESS   read-only
    STATUS       current
    DESCRIPTION  "True if support service is running (0=false; 1=true)"
    ::= { filerServices 3 }

filerSupportServiceTimeout OBJECT-TYPE
    SYNTAX       Integer32
    UNITS        "seconds"
    MAX-ACCESS   read-only
    STATUS       current
    DESCRIPTION  "Timeout until the support service will be disabled (0 = unlimted)"
    ::= { filerServices 4 }


------------------------------------------------------------------------
-- Network (.1.108)
------------------------------------------------------------------------

filerNetwork   OBJECT IDENTIFIER ::= { filer 108 }

filerCloudOut OBJECT-TYPE
    SYNTAX       Counter64
    UNITS        "bits/second"
    MAX-ACCESS   read-only
    STATUS       current
    DESCRIPTION  "Cloud transmit bits/second for the last 1 minute"
    ::= { filerNetwork 1 }

filerCloudIn OBJECT-TYPE
    SYNTAX       Counter64
    UNITS        "bits/second"
    MAX-ACCESS   read-only
    STATUS       current
    DESCRIPTION  "Cloud recieve bits/second for the last 1 minute"
    ::= { filerNetwork 2 }

filerMobileOut OBJECT-TYPE
    SYNTAX       Counter64
    UNITS        "bits/second"
    MAX-ACCESS   read-only
    STATUS       current
    DESCRIPTION  "Mobile transmit bits/second for the last 1 minute"
    ::= { filerNetwork 3 }

filerMobileIn OBJECT-TYPE
    SYNTAX       Counter64
    UNITS        "bits/second"
    MAX-ACCESS   read-only
    STATUS       current
    DESCRIPTION  "Mobile recieve bits/second for the last 1 minute"
    ::= { filerNetwork 4 }

filerUIOut OBJECT-TYPE
    SYNTAX       Counter64
    UNITS        "bits/second"
    MAX-ACCESS   read-only
    STATUS       current
    DESCRIPTION  "User Interface transmit bits/second for the last 1 minute"
    ::= { filerNetwork 5 }

filerUIIn OBJECT-TYPE
    SYNTAX       Counter64
    UNITS        "bits/second"
    MAX-ACCESS   read-only
    STATUS       current
    DESCRIPTION  "User Interface recieve bits/second for the last 1 minute"
    ::= { filerNetwork 6 }

filerClientsOut OBJECT-TYPE
    SYNTAX       Counter64
    UNITS        "bits/second"
    MAX-ACCESS   read-only
    STATUS       current
    DESCRIPTION  "Clients transmit bits/second for the last 1 minute"
    ::= { filerNetwork 7 }

filerClientsIn OBJECT-TYPE
    SYNTAX       Counter64
    UNITS        "bits/second"
    MAX-ACCESS   read-only
    STATUS       current
    DESCRIPTION  "Clients recieve bits/second for the last 1 minute"
    ::= { filerNetwork 8 }

filerMigrationOut OBJECT-TYPE
    SYNTAX       Counter64
    UNITS        "bits/second"
    MAX-ACCESS   read-only
    STATUS       current
    DESCRIPTION  "Migration transmit bits/second for the last 1 minute"
    ::= { filerNetwork 9 }

filerMigrationIn OBJECT-TYPE
    SYNTAX       Counter64
    UNITS        "bits/second"
    MAX-ACCESS   read-only
    STATUS       current
    DESCRIPTION  "Migration recieve bits/second for the last 1 minute"
    ::= { filerNetwork 10 }


------------------------------------------------------------------------
-- Volumes (.2)
------------------------------------------------------------------------

volumes  OBJECT IDENTIFIER ::= { nasuni 2 }

volumeCount OBJECT-TYPE
    SYNTAX       Integer32
    MAX-ACCESS   read-only
    STATUS       current
    DESCRIPTION  "Number of entries in VolumeTable"
    ::= { volumes 1 }


volumeTable OBJECT-TYPE
    SYNTAX       SEQUENCE OF VolumeTableSchema
    MAX-ACCESS   not-accessible
    STATUS       current
    DESCRIPTION  "Table of Volume information"
    ::= { volumes 2 }

VolumeTableSchema
    ::= SEQUENCE {
        volumeTableIndex                 Integer32,
        volumeTableDescription           DisplayString,
        volumeTableProvider              DisplayString,
        volumeTableProtocol              DisplayString,
        volumeTableStatus                DisplayString,
        volumeTableAccessibleData        Counter64,
        volumeTableUnprotectedData       Counter64,
        volumeTableLastSnapshotStart     DisplayString,
        volumeTableLastSnapshotEnd       DisplayString,
        volumeTableLastSnapshotDuration  Integer32,
        volumeTableLastSnapshotVersion   Counter64,
        volumeTableIsActive              Integer32,
        volumeTableIsShared              Integer32,
        volumeTableIsReadOnly            Integer32,
        volumeTableIsPinned              Integer32,
        volumeTableIsRemote              Integer32,
        volumeTableAvEnabled             Integer32,
        volumeTableRemoteAccessEnabled   Integer32,
        volumeTableQuota                 Counter64,
        volumeTableNumAVViolations       Counter64,
        volumeTableNumFileAlerts         Counter64,
        volumeTableNumExports            Integer32,
        volumeTableNumShares             Integer32,
        volumeTableNumFtpdirs            Integer32
    }

volumeTableEntry OBJECT-TYPE
    SYNTAX       VolumeTableSchema
    MAX-ACCESS   not-accessible
    STATUS       current
    DESCRIPTION  "Row in VolumeTable"
    INDEX { volumeTableIndex }
    ::= { volumeTable 1 }

volumeTableIndex OBJECT-TYPE
    SYNTAX       Integer32 (0..999)
    MAX-ACCESS   not-accessible
    STATUS       current
    DESCRIPTION  "Index column used for VolumeTable"
    ::= { volumeTableEntry 1 }

volumeTableDescription OBJECT-TYPE
    SYNTAX       DisplayString
    MAX-ACCESS   read-only
    STATUS       current
    DESCRIPTION  "Volume description"
    ::= { volumeTableEntry 2 }

volumeTableProvider OBJECT-TYPE
    SYNTAX       DisplayString
    MAX-ACCESS   read-only
    STATUS       current
    DESCRIPTION  "Volume provider"
    ::= { volumeTableEntry 3 }

volumeTableProtocol OBJECT-TYPE
    SYNTAX       DisplayString
    MAX-ACCESS   read-only
    STATUS       current
    DESCRIPTION  "Volume protocol"
    ::= { volumeTableEntry 4 }

volumeTableStatus OBJECT-TYPE
    SYNTAX       DisplayString
    MAX-ACCESS   read-only
    STATUS       current
    DESCRIPTION  "Volume status string"
    ::= { volumeTableEntry 5 }

volumeTableAccessibleData OBJECT-TYPE
    SYNTAX       Counter64
    UNITS        "bytes"
    MAX-ACCESS   read-only
    STATUS       current
    DESCRIPTION  "Volume accessible data"
    ::= { volumeTableEntry 6 }

volumeTableUnprotectedData OBJECT-TYPE
    SYNTAX       Counter64
    UNITS        "bytes"
    MAX-ACCESS   read-only
    STATUS       current
    DESCRIPTION  "Volume data not yet protected"
    ::= { volumeTableEntry 7 }

volumeTableLastSnapshotStart OBJECT-TYPE
    SYNTAX       DisplayString
    MAX-ACCESS   read-only
    STATUS       current
    DESCRIPTION  "Date and time the last snapshot started (YYYY-MM-DD HH:MM:SS)"
    ::= { volumeTableEntry 8 }

volumeTableLastSnapshotEnd OBJECT-TYPE
    SYNTAX       DisplayString
    MAX-ACCESS   read-only
    STATUS       current
    DESCRIPTION  "Date and time the last snapshot ended (YYYY-MM-DD HH:MM:SS)"
    ::= { volumeTableEntry 9 }

volumeTableLastSnapshotDuration OBJECT-TYPE
    SYNTAX       Integer32
    UNITS        "seconds"
    MAX-ACCESS   read-only
    STATUS       current
    DESCRIPTION  "Duration of the last snapshot"
    ::= { volumeTableEntry 10 }

volumeTableLastSnapshotVersion OBJECT-TYPE
    SYNTAX       Counter64
    MAX-ACCESS   read-only
    STATUS       current
    DESCRIPTION  "Last snapshot version number"
    ::= { volumeTableEntry 11 }

volumeTableIsActive OBJECT-TYPE
    SYNTAX       Integer32
    MAX-ACCESS   read-only
    STATUS       current
    DESCRIPTION  "True if volume is active (0=false; 1=true)"
    ::= { volumeTableEntry 12 }

volumeTableIsShared OBJECT-TYPE
    SYNTAX       Integer32
    MAX-ACCESS   read-only
    STATUS       current
    DESCRIPTION  "True if volume is shared (0=false; 1=true)"
    ::= { volumeTableEntry 13 }

volumeTableIsReadOnly OBJECT-TYPE
    SYNTAX       Integer32
    MAX-ACCESS   read-only
    STATUS       current
    DESCRIPTION  "True if volume is read-only (0=false; 1=true)"
    ::= { volumeTableEntry 14 }

volumeTableIsPinned OBJECT-TYPE
    SYNTAX       Integer32
    MAX-ACCESS   read-only
    STATUS       current
    DESCRIPTION  "True if volume is pinned (0=false; 1=true)"
    ::= { volumeTableEntry 15 }

volumeTableIsRemote OBJECT-TYPE
    SYNTAX       Integer32
    MAX-ACCESS   read-only
    STATUS       current
    DESCRIPTION  "True if volume is remote (0=false; 1=true)"
    ::= { volumeTableEntry 16 }

volumeTableAvEnabled OBJECT-TYPE
    SYNTAX       Integer32
    MAX-ACCESS   read-only
    STATUS       current
    DESCRIPTION  "True if antivirus is enabled (0=false; 1=true)"
    ::= { volumeTableEntry 17 }

volumeTableRemoteAccessEnabled OBJECT-TYPE
    SYNTAX       Integer32
    MAX-ACCESS   read-only
    STATUS       current
    DESCRIPTION  "True if remote access enabled (0=false; 1=true)"
    ::= { volumeTableEntry 18 }

volumeTableQuota OBJECT-TYPE
    SYNTAX       Counter64
    UNITS        "bytes"
    MAX-ACCESS   read-only
    STATUS       current
    DESCRIPTION  "Volume Quota (0 for disiabled quota)"
    ::= { volumeTableEntry 19 }

volumeTableNumAVViolations OBJECT-TYPE
    SYNTAX       Counter64
    MAX-ACCESS   read-only
    STATUS       current
    DESCRIPTION  "Number of antivirus violations found"
    ::= { volumeTableEntry 20 }

volumeTableNumFileAlerts OBJECT-TYPE
    SYNTAX       Counter64
    MAX-ACCESS   read-only
    STATUS       current
    DESCRIPTION  "Number of file locks"
    ::= { volumeTableEntry 21 }

volumeTableNumExports OBJECT-TYPE
    SYNTAX       Integer32
    MAX-ACCESS   read-only
    STATUS       current
    DESCRIPTION  "Number of volume exports"
    ::= { volumeTableEntry 22 }

volumeTableNumShares OBJECT-TYPE
    SYNTAX       Integer32
    MAX-ACCESS   read-only
    STATUS       current
    DESCRIPTION  "Number of volume shares"
    ::= { volumeTableEntry 23 }

volumeTableNumFtpdirs OBJECT-TYPE
    SYNTAX       Integer32
    MAX-ACCESS   read-only
    STATUS       current
    DESCRIPTION  "Number of volume ftp directories"
    ::= { volumeTableEntry 24 }


------------------------------------------------------------------------
-- Account (.3)
------------------------------------------------------------------------
 
account  OBJECT IDENTIFIER ::= { nasuni 3 }

accountLicensedCapacity OBJECT-TYPE
    SYNTAX       Counter64
    UNITS        "bytes"
    MAX-ACCESS   read-only
    STATUS       current
    DESCRIPTION  "Available licensed capacity"
    ::= { account 1 }

accountUsedCapacity OBJECT-TYPE
    SYNTAX       Counter64
    UNITS        "bytes"
    MAX-ACCESS   read-only
    STATUS       current
    DESCRIPTION  "Used licensed capacity"
    ::= { account 2 }

accountPercentUsedCapacity OBJECT-TYPE
    SYNTAX       Integer32
    UNITS        "percent"
    MAX-ACCESS   read-only
    STATUS       current
    DESCRIPTION  "Percent used licensed capacity"
    ::= { account 3 }


------------------------------------------------------------------------
-- Traps (.100)
-- Generic traps sent with three values (type, level, message)
------------------------------------------------------------------------

filerTrapsWrap  OBJECT IDENTIFIER ::= { nasuni 100 }  
filerTraps      OBJECT IDENTIFIER ::= { filerTrapsWrap 0 }

filerTrapType OBJECT-TYPE
    SYNTAX       DisplayString
    MAX-ACCESS   read-only
    STATUS       current
    DESCRIPTION  "Notification type"
    ::= { filerTraps 1 }

filerTrapLevel OBJECT-TYPE
    SYNTAX       DisplayString
    MAX-ACCESS   read-only
    STATUS       current
    DESCRIPTION  "Notification level (info, update, warning, error, alert)"
    ::= { filerTraps 2 }

filerTrapMessage OBJECT-TYPE
    SYNTAX       DisplayString
    MAX-ACCESS   read-only
    STATUS       current
    DESCRIPTION  "Notification message"
    ::= { filerTraps 3 }

filerTrap NOTIFICATION-TYPE
    OBJECTS      { filerTrapType, filerTrapLevel, filerTrapMessage }
    STATUS       current
    DESCRIPTION  "Notification trap from the Filer"
    ::= { filerTraps 4 }

END
