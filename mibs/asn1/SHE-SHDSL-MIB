--
-- she-shdsl-mib.mib
-- MIB generated by MG-SOFT Visual MIB Builder Version 6.0  Build 88
-- Monday, May 19, 2008 at 08:58:07
--

-- Start of ClearCase branch-information of current release:
-- she-shdsl-mib.mib   /main/she_main_grf/7
-- End of ClearCase branch-information.

	SHE-SHDSL-MIB DEFINITIONS ::= BEGIN
 
		IMPORTS
			she			
				FROM AN-MIB			
			ifIndex, InterfaceIndex			
				FROM IF-MIB			
			PerfCurrentCount, PerfIntervalCount			
				FROM PerfHist-TC-MIB			
			sheAlarmTimeAndDate, sheAlarmReportingSource, sheAlarmReportingSourceType, sheAlarmSeverity			
				FROM SHE-ALARMING-MIB			
			SheControlStatusType			
				FROM SHE-TC-MIB			
			SnmpAdminString			
				FROM SNMP-FRAMEWORK-MIB			
			OBJECT-GROUP, MODULE-COMPLIANCE, NOTIFICATION-GROUP			
				FROM SNMPv2-CONF			
			TimeTicks, Integer32, Unsigned32, Gauge32, Counter32, 
			OBJECT-TYPE, MODULE-IDENTITY, NOTIFICATION-TYPE			
				FROM SNMPv2-SMI			
			TEXTUAL-CONVENTION			
				FROM SNMPv2-TC;
	
	
		sheShdslMib MODULE-IDENTITY 
			LAST-UPDATED "200805191300Z"		-- May 19, 2008 at 13:00 GMT
			ORGANIZATION 
				"Nokia Siemens Networks"
			CONTACT-INFO 
				"Gerd Barchmann
				COO BBA DSLAM RD SDE HW1
				
				gerd.barchmann@nsn.com"
			DESCRIPTION 
				"This MIB module defines a collection of objects for managing
				HDSL2/SHDSL lines according RFC3276.  An agent may reside at 
				either end of the line, however the MIB is designed to require
				no management communication between the modems beyond that 
				inherent in the low-level EOC line protocol as defined in 
				ANSI T1E1.4/2000-006 (for HDSL2 lines), or in ITU G.991.2
				(for SHDSL lines).
				Adapted to support RFC 4319."
			REVISION "200505041041Z"		-- May 04, 2005 at 10:41 GMT
			DESCRIPTION 
				"Initial version."
			REVISION "200505181122Z"		-- May 18, 2005 at 11:22 GMT
			DESCRIPTION 
				"Add sheShdslBondingGroupTable."
			REVISION "200505190840Z"		-- May 19, 2005 at 08:40 GMT
			DESCRIPTION 
				"Correct spelling for dsShdslArSnrMarginThreshold - its now
				sheShdslArSnrMarginThreshold."
			REVISION "200506010833Z"		-- June 01, 2005 at 08:33 GMT
			DESCRIPTION 
				"Correct access for shehdsl2ShdslEndpointAlarmConfProfile to read-only.
				Correct sequence of indices for shehdsl2ShdslEndpointConfEntry.
				Add IntervalEndTime entry in PM interval-tables.
				Add configuration notifications.
				Move entrys from shdslStatus-Table to shdslParam-Table.
				Change param-list for alarm - notifications."
			REVISION "200506071004Z"		-- June 07, 2005 at 10:04 GMT
			DESCRIPTION 
				"Correct comment above mib structure (problem for mib2c-tool.
				Change param list of sheShdslLineParamsEntryModified notification."
			REVISION "200507180432Z"		-- July 18, 2005 at 04:32 GMT
			DESCRIPTION 
				"Change some default values and ranges for the following mib-objects:
				shehdsl2ShdslSpanConfPSD
				sheShdslEncodeCoeffA
				sheShdslEncodeCoeffB
				shehdsl2ShdslSpanConfReferenceClock
				sheShdslParamHybridLossTestStart
				sheShdslParamHybridLossTestEnd
				sheShdslSetIndividualRates1
				sheShdslSetIndividualRates2
				sheShdslSetIndividualRates3
				shehdsl2ShdslMaintPowerBackOff
				shehdsl2ShdslUnitMaintLoopbackTimeout"
			REVISION "200508091040Z"		-- August 09, 2005 at 10:40 GMT
			DESCRIPTION 
				"Add shdslVccTpTable.
				Add values to Shehdsl2ShdslMaintLoopbackConfigType.
				Set range for shehdsl2ShdslSpanConfNumRepeaters to 0."
			REVISION "200508220834Z"		-- August 22, 2005 at 08:34 GMT
			DESCRIPTION 
				"Add description to value
				TransmissionMode and UsedTargetMargins
				in shehdsl2ShdslSpanConfProfileTable 
				(one bit have to be set!).
				Change description for shehdsl2ShdslMaintLoopbackConfig."
			REVISION "200608111050Z"		-- August 11, 2006 at 10:50 GMT
			DESCRIPTION 
				"Take over again for R2.5."
			REVISION "200704251407Z"		-- April 25, 2007 at 14:07 GMT
			DESCRIPTION 
				"Merge modifications from MIB release 159 of SHE R2.0/2.3."
			REVISION "200705020820Z"		-- May 02, 2007 at 08:20 GMT
			DESCRIPTION 
				"Correct Compliance spelling."
			REVISION "200710231023Z"		-- October 23, 2007 at 10:23 GMT
			DESCRIPTION 
				"All modifications of this release will be supported by SHE R2.7.
				Modifications for support RFC4319.
				Add comment for table support by different shdsl boards based 
				on used ifType.
				Set sheShdslBondingTable to status obsolete.
				Add support for LOS and LOF alarms."
			REVISION "200803191310Z"		-- March 19, 2008 at 13:10 GMT
			DESCRIPTION 
				"Add detailed failure returncode definitions to ReqResult enum. The scheduled support release is not defined yet."
			REVISION "200805191306Z"		-- May 19, 2008 at 13:06 GMT
			DESCRIPTION 
				"Update max. possible linerates for support of 6- and 8-wire mode by IFX shdsl card."
			::= { she 12 }

		
	
--
-- Type definitions
--
	
		SheShdslOpStateType ::= INTEGER
			{
			idle(0),
			data(1),
			bootupLoad(8),
			bootupLoadDone(9),
			handshake(16),
			pmms(20),
			training(24),
			framerGearShift(26),
			framerManualReset(27),
			silence(29),
			analogLb(128),
			rmtFramerLb(130),
			digitalLb(131),
			spectrumTest(133),
			selt(138),
			pSDTest(139),
			lclFramerLb(142),
			interfaceLb(143),
			bertTest(144),
			analogLbBertTest(145),
			digLbBertTest(146)
			}

		SheShdslStartProgressType ::= INTEGER
			{
			noActivity(0),
			preActivation(1),
			activation(4),
			checkBitrate(7),
			pmmsChkComnRate(8),
			transmitCr(55),
			transmitSc(56),
			transmitSr(57),
			coLineAgc(64),
			cpLineAgc(65),
			fdEcTrain(66),
			equalizerTrain(67),
			tipRingAligned(68),
			transmitTc(69),
			receiveTr(70),
			transmitFc1(71),
			transmitFc2(72),
			receiveTc(73),
			transmitTr(74),
			receiveFc(75),
			spectTestOk(113),
			albTestOk(114),
			dlbTestOk(115),
			crcFail(116),
			framerSyncFail(117),
			snrMarginFail(118),
			loadCppa(128),
			loadCptrain(129),
			loadCptom(130),
			loadCpdm(131),
			loadCopa(144),
			loadCotrain(145),
			loadCotom(146),
			loadCodm(147)
			}

		SheShdslLineSwapType ::= INTEGER
			{
			unswapped(0),
			swapped(1)
			}

		SheShdslFramerSyncType ::= INTEGER
			{
			outOfSync(0),
			inSync(1)
			}

		SheShdslBertErrorType ::= INTEGER
			{
			outOfSync(0),
			framedSync(64),
			unframedSync(128)
			}

		SheShdslUtopiaCellDelineationType ::= INTEGER
			{
			inSync(1),
			preSync(160),
			hunt(240)
			}

		SheShdslRmtPowerBackoffType ::= INTEGER
			{
			enable(0),
			disable(32768)
			}

		SheShdslEocStateType ::= INTEGER
			{
			online(0),
			discovery(1),
			inventory(2),
			configuration(3),
			cmdInProgress(4)
			}

		SheShdslNtrFaultType ::= INTEGER
			{
			present(0),
			absent(1)
			}

		SheShdslCpeMasterCoreType ::= INTEGER
			{
			core0(0),
			core1(16),
			core2(32),
			core3(48),
			core4(64),
			core5(80),
			core6(96),
			core7(112),
			noMasterCore(128)
			}

		SheShdslParametricTestResultType ::= INTEGER
			{
			pass(0),
			fail(1)
			}

--   for shdsl.bis(SGagMOShdslLineStatusTableTbl)
		SheShdslStartUpInfoType ::= INTEGER
			{
			nonBis(0),
			bis(1),
			unknown(2)
			}

		SheSdslActionType ::= INTEGER
			{
			startUp(0),
			abortReq(2),
			gearShiftReq(6),
			downloadReq(8),
			bertStartTxReq(17),
			bertStartRxReq(18),
			bertStopReq(20),
			spectrumDownReq(25),
			spectrumUpReq(26),
			spectrumTxRxReq(32),
			hybridLossTestReq(33),
			residualEchoReq(34),
			totalEchoReq(35),
			nextPsdReq(36),
			autoRetrainOnReq(37),
			autoRetrainOffReq(38),
			propEocOnReq(45),
			propEocOffReq(46),
			rmtAtmCellStatusReq(47),
			rmtFullStatusReq(48)
			}

		SheShdslModeType ::= INTEGER
			{
			co(0),
			cpe(1)
			}

		SheShdslPowerScaleType ::= INTEGER { defaultScale(26112) }

		SheShdslEncodeCoeffAType ::= INTEGER { default(366) }

		SheShdslEncodeCoeffBType ::= INTEGER { default(817) }

		SheShdslNTRType ::= INTEGER
			{
			disable(1),
			refClkIp8k(2),
			refClkOp4096k(4)
			}

		SheShdslInitiateType ::= INTEGER
			{
			default(0),
			co(1),
			cpe(2)
			}

		SheShdslFramerRxClockModeType ::= INTEGER
			{
			slave(2),
			internal(3)
			}

		SheShdslEnableModeType ::= INTEGER
			{
			disable(0),
			enable(1)
			}

		SheShdslSerialAtmCiuBufferSizeType ::= INTEGER
			{
			size24(24),
			size53(53)
			}

		SheShdslSetReqSilenceModeEnableType ::= INTEGER
			{
			disable(0),
			enable(4)
			}

		SheShdslHsMaxBitsPerBaudType ::= INTEGER
			{
			use1Bit(1),
			use2Bit(2),
			default(3)
			}

		SheShdslHsAnnexBType ::= INTEGER
			{
			default(1),
			anfp(2),
			annexBorAnfp(3)
			}

		SheShdslEnableType ::= INTEGER
			{
			enable(1),
			disable(2)
			}

		SheShdslClkEdgeType ::= INTEGER
			{
			negative(0),
			positive(1)
			}

		SheShdslPulseLvlType ::= INTEGER
			{
			low(0),
			high(1)
			}

		SheShdslFramerType ::= INTEGER
			{
			unframed(0),
			t1Slotted(1),
			e1Slotted(2),
			utopiaL2(3),
			nx64(6),
			serialATM(7),
			vC12(8),
			iMA(9)
			}

		SheShdslAFEType ::= INTEGER
			{
			saturn(3),
			saturnLg(4)
			}

		SheShdslUtopiaDataBusWidthType ::= INTEGER
			{
			tx8Rx8(0),
			tx16Rx16(1),
			tx16Rx8(2),
			tx8Rx16(3)
			}

--   for shdsl.bis(pammode)
		SheShdslPAMModeType ::= INTEGER
			{
			pam16Tc(0),
			pam32Tc(1),
			pamAutoTc(2)
			}

--   This type specifies the user commands (control requests)
-- from the TMN-OS or LCT.
		SheShdslControlRequestType ::= INTEGER
			{
			noRequest(1),
			modifysheShdslLineParamsEntry(101),
			modifyshehdsl2ShdslSpanConfEntry(201),
			modifyshehdsl2ShdslSpanConfEntryAlarmProfile(202),
			modifyshehdsl2ShdslEndpointConfEntry(301),
			modifyshehdsl2ShdslEndpointMaintEntry(401),
			modifyshehdsl2ShdslUnitMaintEntry(501),
			createshehdsl2ShdslSpanConfProfile(601),
			modifyshehdsl2ShdslSpanConfProfile(602),
			deleteshehdsl2ShdslSpanConfProfile(603),
			createshehdsl2ShdslEndpointAlarmConfProfile(701),
			modifyshehdsl2ShdslEndpointAlarmConfProfile(702),
			deleteshehdsl2ShdslEndpointAlarmConfProfile(703),
			modifyShdslVccTp(801),
			modifyAdslVccTpLoopTest(802),
			createShdslVccTp(803),
			deleteShdslVccTp(804)
			}

--   This type specifies the result of user commands (control requests)
-- from the TMN-OS or LCT.
		SheShdslControlRequestResultType ::= INTEGER
			{
			noRequest(1),
			comExecStarted(30),
			paramFaulty(31),
			requestBusy(32),
			setDataFailed(34),
			aswTimeout(35),
			commandFailed(36),
			commandSucceeded(37),
			profileNameStringUnknown(2001),
			profileNameToLong(2002),
			profileNameAlreadyExist(2003),
			maxNumberOfProfilesReached(2004),
			profileNotExist(2005),
			profileAssignFailOnActivePort(2006),
			profileTypDefaultCouldNotModified(2010),
			profileModifyFailOnInvalidArguments(2012),
			profileModifyFailOnInvalidMarginSettings(2013),
			profileModifyFailOnInvalidDataRateSettings(2014),
			profileWireIfModifyFailOnAssignedProfiles(2015),
			profileRefClockModifyFailOnAssignedProfiles(2016),
			profilePowerFeedModifyFailOnAssignedProfiles(2017),
			internalFailureWriteToDataBase(2020),
			internalFailureReadFromDataBase(2021),
			profileUsedByActivePorts(2022),
			internalFailureDuringIuCommunication(2030),
			portNumberNotExist(2040),
			portNumberHasWrongDSLType(2041),
			portNumberOnLegacyCardType(2042)
			}

		SheShdslStatus4WireHsModeType ::= INTEGER
			{
			standard(0),
			enhanced(1)
			}

		SheShdslBondingGroupType ::= INTEGER
			{
			twoPortsBondingGroup(1),
			fourPortsBondingGroup(2)
			}

		Shehdsl2ShdslEndpointCurrStatusType ::= BITS
			{
			noDefect(0),
			powerBackoff(1),
			deviceFault(2),
			dcContinuityFault(3),
			snrMarginAlarm(4),
			loopAttenuationAlarm(5),
			loswFailureAlarm(6),
			configInitFailure(7),
			protocolInitFailure(8),
			noNeighborPresent(9),
			loopbackActive(10)
			}

		Shehdsl2ShdslMaintTipRingReversalType ::= INTEGER
			{
			normal(1),
			reversed(2)
			}

		Shehdsl2ShdslMaintLoopbackConfigType ::= INTEGER
			{
			noLoopback(1),
			normalLoopback(2),
			specialLoopback(3),
			digitalLoopback(4),
			analogLoopback(5),
			interfaceLoopback(6),
			localFramerLoopback(7),
			normalLoopbackEocId9(8),
			specialLoopbackEocId9(9)
			}

		Shehdsl2ShdslMaintPowerBackOffType ::= INTEGER
			{
			default(1),
			enhanced(2),
			disable(3)
			}

		Shehdsl2ShdslMaintSoftRestartType ::= INTEGER
			{
			ready(1),
			restart(2)
			}

		Shehdsl2ShdslMaintUnitPowerSourceType ::= INTEGER
			{
			local(1),
			span(2)
			}

		Shehdsl2ShdslSpanConfWireInterfaceType ::= INTEGER
			{
			twoWire(1),
			fourWire(2),
			fourWireBitInterleaved(3),
			fourWireByteInterleaveEnhanced(4),
			fourWireBitInterleaveEnhanced(5),
			sixWire(6),
			eightWire(7)
			}

		Shehdsl2ShdslSpanConfPSDType ::= INTEGER
			{
			symmetric(1),
			asymmetric(2),
			r1Asymmetric(3),
			r2Asymmetric(4)
			}

		Shehdsl2ShdslSpanConfPowerFeedingType ::= INTEGER
			{
			noPower(1),
			powerFeed(2),
			wettingCurrent(3)
			}

		Shehdsl2ShdslSpanConfUsedTargetMarginsType ::= BITS
			{
			currCondDown(0),
			worstCaseDown(1),
			currCondUp(2),
			worstCaseUp(3)
			}

		Shehdsl2ShdslSpanConfLineProbeEnableType ::= INTEGER
			{
			disable(1),
			enable(2)
			}

		SheShdsl2CapListStyleType ::= INTEGER
			{
			newstyle(0),
			oldstylecaplist(1),
			autocaplist(2)
			}

		SheAtmOamLevelType ::= INTEGER
			{
			undefined(0),
			f1(1),
			f2(2),
			f3(3),
			f4(4),
			f5(5)
			}

		SheAtmOamLoopTestType ::= INTEGER
			{
			none(0),
			segment(1),
			endToEnd(2)
			}

		SheAtmOamLoopTestResultType ::= INTEGER
			{
			segSuccess(0),
			segFailure(1),
			endToEndSuccess(2),
			endToEndFailure(3),
			aborted(4),
			progress(5),
			notAvailable(65535)
			}

	
--
-- Textual conventions
--
	
		SheHdsl2ShdslTransmissionModeType ::= TEXTUAL-CONVENTION
			STATUS current
			DESCRIPTION 
				"Contains the regional setting of the HDSL2/SHDSL span,
				represented as a bit-map of possible settings. The various
				bit positions are:
				
				Bit   Meaning      Description
				1     region 1     Indicates ITU-T G.991.2 Annex A/F.
				2     region 2     Indicates ITU-T G.991.2 Annex B/G."
			SYNTAX BITS
				{
				region1(0),
				region2(1)
				}

		SheHdsl2ShdslUnitId ::= TEXTUAL-CONVENTION
			STATUS current
			DESCRIPTION 
				"This is the unique identification for all units in a
				HDSL2/SHDSL Span.  It is based on the EOC unit addressing
				scheme with reference to the xtuC."
			SYNTAX INTEGER
				{
				xtuC(1),
				xtuR(2),
				xru1(3),
				xru2(4),
				xru3(5),
				xru4(6),
				xru5(7),
				xru6(8),
				xru7(9),
				xru8(10)
				}

		SheHdsl2ShdslUnitSide ::= TEXTUAL-CONVENTION
			STATUS current
			DESCRIPTION 
				"This is the referenced side of a HDSL2/SHDSL unit - Network
				or Customer side.  The side facing the Network is the Network
				side, while the side facing the Customer is the Customer side."
			SYNTAX INTEGER
				{
				networkSide(1),
				customerSide(2)
				}

		SheHdsl2ShdslWirePair ::= TEXTUAL-CONVENTION
			STATUS current
			DESCRIPTION 
				"This is the referenced pair of wires in an HDSL2/SHDSL segment.
				HDSL2 only supports a single pair (wirePair1 or two wire), SHDSL lines
				support an optional second pair (wirePair2 or four wire), and G.shdsl.bis
				support an optional third pair (wirePair3 or six wire) and an optional
				fourth pair (wirePair4 or eight wire)."
			SYNTAX INTEGER
				{
				wirePair1(1),
				wirePair2(2),
				wirePair3(3),
				wirePair4(4)
				}

		SheHdsl2ShdslPerfTimeElapsed ::= TEXTUAL-CONVENTION
			STATUS current
			DESCRIPTION 
				"The number of seconds that have elapsed since the beginning of
				the current measurement period.  If, for some reason, such as
				an adjustment in the system's time-of-day clock or the addition
				of a leap second, the current interval exceeds the maximum
				value, the agent will return the maximum value.
				
				For 15 minute intervals, the range is limited to (0..899).
				For 24 hour intervals, the range is limited to (0..86399)."
			SYNTAX Unsigned32 (0..86399)

		SheHdsl2ShdslPerfCurrDayCount ::= TEXTUAL-CONVENTION
			STATUS current
			DESCRIPTION 
				"A gauge associated with interface performance measurements in
				a current 1-day (24 hour) measurement interval.
				
				The value of this gauge starts at zero at the beginning of an
				interval and is increased when associated events occur, until
				the end of the 1-day interval.  At that time the value of the
				gauge is stored in the previous 1-day history interval, as
				defined in a companion object of type
				Hdsl2Shdsl1DayIntevalCount, and the current interval gauge
				is restarted at zero.
				
				In the case where the agent has no valid data available for
				this interval the corresponding object instance is not
				available and upon a retrieval request a corresponding error
				message shall be returned to indicate that this instance does
				not exist.  Please note that zero is a valid value."
			SYNTAX Gauge32

		SheHdsl2ShdslActivationStateType ::= TEXTUAL-CONVENTION
			STATUS current
			DESCRIPTION 
				"Activation or training state of the wire pair."
			SYNTAX INTEGER
				{
				preActivation(1),
				activation(2),
				data(3)
				}

		SheHdsl2Shdsl1DayIntervalCount ::= TEXTUAL-CONVENTION
			STATUS current
			DESCRIPTION 
				"A counter associated with interface performance measurements
				during the most previous 1-day (24 hour) measurement interval.
				The value of this gauge is equal to the value of the current
				day gauge, as defined in a companion object of type
				Hdsl2ShdslPerfCurrDayCount, at the end of its most recent
				interval.
				
				In the case where the agent has no valid data available for
				this interval the corresponding object instance is not
				available and upon a retrieval request a corresponding error
				message shall be returned to indicate that this instance does
				not exist."
			SYNTAX Gauge32

		SheHdsl2ShdslClockReferenceType ::= TEXTUAL-CONVENTION
			STATUS current
			DESCRIPTION 
				"The various STU-C symbol clock references for the
				HDSL2/SHDSL span, represented as an enumeration."
			SYNTAX INTEGER
				{
				localClk(1),
				networkClk(2),
				dataOrNetworkClk(3),
				dataClk(4)
				}

		SheHdsl2ShdslTCLayerType ::= TEXTUAL-CONVENTION
			STATUS current
			DESCRIPTION 
				"This textual convention represents possible ATMPTM-TC types in
				G.bond/Eth ports. The following values are defined:
				 tc6465         - 64/65-octet encapsulation, as defined in
				                  [802.3] Clause 61.3.3
				 tcHDLC         - HDLC encapsulation, as defined in [G.998.2]
				                  Annex B
				 ATM            - ATM based xDSL bonding, as defined in [G.998.1]
				"
			SYNTAX INTEGER
				{
				atm(0),
				tc6465(1),
				tcHDLC(2)
				}

		SheHdsl2ShdslPerfIntervalThreshold ::= TEXTUAL-CONVENTION
			STATUS current
			DESCRIPTION 
				"This convention defines a range of values that may be set in
				a fault threshold alarm control.  As the number of seconds in
				a 15-minute interval numbers at most 900, objects of this type
				may have a range of 0...900, where the value of 0 disables the
				alarm."
			SYNTAX Unsigned32 (0..900)

	
--
-- Node definitions
--
	
-- 1.3.6.1.4.1.231.7.1.2.2.1.12.1
		sheShdslLineMIB OBJECT IDENTIFIER ::= { sheShdslMib 1 }

		
--   1.3.6.1.4.1.231.7.1.2.2.1.12.1.2
		sheShdslMIBObjects OBJECT IDENTIFIER ::= { sheShdslLineMIB 2 }

		
--   1.3.6.1.4.1.231.7.1.2.2.1.12.1.2.1
		sheShdslCapabilityGroup OBJECT IDENTIFIER ::= { sheShdslMIBObjects 1 }

		
--   1.3.6.1.4.1.231.7.1.2.2.1.12.1.2.1.1
		sheShdslCapabilityLineTxCap OBJECT-TYPE
			SYNTAX SheHdsl2ShdslTransmissionModeType
			MAX-ACCESS read-only
			STATUS current
			DESCRIPTION
				"This bitmap specifies the transmission modes that the STU-C is capable of supporting. Right now, support for Annex A (q9921PotsNonOverlapped(2) and q9921PotsOverlapped(3)) is present.  This value depends on the DSL PHY firmware present on Columbia MxU."
			::= { sheShdslCapabilityGroup 1 }

		
--   1.3.6.1.4.1.231.7.1.2.2.1.12.1.2.2
		sheShdslLineStatusTable OBJECT-TYPE
			SYNTAX SEQUENCE OF SheShdslLineStatusEntry
			MAX-ACCESS not-accessible
			STATUS current
			DESCRIPTION
				"This MO is proprietary extension of RFC 3276 MIB and contains the proprietary line status.
				The table will only be supported for interfaces of iftype sdsl (96)!"
			::= { sheShdslMIBObjects 2 }

		
--   1.3.6.1.4.1.231.7.1.2.2.1.12.1.2.2.1
		sheShdslLineStatusEntry OBJECT-TYPE
			SYNTAX SheShdslLineStatusEntry
			MAX-ACCESS not-accessible
			STATUS current
			DESCRIPTION
				"An entry (conceptual row) in the dsShdslLineStatusTable.
				The Table is indexed by ifIndex.
				The table will only be supported for interfaces of iftype sdsl (96)!"
			INDEX { ifIndex }
			::= { sheShdslLineStatusTable 1 }

		
		SheShdslLineStatusEntry ::=
			SEQUENCE { 
				sheShdslOpState
					SheShdslOpStateType,
				sheShdslStartProgress
					SheShdslStartProgressType,
				sheShdslFwRelease
					OCTET STRING,
				sheShdslLineSwap
					SheShdslLineSwapType,
				sheShdslRmtCountryCode
					OCTET STRING,
				sheShdslRmtEncoderA
					Integer32,
				sheShdslRmtEncoderB
					Integer32,
				sheShdslRmtProviderCode
					OCTET STRING,
				sheShdslLocDetect
					Unsigned32,
				sheShdslTxPower
					Unsigned32,
				sheShdslFramerSync
					SheShdslFramerSyncType,
				sheShdslRmtTomData
					Unsigned32,
				sheShdslDriftAlarm
					Unsigned32,
				sheShdslReceiverGain
					Unsigned32,
				sheShdslBertError
					SheShdslBertErrorType,
				sheShdslFramerOHAndDefects
					OCTET STRING,
				sheShdslRmtFwVersion
					Unsigned32,
				sheShdslUtopiaCellDelineation
					SheShdslUtopiaCellDelineationType,
				sheShdslUtopiaRxCellCnt
					Unsigned32,
				sheShdslUtopiaCellDropCnt
					Unsigned32,
				sheShdslUtopiaRxHecErrorCnt
					Unsigned32,
				sheShdslUtopiaTxCellCnt
					Unsigned32,
				sheShdslRmtNsfCusId
					Unsigned32,
				sheShdslRmtNsfCusData
					OCTET STRING,
				sheShdslLocalHandshake
					OCTET STRING,
				sheShdslRemoteHandshake
					OCTET STRING,
				sheShdslActualHandshake
					OCTET STRING,
				sheShdslRmtTxPower
					Unsigned32,
				sheShdslRmtPowerBackoff
					SheShdslRmtPowerBackoffType,
				sheShdslAutoRetrainCount
					Unsigned32,
				sheShdslEocState
					SheShdslEocStateType,
				sheShdslFramerOneSecondCnt
					OCTET STRING,
				sheShdslNtrFault
					SheShdslNtrFaultType,
				sheShdslCpeMasterCore
					SheShdslCpeMasterCoreType,
				sheShdslParametricTestResult
					SheShdslParametricTestResultType,
				sheShdslParametricTestArray
					OCTET STRING,
				sheShdslStartUpInfo
					SheShdslStartUpInfoType,
				sheShdslBisModeLocalHandshake
					OCTET STRING,
				sheShdslBisModeRemoteHandshake
					OCTET STRING,
				sheShdslBisModeActualHandshake
					OCTET STRING
			 }

--  for shdsl.bis(SGagMOShdslLineStatusTableTbl.sheShdslStartUpInfo)
-- 1.3.6.1.4.1.231.7.1.2.2.1.12.1.2.2.1.1
		sheShdslOpState OBJECT-TYPE
			SYNTAX SheShdslOpStateType
			MAX-ACCESS read-only
			STATUS current
			DESCRIPTION
				"This object identifies the high level operational state for the STU."
			::= { sheShdslLineStatusEntry 1 }

		
--   1.3.6.1.4.1.231.7.1.2.2.1.12.1.2.2.1.2
		sheShdslStartProgress OBJECT-TYPE
			SYNTAX SheShdslStartProgressType
			MAX-ACCESS read-only
			STATUS current
			DESCRIPTION
				"This object identifies the current detailed operational state of the STU."
			::= { sheShdslLineStatusEntry 2 }

		
--   1.3.6.1.4.1.231.7.1.2.2.1.12.1.2.2.1.3
		sheShdslFwRelease OBJECT-TYPE
			SYNTAX OCTET STRING (SIZE (0 | 1))
			MAX-ACCESS read-only
			STATUS current
			DESCRIPTION
				"Transceiver firmware release number."
			::= { sheShdslLineStatusEntry 3 }

		
--   1.3.6.1.4.1.231.7.1.2.2.1.12.1.2.2.1.4
		sheShdslLineSwap OBJECT-TYPE
			SYNTAX SheShdslLineSwapType
			MAX-ACCESS read-only
			STATUS current
			DESCRIPTION
				"This object indicates if the physical lines are swapped, i.e., logical channel A is connected to physical channel B. This applies to 4-wire operation only."
			::= { sheShdslLineStatusEntry 4 }

		
--   1.3.6.1.4.1.231.7.1.2.2.1.12.1.2.2.1.5
		sheShdslRmtCountryCode OBJECT-TYPE
			SYNTAX OCTET STRING (SIZE (0..1))
			MAX-ACCESS read-only
			STATUS current
			DESCRIPTION
				"This object provides the country code word, as defined in ITU-T G.991.2, for the STU at the other end of the loop. GlobespanVirata sets this to USA."
			::= { sheShdslLineStatusEntry 5 }

		
--   1.3.6.1.4.1.231.7.1.2.2.1.12.1.2.2.1.6
		sheShdslRmtEncoderA OBJECT-TYPE
			SYNTAX Integer32
			MAX-ACCESS read-only
			STATUS current
			DESCRIPTION
				"This object identifies the 21-bit value corresponding to encoder coefficient A, as defined in ITU-T G.991.2, for the STU at the other end of the loop."
			::= { sheShdslLineStatusEntry 6 }

		
--   1.3.6.1.4.1.231.7.1.2.2.1.12.1.2.2.1.7
		sheShdslRmtEncoderB OBJECT-TYPE
			SYNTAX Integer32
			MAX-ACCESS read-only
			STATUS current
			DESCRIPTION
				"This object identifies the 21-bit value corresponding to encoder coefficient B, as defined in ITU-T G.991.2, for the STU at the other end of the loop."
			::= { sheShdslLineStatusEntry 7 }

		
--   1.3.6.1.4.1.231.7.1.2.2.1.12.1.2.2.1.8
		sheShdslRmtProviderCode OBJECT-TYPE
			SYNTAX OCTET STRING (SIZE (0..1))
			MAX-ACCESS read-only
			STATUS current
			DESCRIPTION
				"This object identifies the provider code word, as defined in ITU-T G.991.2, for the STU at the other end of the loop."
			::= { sheShdslLineStatusEntry 8 }

		
--   1.3.6.1.4.1.231.7.1.2.2.1.12.1.2.2.1.9
		sheShdslLocDetect OBJECT-TYPE
			SYNTAX Unsigned32
			MAX-ACCESS read-only
			STATUS current
			DESCRIPTION
				"This object is used to determine if carrier has been lost."
			::= { sheShdslLineStatusEntry 9 }

		
--   1.3.6.1.4.1.231.7.1.2.2.1.12.1.2.2.1.10
		sheShdslTxPower OBJECT-TYPE
			SYNTAX Unsigned32
			UNITS "tenths of dBm"
			MAX-ACCESS read-only
			STATUS current
			DESCRIPTION
				"This object identifies the local STU transmit power in tenths of a dBm."
			::= { sheShdslLineStatusEntry 10 }

		
--   1.3.6.1.4.1.231.7.1.2.2.1.12.1.2.2.1.11
		sheShdslFramerSync OBJECT-TYPE
			SYNTAX SheShdslFramerSyncType
			MAX-ACCESS read-only
			STATUS current
			DESCRIPTION
				"This object returns information regarding the framer synchronization status."
			::= { sheShdslLineStatusEntry 11 }

		
--   1.3.6.1.4.1.231.7.1.2.2.1.12.1.2.2.1.12
		sheShdslRmtTomData OBJECT-TYPE
			SYNTAX Unsigned32
			MAX-ACCESS read-only
			STATUS current
			DESCRIPTION
				"This object provides vendor-provided data, as defined in ITU-T G.991.2, for the STU at the other end of the loop."
			::= { sheShdslLineStatusEntry 12 }

		
--   1.3.6.1.4.1.231.7.1.2.2.1.12.1.2.2.1.13
		sheShdslDriftAlarm OBJECT-TYPE
			SYNTAX Unsigned32
			MAX-ACCESS read-only
			STATUS current
			DESCRIPTION
				"This object identifies if the receive clock is in or out of range."
			::= { sheShdslLineStatusEntry 13 }

		
--   1.3.6.1.4.1.231.7.1.2.2.1.12.1.2.2.1.14
		sheShdslReceiverGain OBJECT-TYPE
			SYNTAX Unsigned32
			UNITS "dB"
			MAX-ACCESS read-only
			STATUS current
			DESCRIPTION
				"This object provides the total receiver gain in dB."
			::= { sheShdslLineStatusEntry 14 }

		
--   1.3.6.1.4.1.231.7.1.2.2.1.12.1.2.2.1.15
		sheShdslBertError OBJECT-TYPE
			SYNTAX SheShdslBertErrorType
			MAX-ACCESS read-only
			STATUS current
			DESCRIPTION
				"This object provides the count of bit errors since the last time the object was read, as well as the type of synchronization."
			::= { sheShdslLineStatusEntry 15 }

		
--   1.3.6.1.4.1.231.7.1.2.2.1.12.1.2.2.1.16
		sheShdslFramerOHAndDefects OBJECT-TYPE
			SYNTAX OCTET STRING (SIZE (0..10))
			MAX-ACCESS read-only
			STATUS current
			DESCRIPTION
				"This object returns overhead data. The four least significant bits contain the overhead data in the following format: bit 0 is losd, bit 1 is sega, bit 2 is ps, and bit 3 is segd."
			::= { sheShdslLineStatusEntry 16 }

		
--   1.3.6.1.4.1.231.7.1.2.2.1.12.1.2.2.1.17
		sheShdslRmtFwVersion OBJECT-TYPE
			SYNTAX Unsigned32
			MAX-ACCESS read-only
			STATUS current
			DESCRIPTION
				"This object provides the transceiver firmware release number of the STU at the other end of the loop."
			::= { sheShdslLineStatusEntry 17 }

		
--   1.3.6.1.4.1.231.7.1.2.2.1.12.1.2.2.1.18
		sheShdslUtopiaCellDelineation OBJECT-TYPE
			SYNTAX SheShdslUtopiaCellDelineationType
			MAX-ACCESS read-only
			STATUS current
			DESCRIPTION
				"This object indicates whether cell delineation has been found."
			::= { sheShdslLineStatusEntry 18 }

		
--   1.3.6.1.4.1.231.7.1.2.2.1.12.1.2.2.1.19
		sheShdslUtopiaRxCellCnt OBJECT-TYPE
			SYNTAX Unsigned32 (0..65535)
			MAX-ACCESS read-only
			STATUS current
			DESCRIPTION
				"This object indicates the number of UTOPIA cells received since the last time the object has been called. The maximum value is 0xFFFF."
			::= { sheShdslLineStatusEntry 19 }

		
--   1.3.6.1.4.1.231.7.1.2.2.1.12.1.2.2.1.20
		sheShdslUtopiaCellDropCnt OBJECT-TYPE
			SYNTAX Unsigned32 (0..255)
			MAX-ACCESS read-only
			STATUS current
			DESCRIPTION
				"This object indicates the number of UTOPIA cells dropped since the last time the object has been called. The maximum value is 0xFF."
			::= { sheShdslLineStatusEntry 20 }

		
--   1.3.6.1.4.1.231.7.1.2.2.1.12.1.2.2.1.21
		sheShdslUtopiaRxHecErrorCnt OBJECT-TYPE
			SYNTAX Unsigned32 (0..255)
			MAX-ACCESS read-only
			STATUS current
			DESCRIPTION
				"This object indicates the number of UTOPIA cells with HEC errors since the last time the object has been called. The maximum value is 0xFF."
			::= { sheShdslLineStatusEntry 21 }

		
--   1.3.6.1.4.1.231.7.1.2.2.1.12.1.2.2.1.22
		sheShdslUtopiaTxCellCnt OBJECT-TYPE
			SYNTAX Unsigned32 (0..65535)
			MAX-ACCESS read-only
			STATUS current
			DESCRIPTION
				"This object indicates the number of UTOPIA cells transmitted since the last time the object has been called. The maximum value is 0xFFFF."
			::= { sheShdslLineStatusEntry 22 }

		
--   1.3.6.1.4.1.231.7.1.2.2.1.12.1.2.2.1.23
		sheShdslRmtNsfCusId OBJECT-TYPE
			SYNTAX Unsigned32
			MAX-ACCESS read-only
			STATUS current
			DESCRIPTION
				"This object returns the customer identification that was sent by the STU at the other end of the loop."
			::= { sheShdslLineStatusEntry 23 }

		
--   1.3.6.1.4.1.231.7.1.2.2.1.12.1.2.2.1.24
		sheShdslRmtNsfCusData OBJECT-TYPE
			SYNTAX OCTET STRING (SIZE (0..4))
			MAX-ACCESS read-only
			STATUS current
			DESCRIPTION
				"This object returns non-standard format customer data that was sent by the STU at the other end of the loop."
			::= { sheShdslLineStatusEntry 24 }

		
--   1.3.6.1.4.1.231.7.1.2.2.1.12.1.2.2.1.25
		sheShdslLocalHandshake OBJECT-TYPE
			SYNTAX OCTET STRING (SIZE (0..52))
			MAX-ACCESS read-only
			STATUS current
			DESCRIPTION
				"This object provides a way to see what capabilities are supported by the local STU. A total of 26 handshake parameters are supported."
			::= { sheShdslLineStatusEntry 25 }

		
--   1.3.6.1.4.1.231.7.1.2.2.1.12.1.2.2.1.26
		sheShdslRemoteHandshake OBJECT-TYPE
			SYNTAX OCTET STRING (SIZE (0..52))
			MAX-ACCESS read-only
			STATUS current
			DESCRIPTION
				"This object provides a way to see what capabilities are supported by the STU at the other end of the loop. A total of 26 handshake parameters are supported."
			::= { sheShdslLineStatusEntry 26 }

		
--   1.3.6.1.4.1.231.7.1.2.2.1.12.1.2.2.1.27
		sheShdslActualHandshake OBJECT-TYPE
			SYNTAX OCTET STRING (SIZE (0..52))
			MAX-ACCESS read-only
			STATUS current
			DESCRIPTION
				"This object provides the results of capabilities exchanged during handshake. A total of 26 handshake parameters are supported."
			::= { sheShdslLineStatusEntry 27 }

		
--   1.3.6.1.4.1.231.7.1.2.2.1.12.1.2.2.1.28
		sheShdslRmtTxPower OBJECT-TYPE
			SYNTAX Unsigned32
			MAX-ACCESS read-only
			STATUS current
			DESCRIPTION
				"This object provides the transmit power of the STU at the other end of the loop."
			::= { sheShdslLineStatusEntry 28 }

		
--   1.3.6.1.4.1.231.7.1.2.2.1.12.1.2.2.1.29
		sheShdslRmtPowerBackoff OBJECT-TYPE
			SYNTAX SheShdslRmtPowerBackoffType
			MAX-ACCESS read-only
			STATUS current
			DESCRIPTION
				"This object indicates whether power backoff is enabled or disabled at the STU at the other end of the loop."
			::= { sheShdslLineStatusEntry 29 }

		
--   1.3.6.1.4.1.231.7.1.2.2.1.12.1.2.2.1.30
		sheShdslAutoRetrainCount OBJECT-TYPE
			SYNTAX Unsigned32
			MAX-ACCESS read-only
			STATUS current
			DESCRIPTION
				"This object indicates the number of automatic retrains. This counter is only reset when a startup is initiated."
			::= { sheShdslLineStatusEntry 30 }

		
--   1.3.6.1.4.1.231.7.1.2.2.1.12.1.2.2.1.31
		sheShdslEocState OBJECT-TYPE
			SYNTAX SheShdslEocStateType
			MAX-ACCESS read-only
			STATUS current
			DESCRIPTION
				"This object provides status information about the eoc stage."
			::= { sheShdslLineStatusEntry 31 }

		
--   1.3.6.1.4.1.231.7.1.2.2.1.12.1.2.2.1.32
		sheShdslFramerOneSecondCnt OBJECT-TYPE
			SYNTAX OCTET STRING (SIZE (0..6))
			MAX-ACCESS read-only
			STATUS current
			DESCRIPTION
				"This object provides CRC, SEGA, and LOSW defect one second error counts, and should be called every second."
			::= { sheShdslLineStatusEntry 32 }

		
--   1.3.6.1.4.1.231.7.1.2.2.1.12.1.2.2.1.33
		sheShdslNtrFault OBJECT-TYPE
			SYNTAX SheShdslNtrFaultType
			MAX-ACCESS read-only
			STATUS current
			DESCRIPTION
				"This object identifies the Network Timing Recovery Fault."
			::= { sheShdslLineStatusEntry 33 }

		
--   1.3.6.1.4.1.231.7.1.2.2.1.12.1.2.2.1.34
		sheShdslCpeMasterCore OBJECT-TYPE
			SYNTAX SheShdslCpeMasterCoreType
			MAX-ACCESS read-only
			STATUS current
			DESCRIPTION
				"The CPE master Core."
			::= { sheShdslLineStatusEntry 34 }

		
--   1.3.6.1.4.1.231.7.1.2.2.1.12.1.2.2.1.35
		sheShdslParametricTestResult OBJECT-TYPE
			SYNTAX SheShdslParametricTestResultType
			MAX-ACCESS read-only
			STATUS current
			DESCRIPTION
				"Indicates the Result of the Parametric Test conducted on the Xcvr."
			::= { sheShdslLineStatusEntry 35 }

		
--   1.3.6.1.4.1.231.7.1.2.2.1.12.1.2.2.1.36
		sheShdslParametricTestArray OBJECT-TYPE
			SYNTAX OCTET STRING (SIZE (0..256))
			MAX-ACCESS read-only
			STATUS current
			DESCRIPTION
				"Conexant parameter that indicates the Parametric Test Array."
			::= { sheShdslLineStatusEntry 36 }

		
--  for shdsl.bis(SGagMOShdslLineStatusTableTbl.sheShdslStartUpInfo)
-- 1.3.6.1.4.1.231.7.1.2.2.1.12.1.2.2.1.37
		sheShdslStartUpInfo OBJECT-TYPE
			SYNTAX SheShdslStartUpInfoType
			MAX-ACCESS read-only
			STATUS current
			DESCRIPTION
				"This conexant parameter indicates the startup mode, whether the lines comes up in bis mode or legacy mode (non bis)."
			::= { sheShdslLineStatusEntry 37 }

		
--  for shdsl.bis(SGagMOShdslLineStatusTableTbl.sheShdslBisModeLocalHandshake)
-- 1.3.6.1.4.1.231.7.1.2.2.1.12.1.2.2.1.38
		sheShdslBisModeLocalHandshake OBJECT-TYPE
			SYNTAX OCTET STRING (SIZE (0..52))
			MAX-ACCESS read-only
			STATUS current
			DESCRIPTION
				"This conexant parameter provides a way to see what rates are supported by the local STU in the form of tuples."
			::= { sheShdslLineStatusEntry 38 }

		
--   for shdsl.bis(SGagMOShdslLineStatusTableTbl)
-- 1.3.6.1.4.1.231.7.1.2.2.1.12.1.2.2.1.39
		sheShdslBisModeRemoteHandshake OBJECT-TYPE
			SYNTAX OCTET STRING (SIZE (0..52))
			MAX-ACCESS read-only
			STATUS current
			DESCRIPTION
				"This conexant parameter provides a way to see what rates are supported by the STU at other end of the loop in the form of tuples."
			::= { sheShdslLineStatusEntry 39 }

		
--   for shdsl.bis(SGagMOShdslLineStatusTableTbl)
-- 1.3.6.1.4.1.231.7.1.2.2.1.12.1.2.2.1.40
		sheShdslBisModeActualHandshake OBJECT-TYPE
			SYNTAX OCTET STRING (SIZE (0..52))
			MAX-ACCESS read-only
			STATUS current
			DESCRIPTION
				"This conexant parametetr provides the results of rates exchanged during handshake in the form of tuples."
			::= { sheShdslLineStatusEntry 40 }

		
--   1.3.6.1.4.1.231.7.1.2.2.1.12.1.2.3
		sheShdslLineParamsTable OBJECT-TYPE
			SYNTAX SEQUENCE OF SheShdslLineParamsEntry
			MAX-ACCESS not-accessible
			STATUS current
			DESCRIPTION
				"This MO is proprietary extension of RFC 3276 MIB and contains the proprietary line parameters.
				The table will only be supported for interfaces of iftype sdsl (96)!"
			::= { sheShdslMIBObjects 3 }

		
--   1.3.6.1.4.1.231.7.1.2.2.1.12.1.2.3.1
		sheShdslLineParamsEntry OBJECT-TYPE
			SYNTAX SheShdslLineParamsEntry
			MAX-ACCESS not-accessible
			STATUS current
			DESCRIPTION
				"An entry (conceptual row) in the dsShdslLineParamsTable.
				The Table is indexed by ifIndex.
				The table will only be supported for interfaces of iftype sdsl (96)!"
			INDEX { ifIndex }
			::= { sheShdslLineParamsTable 1 }

		
		SheShdslLineParamsEntry ::=
			SEQUENCE { 
				sheShdslAction
					SheSdslActionType,
				sheShdslMode
					SheShdslModeType,
				sheShdslPowerScale
					SheShdslPowerScaleType,
				sheShdslEncodeCoeffA
					SheShdslEncodeCoeffAType,
				sheShdslEncodeCoeffB
					SheShdslEncodeCoeffBType,
				sheShdslTxEOCBufferLen
					Unsigned32,
				sheShdslRxEOCBufferLen
					Unsigned32,
				sheShdslNTR
					SheShdslNTRType,
				sheShdslRxUpstreamFrameSync
					Unsigned32,
				sheShdslRxDownstreamFrameSync
					Unsigned32,
				sheShdslRxUpstreamStuffBits
					Unsigned32,
				sheShdslRxDownstreamStuffBits
					Unsigned32,
				sheShdslInitiate
					SheShdslInitiateType,
				sheShdslFramerRxClockMode
					SheShdslFramerRxClockModeType,
				sheShdslFramerRxPllMode
					SheShdslEnableModeType,
				sheShdslSerialAtmCiuBufferSize
					SheShdslSerialAtmCiuBufferSizeType,
				sheShdslTxFramerPulseDelay
					Unsigned32,
				sheShdslRxFramerPulseDelay
					Unsigned32,
				sheShdslMultiFrameMode
					SheShdslEnableModeType,
				sheShdslEnable4or6MbpsBitrate
					SheShdslEnableModeType,
				sheShdslTomDataWord1
					Unsigned32,
				sheShdslTomDataWord2
					Unsigned32,
				sheShdslTomDataWord3
					Unsigned32,
				sheShdslTomDataWord4
					Unsigned32,
				sheShdslSetReqSilenceMode
					SheShdslSetReqSilenceModeEnableType,
				sheShdslSetIndividualRates1
					Unsigned32,
				sheShdslSetIndividualRates2
					Unsigned32,
				sheShdslSetIndividualRates3
					Unsigned32,
				sheShdslSatmCellDelineation
					SheShdslEnableModeType,
				sheShdslFramerCellDropOnError
					SheShdslEnableModeType,
				sheShdslGearShiftType
					Unsigned32,
				sheShdslHsNsf
					SheShdslEnableModeType,
				sheShdslHsMaxBitsPerBaud
					SheShdslHsMaxBitsPerBaudType,
				sheShdslHsCusId
					Unsigned32,
				sheShdslHsCusData0
					Unsigned32,
				sheShdslHsCusData1
					Unsigned32,
				sheShdslHsAnnexBType
					SheShdslHsAnnexBType,
				sheShdslAutoRetrain
					SheShdslEnableModeType,
				sheShdslArCrcCheck
					SheShdslEnableModeType,
				sheShdslArFramerSyncCheck
					SheShdslEnableModeType,
				sheShdslArSnrMarginCheck
					SheShdslEnableModeType,
				sheShdslArCrcThreshold
					Unsigned32,
				sheShdslArSnrMarginThreshold
					Unsigned32,
				sheShdslArRetrainTime
					INTEGER,
				sheShdslOpStateTrapEnable
					SheShdslEnableType,
				sheShdslTxFrmrDataClkEdge
					SheShdslClkEdgeType,
				sheShdslRxFrmrDataClkEdge
					SheShdslClkEdgeType,
				sheShdslTxFrmrPulseClkEdge
					SheShdslClkEdgeType,
				sheShdslRxFrmrPulseClkEdge
					SheShdslClkEdgeType,
				sheShdslTxFrmrPulseLvl
					SheShdslPulseLvlType,
				sheShdslRxFrmrPulseLvl
					SheShdslPulseLvlType,
				sheShdslFrmrOH
					Unsigned32,
				sheShdslLoopAttenCrossingTrapEnable
					SheShdslEnableType,
				sheShdslSNRMarginCrossingTrapEnable
					SheShdslEnableType,
				sheShdslFramerOHAndDefectsTrapEnable
					SheShdslEnableType,
				sheShdslParametricTestInputFile
					OCTET STRING,
				sheShdslParamHybridLossTestStart
					Unsigned32,
				sheShdslParamHybridLossTestEnd
					Unsigned32,
				sheShdslFramerType
					SheShdslFramerType,
				sheShdslAFEType
					SheShdslAFEType,
				sheShdslUtopiaL2TxAddress
					Unsigned32,
				sheShdslUtopiaL2RxAddress
					Unsigned32,
				sheShdslUtopiaDataBusWidth
					SheShdslUtopiaDataBusWidthType,
				sheShdslPAMMode
					SheShdslPAMModeType
			 }

--   for shdsl.bis(pammode) 
-- 1.3.6.1.4.1.231.7.1.2.2.1.12.1.2.3.1.1
		sheShdslAction OBJECT-TYPE
			SYNTAX SheSdslActionType
			MAX-ACCESS read-only
			STATUS current
			DESCRIPTION
				"This object specifies actions that are used to control transceiver operation."
			DEFVAL { 0 }
			::= { sheShdslLineParamsEntry 1 }

		
--   1.3.6.1.4.1.231.7.1.2.2.1.12.1.2.3.1.2
		sheShdslMode OBJECT-TYPE
			SYNTAX SheShdslModeType
			MAX-ACCESS read-only
			STATUS current
			DESCRIPTION
				"This object specifies the operational mode of the transceiver."
			DEFVAL { 0 }
			::= { sheShdslLineParamsEntry 2 }

		
--   1.3.6.1.4.1.231.7.1.2.2.1.12.1.2.3.1.3
		sheShdslPowerScale OBJECT-TYPE
			SYNTAX SheShdslPowerScaleType
			MAX-ACCESS read-only
			STATUS current
			DESCRIPTION
				"This object is used to compensate for minor differences in transmit power between designs."
			DEFVAL { 26112 }
			::= { sheShdslLineParamsEntry 3 }

		
--   1.3.6.1.4.1.231.7.1.2.2.1.12.1.2.3.1.4
		sheShdslEncodeCoeffA OBJECT-TYPE
			SYNTAX SheShdslEncodeCoeffAType
			MAX-ACCESS read-only
			STATUS current
			DESCRIPTION
				"This object determines the value of encoder coefficient A, as defined in ITU-T G.991.2."
			DEFVAL { 366 }
			::= { sheShdslLineParamsEntry 4 }

		
--   1.3.6.1.4.1.231.7.1.2.2.1.12.1.2.3.1.5
		sheShdslEncodeCoeffB OBJECT-TYPE
			SYNTAX SheShdslEncodeCoeffBType
			MAX-ACCESS read-only
			STATUS current
			DESCRIPTION
				"This object determines the value of encoder coefficient B, as defined in ITU-T G.991.2"
			DEFVAL { 817 }
			::= { sheShdslLineParamsEntry 5 }

		
--   1.3.6.1.4.1.231.7.1.2.2.1.12.1.2.3.1.6
		sheShdslTxEOCBufferLen OBJECT-TYPE
			SYNTAX Unsigned32 (5..60)
			UNITS "multiple of 5"
			MAX-ACCESS read-only
			STATUS current
			DESCRIPTION
				"This object determines the number of bytes of EOC data that is buffered by the DSP in the transmit direction."
			DEFVAL { 5 }
			::= { sheShdslLineParamsEntry 6 }

		
--   1.3.6.1.4.1.231.7.1.2.2.1.12.1.2.3.1.7
		sheShdslRxEOCBufferLen OBJECT-TYPE
			SYNTAX Unsigned32 (5..60)
			UNITS "multiple of 5"
			MAX-ACCESS read-only
			STATUS current
			DESCRIPTION
				"This object determines the number of bytes of EOC data that is buffered by the DSP in the receive direction."
			DEFVAL { 5 }
			::= { sheShdslLineParamsEntry 7 }

		
--   1.3.6.1.4.1.231.7.1.2.2.1.12.1.2.3.1.8
		sheShdslNTR OBJECT-TYPE
			SYNTAX SheShdslNTRType
			MAX-ACCESS read-only
			STATUS current
			DESCRIPTION
				"This object defines how network-timing recovery is performed."
			DEFVAL { 1 }
			::= { sheShdslLineParamsEntry 8 }

		
--   1.3.6.1.4.1.231.7.1.2.2.1.12.1.2.3.1.9
		sheShdslRxUpstreamFrameSync OBJECT-TYPE
			SYNTAX Unsigned32
			MAX-ACCESS read-only
			STATUS current
			DESCRIPTION
				"Customer-defined value. This object defines the upstream frame sync word."
			DEFVAL { 359 }
			::= { sheShdslLineParamsEntry 9 }

		
--   1.3.6.1.4.1.231.7.1.2.2.1.12.1.2.3.1.10
		sheShdslRxDownstreamFrameSync OBJECT-TYPE
			SYNTAX Unsigned32
			MAX-ACCESS read-only
			STATUS current
			DESCRIPTION
				"This object defines the downstream frame sync word."
			DEFVAL { 359 }
			::= { sheShdslLineParamsEntry 10 }

		
--   1.3.6.1.4.1.231.7.1.2.2.1.12.1.2.3.1.11
		sheShdslRxUpstreamStuffBits OBJECT-TYPE
			SYNTAX Unsigned32
			MAX-ACCESS read-only
			STATUS current
			DESCRIPTION
				"Customer-defined value. This object defines the upstream."
			DEFVAL { 0 }
			::= { sheShdslLineParamsEntry 11 }

		
--   1.3.6.1.4.1.231.7.1.2.2.1.12.1.2.3.1.12
		sheShdslRxDownstreamStuffBits OBJECT-TYPE
			SYNTAX Unsigned32
			MAX-ACCESS read-only
			STATUS current
			DESCRIPTION
				"This object defines the downstream stuff bits."
			DEFVAL { 0 }
			::= { sheShdslLineParamsEntry 12 }

		
--   1.3.6.1.4.1.231.7.1.2.2.1.12.1.2.3.1.13
		sheShdslInitiate OBJECT-TYPE
			SYNTAX SheShdslInitiateType
			MAX-ACCESS read-only
			STATUS current
			DESCRIPTION
				"This object defines which STU initiates a startup. The default is STU-R initiates and STU-C waits."
			DEFVAL { 0 }
			::= { sheShdslLineParamsEntry 13 }

		
--   1.3.6.1.4.1.231.7.1.2.2.1.12.1.2.3.1.14
		sheShdslFramerRxClockMode OBJECT-TYPE
			SYNTAX SheShdslFramerRxClockModeType
			MAX-ACCESS read-only
			STATUS current
			DESCRIPTION
				"This object determines the source of the receive clock."
			DEFVAL { 2 }
			::= { sheShdslLineParamsEntry 14 }

		
--   1.3.6.1.4.1.231.7.1.2.2.1.12.1.2.3.1.15
		sheShdslFramerRxPllMode OBJECT-TYPE
			SYNTAX SheShdslEnableModeType
			MAX-ACCESS read-only
			STATUS current
			DESCRIPTION
				"This object enables or disables the internal PLL."
			DEFVAL { 0 }
			::= { sheShdslLineParamsEntry 15 }

		
--   1.3.6.1.4.1.231.7.1.2.2.1.12.1.2.3.1.16
		sheShdslSerialAtmCiuBufferSize OBJECT-TYPE
			SYNTAX SheShdslSerialAtmCiuBufferSizeType
			MAX-ACCESS read-only
			STATUS current
			DESCRIPTION
				"This object enables the user to set the size of the framer buffer for serial ATM operation."
			DEFVAL { 53 }
			::= { sheShdslLineParamsEntry 16 }

		
--   1.3.6.1.4.1.231.7.1.2.2.1.12.1.2.3.1.17
		sheShdslTxFramerPulseDelay OBJECT-TYPE
			SYNTAX Unsigned32 (0..7)
			MAX-ACCESS read-only
			STATUS current
			DESCRIPTION
				"This parameter is for Serial ATM applications only. It is recommended that the default value be used. For special customer configurations, a delay of up to 7 clock cycles can be specified for the transmit frame pulse."
			DEFVAL { 0 }
			::= { sheShdslLineParamsEntry 17 }

		
--   1.3.6.1.4.1.231.7.1.2.2.1.12.1.2.3.1.18
		sheShdslRxFramerPulseDelay OBJECT-TYPE
			SYNTAX Unsigned32 (0..7)
			MAX-ACCESS read-only
			STATUS current
			DESCRIPTION
				"This parameter is for Serial ATM applications only. It is recommended that the default value be used. For special customer configurations, a delay of up to 7 clock cycles can be specified for the receive frame pulse."
			DEFVAL { 0 }
			::= { sheShdslLineParamsEntry 18 }

		
--   1.3.6.1.4.1.231.7.1.2.2.1.12.1.2.3.1.19
		sheShdslMultiFrameMode OBJECT-TYPE
			SYNTAX SheShdslEnableModeType
			MAX-ACCESS read-only
			STATUS current
			DESCRIPTION
				"This object specifies the multi frame operational mode of the transceiver."
			DEFVAL { 0 }
			::= { sheShdslLineParamsEntry 19 }

		
--   1.3.6.1.4.1.231.7.1.2.2.1.12.1.2.3.1.20
		sheShdslEnable4or6MbpsBitrate OBJECT-TYPE
			SYNTAX SheShdslEnableModeType
			MAX-ACCESS read-only
			STATUS current
			DESCRIPTION
				"This object specifies the operational state of the 4_6Mbps bit rate."
			DEFVAL { 0 }
			::= { sheShdslLineParamsEntry 20 }

		
--   1.3.6.1.4.1.231.7.1.2.2.1.12.1.2.3.1.21
		sheShdslTomDataWord1 OBJECT-TYPE
			SYNTAX Unsigned32
			MAX-ACCESS read-only
			STATUS current
			DESCRIPTION
				"This object identifies one of four words of proprietary vendor data, as described in the Vendor Data section of ITU-T G.994.1.bis."
			DEFVAL { 0 }
			::= { sheShdslLineParamsEntry 21 }

		
--   1.3.6.1.4.1.231.7.1.2.2.1.12.1.2.3.1.22
		sheShdslTomDataWord2 OBJECT-TYPE
			SYNTAX Unsigned32
			MAX-ACCESS read-only
			STATUS current
			DESCRIPTION
				"This object identifies one of four words of proprietary vendor data, as described in the Vendor Data section of ITU-T G.994.1.bis."
			DEFVAL { 0 }
			::= { sheShdslLineParamsEntry 22 }

		
--   1.3.6.1.4.1.231.7.1.2.2.1.12.1.2.3.1.23
		sheShdslTomDataWord3 OBJECT-TYPE
			SYNTAX Unsigned32
			MAX-ACCESS read-only
			STATUS current
			DESCRIPTION
				"This object identifies one of four words of proprietary vendor data, as described in the Vendor Data section of ITU-T G.994.1.bis."
			DEFVAL { 0 }
			::= { sheShdslLineParamsEntry 23 }

		
--   1.3.6.1.4.1.231.7.1.2.2.1.12.1.2.3.1.24
		sheShdslTomDataWord4 OBJECT-TYPE
			SYNTAX Unsigned32
			MAX-ACCESS read-only
			STATUS current
			DESCRIPTION
				"This object identifies one of four words of proprietary vendor data, as described in the Vendor Data section of ITU-T G.994.1.bis."
			DEFVAL { 0 }
			::= { sheShdslLineParamsEntry 24 }

		
--   1.3.6.1.4.1.231.7.1.2.2.1.12.1.2.3.1.25
		sheShdslSetReqSilenceMode OBJECT-TYPE
			SYNTAX SheShdslSetReqSilenceModeEnableType
			MAX-ACCESS read-only
			STATUS current
			DESCRIPTION
				"This object enables a silent mode for the STU at the opposite end of the loop for approximately one minute. During the silent period, the STU that requested the silent mode could perform whatever operations it wants and the STU at the opposite end will remain in handshake."
			DEFVAL { 0 }
			::= { sheShdslLineParamsEntry 25 }

		
--   1.3.6.1.4.1.231.7.1.2.2.1.12.1.2.3.1.26
		sheShdslSetIndividualRates1 OBJECT-TYPE
			SYNTAX Unsigned32 (0..65535)
			MAX-ACCESS read-only
			STATUS current
			DESCRIPTION
				"This item enables the user to individually enable or disable base rates for N=1 through N=16. The default is all rates enabled."
			DEFVAL { 65535 }
			::= { sheShdslLineParamsEntry 26 }

		
--   1.3.6.1.4.1.231.7.1.2.2.1.12.1.2.3.1.27
		sheShdslSetIndividualRates2 OBJECT-TYPE
			SYNTAX Unsigned32 (0..65535)
			MAX-ACCESS read-only
			STATUS current
			DESCRIPTION
				"This item enables the user to individually enable or disable base rates for N=17 through N=32. The default is all rates enabled."
			DEFVAL { 65535 }
			::= { sheShdslLineParamsEntry 27 }

		
--   1.3.6.1.4.1.231.7.1.2.2.1.12.1.2.3.1.28
		sheShdslSetIndividualRates3 OBJECT-TYPE
			SYNTAX Unsigned32 (0..15)
			MAX-ACCESS read-only
			STATUS current
			DESCRIPTION
				"This item enables the user to individually enable or disable base rates for N=33 through N=36. The default is all rates enabled."
			DEFVAL { 15 }
			::= { sheShdslLineParamsEntry 28 }

		
--   1.3.6.1.4.1.231.7.1.2.2.1.12.1.2.3.1.29
		sheShdslSatmCellDelineation OBJECT-TYPE
			SYNTAX SheShdslEnableModeType
			MAX-ACCESS read-only
			STATUS current
			DESCRIPTION
				"This object enables the user to enable or disable cell delineation for serial ATM operation. This parameter should be set before a startup."
			DEFVAL { 0 }
			::= { sheShdslLineParamsEntry 29 }

		
--   1.3.6.1.4.1.231.7.1.2.2.1.12.1.2.3.1.30
		sheShdslFramerCellDropOnError OBJECT-TYPE
			SYNTAX SheShdslEnableModeType
			MAX-ACCESS read-only
			STATUS current
			DESCRIPTION
				"This object determines whether cells are dropped, i.e., not passed to the host, or not dropped, i.e., passed to the host. This object must be set prior to startup."
			DEFVAL { 0 }
			::= { sheShdslLineParamsEntry 30 }

		
--   1.3.6.1.4.1.231.7.1.2.2.1.12.1.2.3.1.31
		sheShdslGearShiftType OBJECT-TYPE
			SYNTAX Unsigned32 (0..1)
			MAX-ACCESS read-only
			STATUS current
			DESCRIPTION
				"This object specifies the Gear Shift Type."
			DEFVAL { 0 }
			::= { sheShdslLineParamsEntry 31 }

		
--   1.3.6.1.4.1.231.7.1.2.2.1.12.1.2.3.1.32
		sheShdslHsNsf OBJECT-TYPE
			SYNTAX SheShdslEnableModeType
			MAX-ACCESS read-only
			STATUS current
			DESCRIPTION
				"This object enables or disables nonstandard Information fields for MP, MS, CL, and CLR messages, as defined in ITU-T G.994.1.bis."
			DEFVAL { 0 }
			::= { sheShdslLineParamsEntry 32 }

		
--   1.3.6.1.4.1.231.7.1.2.2.1.12.1.2.3.1.33
		sheShdslHsMaxBitsPerBaud OBJECT-TYPE
			SYNTAX SheShdslHsMaxBitsPerBaudType
			MAX-ACCESS read-only
			STATUS current
			DESCRIPTION
				"This object specifies the maximum bit per baud."
			DEFVAL { 3 }
			::= { sheShdslLineParamsEntry 33 }

		
--   1.3.6.1.4.1.231.7.1.2.2.1.12.1.2.3.1.34
		sheShdslHsCusId OBJECT-TYPE
			SYNTAX Unsigned32
			MAX-ACCESS read-only
			STATUS current
			DESCRIPTION
				"This object identifies the customer identification during handshaking, as described in ITU-T G.994.1.bis."
			DEFVAL { 0 }
			::= { sheShdslLineParamsEntry 34 }

		
--   1.3.6.1.4.1.231.7.1.2.2.1.12.1.2.3.1.35
		sheShdslHsCusData0 OBJECT-TYPE
			SYNTAX Unsigned32
			MAX-ACCESS read-only
			STATUS current
			DESCRIPTION
				"This object identifies two words of customer data during handshaking, as defined in ITU-T G.994.1.bis."
			DEFVAL { 0 }
			::= { sheShdslLineParamsEntry 35 }

		
--   1.3.6.1.4.1.231.7.1.2.2.1.12.1.2.3.1.36
		sheShdslHsCusData1 OBJECT-TYPE
			SYNTAX Unsigned32
			MAX-ACCESS read-only
			STATUS current
			DESCRIPTION
				"This object identifies two words of customer data during handshaking, as defined in ITU-T G.994.1.bis."
			DEFVAL { 0 }
			::= { sheShdslLineParamsEntry 36 }

		
--   1.3.6.1.4.1.231.7.1.2.2.1.12.1.2.3.1.37
		sheShdslHsAnnexBType OBJECT-TYPE
			SYNTAX SheShdslHsAnnexBType
			MAX-ACCESS read-only
			STATUS current
			DESCRIPTION
				"This object allows the customer to choose between support for Annex B, Annex B with Access Network Frequency Plan (ANFP), or both."
			DEFVAL { 1 }
			::= { sheShdslLineParamsEntry 37 }

		
--   1.3.6.1.4.1.231.7.1.2.2.1.12.1.2.3.1.38
		sheShdslAutoRetrain OBJECT-TYPE
			SYNTAX SheShdslEnableModeType
			MAX-ACCESS read-only
			STATUS current
			DESCRIPTION
				"Enables or disables auto-retrain."
			DEFVAL { 0 }
			::= { sheShdslLineParamsEntry 38 }

		
--   1.3.6.1.4.1.231.7.1.2.2.1.12.1.2.3.1.39
		sheShdslArCrcCheck OBJECT-TYPE
			SYNTAX SheShdslEnableModeType
			MAX-ACCESS read-only
			STATUS current
			DESCRIPTION
				"Enables or disables auto-retrain based on CRC errors."
			DEFVAL { 0 }
			::= { sheShdslLineParamsEntry 39 }

		
--   1.3.6.1.4.1.231.7.1.2.2.1.12.1.2.3.1.40
		sheShdslArFramerSyncCheck OBJECT-TYPE
			SYNTAX SheShdslEnableModeType
			MAX-ACCESS read-only
			STATUS current
			DESCRIPTION
				"Enables or disables auto-retrain based on framer synchronization."
			DEFVAL { 0 }
			::= { sheShdslLineParamsEntry 40 }

		
--   1.3.6.1.4.1.231.7.1.2.2.1.12.1.2.3.1.41
		sheShdslArSnrMarginCheck OBJECT-TYPE
			SYNTAX SheShdslEnableModeType
			MAX-ACCESS read-only
			STATUS current
			DESCRIPTION
				"Enables or disables auto-retrain based on whether the S/N margin falls below a preset threshold."
			DEFVAL { 0 }
			::= { sheShdslLineParamsEntry 41 }

		
--   1.3.6.1.4.1.231.7.1.2.2.1.12.1.2.3.1.42
		sheShdslArCrcThreshold OBJECT-TYPE
			SYNTAX Unsigned32 (0..1024)
			MAX-ACCESS read-only
			STATUS current
			DESCRIPTION
				"Sets the threshold for the number of frames with CRC errors for autoretrain."
			DEFVAL { 1 }
			::= { sheShdslLineParamsEntry 42 }

		
--   1.3.6.1.4.1.231.7.1.2.2.1.12.1.2.3.1.43
		sheShdslArSnrMarginThreshold OBJECT-TYPE
			SYNTAX Unsigned32 (1..6)
			MAX-ACCESS read-only
			STATUS current
			DESCRIPTION
				"Set the margin threshold for autoretrain."
			DEFVAL { 1 }
			::= { sheShdslLineParamsEntry 43 }

		
--   1.3.6.1.4.1.231.7.1.2.2.1.12.1.2.3.1.44
		sheShdslArRetrainTime OBJECT-TYPE
			SYNTAX INTEGER (1..10)
			MAX-ACCESS read-only
			STATUS current
			DESCRIPTION
				"Sets the time over which the autoretrain parameters must be outside their normal ranges, so that an auto-retrain occurs."
			DEFVAL { 3 }
			::= { sheShdslLineParamsEntry 44 }

		
--   1.3.6.1.4.1.231.7.1.2.2.1.12.1.2.3.1.45
		sheShdslOpStateTrapEnable OBJECT-TYPE
			SYNTAX SheShdslEnableType
			MAX-ACCESS read-only
			STATUS current
			DESCRIPTION
				"Enables/disables trap indicating a change in op state."
			DEFVAL { 2 }
			::= { sheShdslLineParamsEntry 45 }

		
--   1.3.6.1.4.1.231.7.1.2.2.1.12.1.2.3.1.46
		sheShdslTxFrmrDataClkEdge OBJECT-TYPE
			SYNTAX SheShdslClkEdgeType
			MAX-ACCESS read-only
			STATUS current
			DESCRIPTION
				"This parameter is for Serial ATM applications only. It is recommended that the default value be used. For special customer configurations, transmit data can be sampled upon either rising or falling edge of the transmit clock."
			DEFVAL { 0 }
			::= { sheShdslLineParamsEntry 46 }

		
--   1.3.6.1.4.1.231.7.1.2.2.1.12.1.2.3.1.47
		sheShdslRxFrmrDataClkEdge OBJECT-TYPE
			SYNTAX SheShdslClkEdgeType
			MAX-ACCESS read-only
			STATUS current
			DESCRIPTION
				"This parameter is for Serial ATM applications only. It is recommended that the default value be used. For special customer configurations, receive data can be valid upon either rising or falling edge of the receive clock."
			DEFVAL { 1 }
			::= { sheShdslLineParamsEntry 47 }

		
--   1.3.6.1.4.1.231.7.1.2.2.1.12.1.2.3.1.48
		sheShdslTxFrmrPulseClkEdge OBJECT-TYPE
			SYNTAX SheShdslClkEdgeType
			MAX-ACCESS read-only
			STATUS current
			DESCRIPTION
				"This parameter is for Serial ATM applications only. It is recommended that the default value be used. For special customer configurations, the transmit frame pulse can be active upon either rising or falling edge."
			DEFVAL { 0 }
			::= { sheShdslLineParamsEntry 48 }

		
--   1.3.6.1.4.1.231.7.1.2.2.1.12.1.2.3.1.49
		sheShdslRxFrmrPulseClkEdge OBJECT-TYPE
			SYNTAX SheShdslClkEdgeType
			MAX-ACCESS read-only
			STATUS current
			DESCRIPTION
				"This parameter is for Serial ATM applications only. It is recommended that the default value be used. For special customer configurations, the transmit frame pulse can be active upon either rising or falling edge."
			DEFVAL { 1 }
			::= { sheShdslLineParamsEntry 49 }

		
--   1.3.6.1.4.1.231.7.1.2.2.1.12.1.2.3.1.50
		sheShdslTxFrmrPulseLvl OBJECT-TYPE
			SYNTAX SheShdslPulseLvlType
			MAX-ACCESS read-only
			STATUS current
			DESCRIPTION
				"This parameter is for Serial ATM applications only. It is recommended that the default value be used. For special customer configurations, the transmit frame pulse can be either active high (1) or active low (0)."
			DEFVAL { 1 }
			::= { sheShdslLineParamsEntry 50 }

		
--   1.3.6.1.4.1.231.7.1.2.2.1.12.1.2.3.1.51
		sheShdslRxFrmrPulseLvl OBJECT-TYPE
			SYNTAX SheShdslPulseLvlType
			MAX-ACCESS read-only
			STATUS current
			DESCRIPTION
				"This parameter is for Serial ATM applications only. It is recommended that the default value be used. For special customer configurations, the transmit frame pulse can be either active high (1) or active low (0)."
			DEFVAL { 1 }
			::= { sheShdslLineParamsEntry 51 }

		
--   1.3.6.1.4.1.231.7.1.2.2.1.12.1.2.3.1.52
		sheShdslFrmrOH OBJECT-TYPE
			SYNTAX Unsigned32 (0..65535)
			MAX-ACCESS read-only
			STATUS current
			DESCRIPTION
				"This object specifies framer OverHead Channel."
			DEFVAL { 0 }
			::= { sheShdslLineParamsEntry 52 }

		
--   1.3.6.1.4.1.231.7.1.2.2.1.12.1.2.3.1.53
		sheShdslLoopAttenCrossingTrapEnable OBJECT-TYPE
			SYNTAX SheShdslEnableType
			MAX-ACCESS read-only
			STATUS current
			DESCRIPTION
				"This Parameter enables or disables the Trap for Loop Attenuation Threshold crossing."
			DEFVAL { 1 }
			::= { sheShdslLineParamsEntry 53 }

		
--   1.3.6.1.4.1.231.7.1.2.2.1.12.1.2.3.1.54
		sheShdslSNRMarginCrossingTrapEnable OBJECT-TYPE
			SYNTAX SheShdslEnableType
			MAX-ACCESS read-only
			STATUS current
			DESCRIPTION
				"This Parameter enables or disables the Trap for SNR Margin Threshold crossing."
			DEFVAL { 1 }
			::= { sheShdslLineParamsEntry 54 }

		
--   1.3.6.1.4.1.231.7.1.2.2.1.12.1.2.3.1.55
		sheShdslFramerOHAndDefectsTrapEnable OBJECT-TYPE
			SYNTAX SheShdslEnableType
			MAX-ACCESS read-only
			STATUS current
			DESCRIPTION
				"This Parameter enables or disables the Trap for Framer Overhead and Defects."
			DEFVAL { 1 }
			::= { sheShdslLineParamsEntry 55 }

		
--   1.3.6.1.4.1.231.7.1.2.2.1.12.1.2.3.1.56
		sheShdslParametricTestInputFile OBJECT-TYPE
			SYNTAX OCTET STRING (SIZE (0..56))
			MAX-ACCESS read-only
			STATUS current
			DESCRIPTION
				"Indicates Name of the Input file from which to take the Mask Array Size, lower and upper mask Array. Null string means no file is specified."
			::= { sheShdslLineParamsEntry 56 }

		
--   1.3.6.1.4.1.231.7.1.2.2.1.12.1.2.3.1.57
		sheShdslParamHybridLossTestStart OBJECT-TYPE
			SYNTAX Unsigned32 (0..255)
			MAX-ACCESS read-only
			STATUS current
			DESCRIPTION
				"Indicates Start bin for range of bins to be measured. The default value mentioned is an indicative value only, for exact value refer to document number DO-400523-AN and DO-401163-AN."
			DEFVAL { 2 }
			::= { sheShdslLineParamsEntry 57 }

		
--   1.3.6.1.4.1.231.7.1.2.2.1.12.1.2.3.1.58
		sheShdslParamHybridLossTestEnd OBJECT-TYPE
			SYNTAX Unsigned32 (0..255)
			MAX-ACCESS read-only
			STATUS current
			DESCRIPTION
				"Indicates End bin for range of bins to be measured.  The default value mentioned is an indicative value only."
			DEFVAL { 40 }
			::= { sheShdslLineParamsEntry 58 }

		
--   1.3.6.1.4.1.231.7.1.2.2.1.12.1.2.3.1.59
		sheShdslFramerType OBJECT-TYPE
			SYNTAX SheShdslFramerType
			MAX-ACCESS read-only
			STATUS current
			DESCRIPTION
				"This object defines which type of data interface type is used. Note that the non-default values only apply to Conexant chips that support serial interfaces."
			::= { sheShdslLineParamsEntry 59 }

		
--   1.3.6.1.4.1.231.7.1.2.2.1.12.1.2.3.1.60
		sheShdslAFEType OBJECT-TYPE
			SYNTAX SheShdslAFEType
			MAX-ACCESS read-only
			STATUS current
			DESCRIPTION
				"This objects defines which AFE is being used."
			::= { sheShdslLineParamsEntry 60 }

		
--   1.3.6.1.4.1.231.7.1.2.2.1.12.1.2.3.1.61
		sheShdslUtopiaL2TxAddress OBJECT-TYPE
			SYNTAX Unsigned32
			MAX-ACCESS read-only
			STATUS current
			DESCRIPTION
				"This object selects the appropriate UTOPIA Level 2 address for the transmit interface."
			::= { sheShdslLineParamsEntry 61 }

		
--   1.3.6.1.4.1.231.7.1.2.2.1.12.1.2.3.1.62
		sheShdslUtopiaL2RxAddress OBJECT-TYPE
			SYNTAX Unsigned32
			MAX-ACCESS read-only
			STATUS current
			DESCRIPTION
				"This object selects the appropriate UTOPIA Level 2 address for the receive interface."
			::= { sheShdslLineParamsEntry 62 }

		
--   1.3.6.1.4.1.231.7.1.2.2.1.12.1.2.3.1.63
		sheShdslUtopiaDataBusWidth OBJECT-TYPE
			SYNTAX SheShdslUtopiaDataBusWidthType
			MAX-ACCESS read-only
			STATUS current
			DESCRIPTION
				"This parameter is used to specify width of UTOPIA data bus."
			::= { sheShdslLineParamsEntry 63 }

		
--   for shdsl.bis(pammode)
-- 1.3.6.1.4.1.231.7.1.2.2.1.12.1.2.3.1.64
		sheShdslPAMMode OBJECT-TYPE
			SYNTAX SheShdslPAMModeType
			MAX-ACCESS read-only
			STATUS current
			DESCRIPTION
				"This parameter is used to configure the PAM mode value for startup."
			DEFVAL { 0 }
			::= { sheShdslLineParamsEntry 64 }

		
--   1.3.6.1.4.1.231.7.1.2.2.1.12.1.2.4
		sheShdslLineParamsControl OBJECT IDENTIFIER ::= { sheShdslMIBObjects 4 }

		
--   1.3.6.1.4.1.231.7.1.2.2.1.12.1.2.4.1
		sheShdslLineParamsControlRequest OBJECT-TYPE
			SYNTAX SheShdslControlRequestType
			MAX-ACCESS read-write
			STATUS current
			DESCRIPTION
				"modifyShdslLineParamsEntry
				
				a complete set of configurable parameters according the sheShdlsLinParamsControl-group."
			::= { sheShdslLineParamsControl 1 }

		
--   1.3.6.1.4.1.231.7.1.2.2.1.12.1.2.4.2
		sheShdslLineParamsControlIndex OBJECT-TYPE
			SYNTAX InterfaceIndex
			MAX-ACCESS read-write
			STATUS current
			DESCRIPTION
				"Index of the modified entry."
			::= { sheShdslLineParamsControl 2 }

		
--   1.3.6.1.4.1.231.7.1.2.2.1.12.1.2.4.3
		sheShdslLineParamsControlStatus OBJECT-TYPE
			SYNTAX SheControlStatusType
			MAX-ACCESS read-only
			STATUS current
			DESCRIPTION
				"The status of a user command. 
				"
			::= { sheShdslLineParamsControl 3 }

		
--   1.3.6.1.4.1.231.7.1.2.2.1.12.1.2.4.4
		sheShdslLineParamsControlTimer OBJECT-TYPE
			SYNTAX Gauge32
			MAX-ACCESS read-only
			STATUS current
			DESCRIPTION
				"The maximum wait time for the manager for a long running user command. 
				"
			::= { sheShdslLineParamsControl 4 }

		
--   1.3.6.1.4.1.231.7.1.2.2.1.12.1.2.4.5
		sheShdslLineParamsControlReqResult OBJECT-TYPE
			SYNTAX SheShdslControlRequestResultType
			MAX-ACCESS read-only
			STATUS current
			DESCRIPTION
				"The result of the last user command."
			::= { sheShdslLineParamsControl 5 }

		
--   1.3.6.1.4.1.231.7.1.2.2.1.12.1.2.4.6
		sheShdslLineParamsControlTimeStamp OBJECT-TYPE
			SYNTAX Unsigned32
			UNITS "sec"
			MAX-ACCESS read-only
			STATUS current
			DESCRIPTION
				"The time stamp of the last command (end of command)."
			::= { sheShdslLineParamsControl 6 }

		
--   1.3.6.1.4.1.231.7.1.2.2.1.12.1.2.4.7
		sheShdslLineParamsControlAction OBJECT-TYPE
			SYNTAX SheSdslActionType
			MAX-ACCESS read-write
			STATUS current
			DESCRIPTION
				"Look at Table."
			::= { sheShdslLineParamsControl 7 }

		
--   1.3.6.1.4.1.231.7.1.2.2.1.12.1.2.4.8
		sheShdslLineParamsControlMode OBJECT-TYPE
			SYNTAX SheShdslModeType
			MAX-ACCESS read-write
			STATUS current
			DESCRIPTION
				"Look at table."
			::= { sheShdslLineParamsControl 8 }

		
--   1.3.6.1.4.1.231.7.1.2.2.1.12.1.2.4.9
		sheShdslLineParamsControlPowerScale OBJECT-TYPE
			SYNTAX Unsigned32
			MAX-ACCESS read-write
			STATUS current
			DESCRIPTION
				"Look at table."
			::= { sheShdslLineParamsControl 9 }

		
--   1.3.6.1.4.1.231.7.1.2.2.1.12.1.2.4.10
		sheShdslLineParamsControlEncodeCoeffA OBJECT-TYPE
			SYNTAX SheShdslEncodeCoeffAType
			MAX-ACCESS read-write
			STATUS current
			DESCRIPTION
				"Look at table."
			::= { sheShdslLineParamsControl 10 }

		
--   1.3.6.1.4.1.231.7.1.2.2.1.12.1.2.4.11
		sheShdslLineParamsControlEncodeCoeffB OBJECT-TYPE
			SYNTAX SheShdslEncodeCoeffBType
			MAX-ACCESS read-write
			STATUS current
			DESCRIPTION
				"Look at table."
			::= { sheShdslLineParamsControl 11 }

		
--   1.3.6.1.4.1.231.7.1.2.2.1.12.1.2.4.12
		sheShdslLineParamsControlTxEOCBufferLen OBJECT-TYPE
			SYNTAX Unsigned32 (5..60)
			UNITS "multiple of 5"
			MAX-ACCESS read-write
			STATUS current
			DESCRIPTION
				"Look at table."
			::= { sheShdslLineParamsControl 12 }

		
--   1.3.6.1.4.1.231.7.1.2.2.1.12.1.2.4.13
		sheShdslLineParamsControlRxEOCBufferLen OBJECT-TYPE
			SYNTAX Unsigned32 (5..60)
			UNITS "multiple of 5"
			MAX-ACCESS read-write
			STATUS current
			DESCRIPTION
				"Look at table."
			::= { sheShdslLineParamsControl 13 }

		
--   1.3.6.1.4.1.231.7.1.2.2.1.12.1.2.4.14
		sheShdslLineParamsControlNTR OBJECT-TYPE
			SYNTAX SheShdslNTRType
			MAX-ACCESS read-write
			STATUS current
			DESCRIPTION
				"Look at table."
			::= { sheShdslLineParamsControl 14 }

		
--   1.3.6.1.4.1.231.7.1.2.2.1.12.1.2.4.15
		sheShdslLineParamsControlRxUpstreamFrameSync OBJECT-TYPE
			SYNTAX Unsigned32
			MAX-ACCESS read-write
			STATUS current
			DESCRIPTION
				"Look at table."
			::= { sheShdslLineParamsControl 15 }

		
--   1.3.6.1.4.1.231.7.1.2.2.1.12.1.2.4.16
		sheShdslLineParamsControlRxDownstreamFrameSync OBJECT-TYPE
			SYNTAX Unsigned32
			MAX-ACCESS read-write
			STATUS current
			DESCRIPTION
				"Look at table."
			::= { sheShdslLineParamsControl 16 }

		
--   1.3.6.1.4.1.231.7.1.2.2.1.12.1.2.4.17
		sheShdslLineParamsControlRxUpstreamStuffBits OBJECT-TYPE
			SYNTAX Unsigned32
			MAX-ACCESS read-write
			STATUS current
			DESCRIPTION
				"Look at table."
			::= { sheShdslLineParamsControl 17 }

		
--   1.3.6.1.4.1.231.7.1.2.2.1.12.1.2.4.18
		sheShdslLineParamsControlRxDownstreamStuffBits OBJECT-TYPE
			SYNTAX Unsigned32
			MAX-ACCESS read-write
			STATUS current
			DESCRIPTION
				"Look at table."
			::= { sheShdslLineParamsControl 18 }

		
--   1.3.6.1.4.1.231.7.1.2.2.1.12.1.2.4.19
		sheShdslLineParamsControlInitiate OBJECT-TYPE
			SYNTAX SheShdslInitiateType
			MAX-ACCESS read-write
			STATUS current
			DESCRIPTION
				"Look at table."
			::= { sheShdslLineParamsControl 19 }

		
--   1.3.6.1.4.1.231.7.1.2.2.1.12.1.2.4.20
		sheShdslLineParamsControlFramerRxClockMode OBJECT-TYPE
			SYNTAX SheShdslFramerRxClockModeType
			MAX-ACCESS read-write
			STATUS current
			DESCRIPTION
				"Look at table."
			::= { sheShdslLineParamsControl 20 }

		
--   1.3.6.1.4.1.231.7.1.2.2.1.12.1.2.4.21
		sheShdslLineParamsControlFramerRxPllMode OBJECT-TYPE
			SYNTAX SheShdslEnableModeType
			MAX-ACCESS read-write
			STATUS current
			DESCRIPTION
				"Look at table."
			::= { sheShdslLineParamsControl 21 }

		
--   1.3.6.1.4.1.231.7.1.2.2.1.12.1.2.4.22
		sheShdslLineParamsControlSerialAtmCiuBufferSize OBJECT-TYPE
			SYNTAX SheShdslSerialAtmCiuBufferSizeType
			MAX-ACCESS read-write
			STATUS current
			DESCRIPTION
				"Look at table."
			::= { sheShdslLineParamsControl 22 }

		
--   1.3.6.1.4.1.231.7.1.2.2.1.12.1.2.4.23
		sheShdslLineParamsControlTxFramerPulseDelay OBJECT-TYPE
			SYNTAX Unsigned32 (0..7)
			MAX-ACCESS read-write
			STATUS current
			DESCRIPTION
				"Look at table."
			::= { sheShdslLineParamsControl 23 }

		
--   1.3.6.1.4.1.231.7.1.2.2.1.12.1.2.4.24
		sheShdslLineParamsControlRxFramerPulseDelay OBJECT-TYPE
			SYNTAX Unsigned32 (0..7)
			MAX-ACCESS read-write
			STATUS current
			DESCRIPTION
				"Look at table."
			::= { sheShdslLineParamsControl 24 }

		
--   1.3.6.1.4.1.231.7.1.2.2.1.12.1.2.4.25
		sheShdslLineParamsControlMultiFrameMode OBJECT-TYPE
			SYNTAX SheShdslEnableModeType
			MAX-ACCESS read-write
			STATUS current
			DESCRIPTION
				"Look at table."
			::= { sheShdslLineParamsControl 25 }

		
--   1.3.6.1.4.1.231.7.1.2.2.1.12.1.2.4.26
		sheShdslLineParamsControlEnable4or6MbpsBitrate OBJECT-TYPE
			SYNTAX SheShdslEnableModeType
			MAX-ACCESS read-write
			STATUS current
			DESCRIPTION
				"Look at table."
			::= { sheShdslLineParamsControl 26 }

		
--   1.3.6.1.4.1.231.7.1.2.2.1.12.1.2.4.27
		sheShdslLineParamsControlTomDataWord1 OBJECT-TYPE
			SYNTAX Unsigned32
			MAX-ACCESS read-write
			STATUS current
			DESCRIPTION
				"Look at table."
			::= { sheShdslLineParamsControl 27 }

		
--   1.3.6.1.4.1.231.7.1.2.2.1.12.1.2.4.28
		sheShdslLineParamsControlTomDataWord2 OBJECT-TYPE
			SYNTAX Unsigned32
			MAX-ACCESS read-write
			STATUS current
			DESCRIPTION
				"Look at table."
			::= { sheShdslLineParamsControl 28 }

		
--   1.3.6.1.4.1.231.7.1.2.2.1.12.1.2.4.29
		sheShdslLineParamsControlTomDataWord3 OBJECT-TYPE
			SYNTAX Unsigned32
			MAX-ACCESS read-write
			STATUS current
			DESCRIPTION
				"Look at table."
			::= { sheShdslLineParamsControl 29 }

		
--   1.3.6.1.4.1.231.7.1.2.2.1.12.1.2.4.30
		sheShdslLineParamsControlTomDataWord4 OBJECT-TYPE
			SYNTAX Unsigned32
			MAX-ACCESS read-write
			STATUS current
			DESCRIPTION
				"Look at table."
			::= { sheShdslLineParamsControl 30 }

		
--   1.3.6.1.4.1.231.7.1.2.2.1.12.1.2.4.31
		sheShdslLineParamsControlSetReqSilenceMode OBJECT-TYPE
			SYNTAX SheShdslSetReqSilenceModeEnableType
			MAX-ACCESS read-write
			STATUS current
			DESCRIPTION
				"Look at table."
			::= { sheShdslLineParamsControl 31 }

		
--   1.3.6.1.4.1.231.7.1.2.2.1.12.1.2.4.32
		sheShdslLineParamsControlSetIndividualRates1 OBJECT-TYPE
			SYNTAX Unsigned32 (0..65535)
			MAX-ACCESS read-write
			STATUS current
			DESCRIPTION
				"Look at table."
			::= { sheShdslLineParamsControl 32 }

		
--   1.3.6.1.4.1.231.7.1.2.2.1.12.1.2.4.33
		sheShdslLineParamsControlSetIndividualRates2 OBJECT-TYPE
			SYNTAX Unsigned32 (0..65535)
			MAX-ACCESS read-write
			STATUS current
			DESCRIPTION
				"Look at table."
			::= { sheShdslLineParamsControl 33 }

		
--   1.3.6.1.4.1.231.7.1.2.2.1.12.1.2.4.34
		sheShdslLineParamsControlSetIndividualRates3 OBJECT-TYPE
			SYNTAX Unsigned32 (0..15)
			MAX-ACCESS read-write
			STATUS current
			DESCRIPTION
				"Look at table."
			::= { sheShdslLineParamsControl 34 }

		
--   1.3.6.1.4.1.231.7.1.2.2.1.12.1.2.4.35
		sheShdslLineParamsControlSatmCellDelineation OBJECT-TYPE
			SYNTAX SheShdslEnableModeType
			MAX-ACCESS read-write
			STATUS current
			DESCRIPTION
				"Look at table."
			::= { sheShdslLineParamsControl 35 }

		
--   1.3.6.1.4.1.231.7.1.2.2.1.12.1.2.4.36
		sheShdslLineParamsControlFramerCellDropOnError OBJECT-TYPE
			SYNTAX SheShdslEnableModeType
			MAX-ACCESS read-write
			STATUS current
			DESCRIPTION
				"Look at table."
			::= { sheShdslLineParamsControl 36 }

		
--   1.3.6.1.4.1.231.7.1.2.2.1.12.1.2.4.37
		sheShdslLineParamsControlGearShiftType OBJECT-TYPE
			SYNTAX Unsigned32 (0..1)
			MAX-ACCESS read-write
			STATUS current
			DESCRIPTION
				"Look at table."
			::= { sheShdslLineParamsControl 37 }

		
--   1.3.6.1.4.1.231.7.1.2.2.1.12.1.2.4.38
		sheShdslLineParamsControlHsNsf OBJECT-TYPE
			SYNTAX SheShdslEnableModeType
			MAX-ACCESS read-write
			STATUS current
			DESCRIPTION
				"Look at table."
			::= { sheShdslLineParamsControl 38 }

		
--   1.3.6.1.4.1.231.7.1.2.2.1.12.1.2.4.39
		sheShdslLineParamsControlHsMaxBitsPerBaud OBJECT-TYPE
			SYNTAX SheShdslHsMaxBitsPerBaudType
			MAX-ACCESS read-write
			STATUS current
			DESCRIPTION
				"Look at table."
			::= { sheShdslLineParamsControl 39 }

		
--   1.3.6.1.4.1.231.7.1.2.2.1.12.1.2.4.40
		sheShdslLineParamsControlHsCusId OBJECT-TYPE
			SYNTAX Unsigned32
			MAX-ACCESS read-write
			STATUS current
			DESCRIPTION
				"Look at table."
			::= { sheShdslLineParamsControl 40 }

		
--   1.3.6.1.4.1.231.7.1.2.2.1.12.1.2.4.41
		sheShdslLineParamsControlHsCusData0 OBJECT-TYPE
			SYNTAX Unsigned32
			MAX-ACCESS read-write
			STATUS current
			DESCRIPTION
				"Look at table."
			::= { sheShdslLineParamsControl 41 }

		
--   1.3.6.1.4.1.231.7.1.2.2.1.12.1.2.4.42
		sheShdslLineParamsControlHsCusData1 OBJECT-TYPE
			SYNTAX Unsigned32
			MAX-ACCESS read-write
			STATUS current
			DESCRIPTION
				"Look at table."
			::= { sheShdslLineParamsControl 42 }

		
--   1.3.6.1.4.1.231.7.1.2.2.1.12.1.2.4.43
		sheShdslLineParamsControlHsAnnexBType OBJECT-TYPE
			SYNTAX SheShdslHsAnnexBType
			MAX-ACCESS read-write
			STATUS current
			DESCRIPTION
				"Look at table."
			::= { sheShdslLineParamsControl 43 }

		
--   1.3.6.1.4.1.231.7.1.2.2.1.12.1.2.4.44
		sheShdslLineParamsControlAutoRetrain OBJECT-TYPE
			SYNTAX SheShdslEnableModeType
			MAX-ACCESS read-write
			STATUS current
			DESCRIPTION
				"Look at table."
			::= { sheShdslLineParamsControl 44 }

		
--   1.3.6.1.4.1.231.7.1.2.2.1.12.1.2.4.45
		sheShdslLineParamsControlArCrcCheck OBJECT-TYPE
			SYNTAX SheShdslEnableModeType
			MAX-ACCESS read-write
			STATUS current
			DESCRIPTION
				"Look at table."
			::= { sheShdslLineParamsControl 45 }

		
--   1.3.6.1.4.1.231.7.1.2.2.1.12.1.2.4.46
		sheShdslLineParamsControlArFramerSyncCheck OBJECT-TYPE
			SYNTAX SheShdslEnableModeType
			MAX-ACCESS read-write
			STATUS current
			DESCRIPTION
				"Look at table."
			::= { sheShdslLineParamsControl 46 }

		
--   1.3.6.1.4.1.231.7.1.2.2.1.12.1.2.4.47
		sheShdslLineParamsControlArSnrMarginCheck OBJECT-TYPE
			SYNTAX SheShdslEnableModeType
			MAX-ACCESS read-write
			STATUS current
			DESCRIPTION
				"Look at table."
			::= { sheShdslLineParamsControl 47 }

		
--   1.3.6.1.4.1.231.7.1.2.2.1.12.1.2.4.48
		sheShdslLineParamsControlArCrcThreshold OBJECT-TYPE
			SYNTAX Unsigned32 (0..1024)
			MAX-ACCESS read-write
			STATUS current
			DESCRIPTION
				"Look at table."
			::= { sheShdslLineParamsControl 48 }

		
--   1.3.6.1.4.1.231.7.1.2.2.1.12.1.2.4.49
		sheShdslLineParamsControlArSnrMarginThreshold OBJECT-TYPE
			SYNTAX Unsigned32 (1..6)
			MAX-ACCESS read-write
			STATUS current
			DESCRIPTION
				"Look at table."
			::= { sheShdslLineParamsControl 49 }

		
--   1.3.6.1.4.1.231.7.1.2.2.1.12.1.2.4.50
		sheShdslLineParamsControlArRetrainTime OBJECT-TYPE
			SYNTAX Unsigned32 (1..10)
			MAX-ACCESS read-write
			STATUS current
			DESCRIPTION
				"Look at table."
			::= { sheShdslLineParamsControl 50 }

		
--   1.3.6.1.4.1.231.7.1.2.2.1.12.1.2.4.51
		sheShdslLineParamsControlOpStateTrapEnable OBJECT-TYPE
			SYNTAX SheShdslEnableType
			MAX-ACCESS read-write
			STATUS current
			DESCRIPTION
				"Look at table."
			::= { sheShdslLineParamsControl 51 }

		
--   1.3.6.1.4.1.231.7.1.2.2.1.12.1.2.4.52
		sheShdslLineParamsControlTxFrmrDataClkEdge OBJECT-TYPE
			SYNTAX SheShdslClkEdgeType
			MAX-ACCESS read-write
			STATUS current
			DESCRIPTION
				"Look at table."
			::= { sheShdslLineParamsControl 52 }

		
--   1.3.6.1.4.1.231.7.1.2.2.1.12.1.2.4.53
		sheShdslLineParamsControlRxFrmrDataClkEdge OBJECT-TYPE
			SYNTAX SheShdslClkEdgeType
			MAX-ACCESS read-write
			STATUS current
			DESCRIPTION
				"Look at table."
			::= { sheShdslLineParamsControl 53 }

		
--   1.3.6.1.4.1.231.7.1.2.2.1.12.1.2.4.54
		sheShdslLineParamsControlTxFrmrPulseClkEdge OBJECT-TYPE
			SYNTAX SheShdslClkEdgeType
			MAX-ACCESS read-write
			STATUS current
			DESCRIPTION
				"Look at table."
			::= { sheShdslLineParamsControl 54 }

		
--   1.3.6.1.4.1.231.7.1.2.2.1.12.1.2.4.55
		sheShdslLineParamsControlRxFrmrPulseClkEdge OBJECT-TYPE
			SYNTAX SheShdslClkEdgeType
			MAX-ACCESS read-write
			STATUS current
			DESCRIPTION
				"Look at table."
			::= { sheShdslLineParamsControl 55 }

		
--   1.3.6.1.4.1.231.7.1.2.2.1.12.1.2.4.56
		sheShdslLineParamsControlTxFrmrPulseLvl OBJECT-TYPE
			SYNTAX SheShdslPulseLvlType
			MAX-ACCESS read-write
			STATUS current
			DESCRIPTION
				"Look at table."
			::= { sheShdslLineParamsControl 56 }

		
--   1.3.6.1.4.1.231.7.1.2.2.1.12.1.2.4.57
		sheShdslLineParamsControlRxFrmrPulseLvl OBJECT-TYPE
			SYNTAX SheShdslPulseLvlType
			MAX-ACCESS read-write
			STATUS current
			DESCRIPTION
				"Look at table."
			::= { sheShdslLineParamsControl 57 }

		
--   1.3.6.1.4.1.231.7.1.2.2.1.12.1.2.4.58
		sheShdslLineParamsControlFrmrOH OBJECT-TYPE
			SYNTAX Unsigned32 (0..65535)
			MAX-ACCESS read-write
			STATUS current
			DESCRIPTION
				"Look at table."
			::= { sheShdslLineParamsControl 58 }

		
--   1.3.6.1.4.1.231.7.1.2.2.1.12.1.2.4.59
		sheShdslLineParamsControlLoopAttenCrossingTrapEnable OBJECT-TYPE
			SYNTAX SheShdslEnableType
			MAX-ACCESS read-write
			STATUS current
			DESCRIPTION
				"Look at table."
			::= { sheShdslLineParamsControl 59 }

		
--   1.3.6.1.4.1.231.7.1.2.2.1.12.1.2.4.60
		sheShdslLineParamsControlSNRMarginCrossingTrapEnable OBJECT-TYPE
			SYNTAX SheShdslEnableType
			MAX-ACCESS read-write
			STATUS current
			DESCRIPTION
				"Look at table."
			::= { sheShdslLineParamsControl 60 }

		
--   1.3.6.1.4.1.231.7.1.2.2.1.12.1.2.4.61
		sheShdslLineParamsControlFramerOHAndDefectsTrapEnable OBJECT-TYPE
			SYNTAX SheShdslEnableType
			MAX-ACCESS read-write
			STATUS current
			DESCRIPTION
				"Look at table."
			::= { sheShdslLineParamsControl 61 }

		
--   1.3.6.1.4.1.231.7.1.2.2.1.12.1.2.4.62
		sheShdslLineParamsControlParametricTestInputFile OBJECT-TYPE
			SYNTAX OCTET STRING (SIZE (0..56))
			MAX-ACCESS read-write
			STATUS current
			DESCRIPTION
				"Look at table."
			::= { sheShdslLineParamsControl 62 }

		
--   1.3.6.1.4.1.231.7.1.2.2.1.12.1.2.4.63
		sheShdslLineParamsControlHybridLossTestStart OBJECT-TYPE
			SYNTAX Unsigned32 (0..255)
			MAX-ACCESS read-write
			STATUS current
			DESCRIPTION
				"Look at table."
			::= { sheShdslLineParamsControl 63 }

		
--   1.3.6.1.4.1.231.7.1.2.2.1.12.1.2.4.64
		sheShdslLineParamsControlHybridLossTestEnd OBJECT-TYPE
			SYNTAX Unsigned32 (0..255)
			MAX-ACCESS read-write
			STATUS current
			DESCRIPTION
				"Look at table."
			::= { sheShdslLineParamsControl 64 }

		
--   for shdsl.bis(pammode)
-- 1.3.6.1.4.1.231.7.1.2.2.1.12.1.2.4.65
		sheShdslLineParamsControlPAMMode OBJECT-TYPE
			SYNTAX SheShdslPAMModeType
			MAX-ACCESS read-write
			STATUS current
			DESCRIPTION
				"Look at table."
			::= { sheShdslLineParamsControl 65 }

		
--   1.3.6.1.4.1.231.7.1.2.2.1.12.1.2.5
		sheShdslSpanStatusExtnTable OBJECT-TYPE
			SYNTAX SEQUENCE OF SheShdslSpanStatusExtnEntry
			MAX-ACCESS not-accessible
			STATUS current
			DESCRIPTION
				"This table is a proprietary extension of hdsl2ShdslSpanStatusTable.
				The table will only be supported for interfaces of iftype sdsl (96)!
				"
			::= { sheShdslMIBObjects 5 }

		
--   1.3.6.1.4.1.231.7.1.2.2.1.12.1.2.5.1
		sheShdslSpanStatusExtnEntry OBJECT-TYPE
			SYNTAX SheShdslSpanStatusExtnEntry
			MAX-ACCESS not-accessible
			STATUS current
			DESCRIPTION
				"An entry (conceptual row) in the dsShdslSpanStatusExtnTable.
				The Table is indexed by ifIndex.
				The table will only be supported for interfaces of iftype sdsl (96)!"
			INDEX { ifIndex }
			::= { sheShdslSpanStatusExtnTable 1 }

		
		SheShdslSpanStatusExtnEntry ::=
			SEQUENCE { 
				sheShdslStatusPMMSMaxLineRate
					Unsigned32,
				sheShdslStatus4WireHsMode
					SheShdslStatus4WireHsModeType
			 }

--   for shdsl.bis(4624000 -> 11408000)
-- 1.3.6.1.4.1.231.7.1.2.2.1.12.1.2.5.1.1
		sheShdslStatusPMMSMaxLineRate OBJECT-TYPE
			SYNTAX Unsigned32 (0..11408000)
			MAX-ACCESS read-only
			STATUS current
			DESCRIPTION
				"This object provides the maximum PMMS rate the line is capable of achieving"
			::= { sheShdslSpanStatusExtnEntry 1 }

		
--   1.3.6.1.4.1.231.7.1.2.2.1.12.1.2.5.1.2
		sheShdslStatus4WireHsMode OBJECT-TYPE
			SYNTAX SheShdslStatus4WireHsModeType
			MAX-ACCESS read-only
			STATUS current
			DESCRIPTION
				"Contains the current 4 Wire Handshake Mode Configured"
			::= { sheShdslSpanStatusExtnEntry 2 }

		
--   1.3.6.1.4.1.231.7.1.2.2.1.12.1.2.6
		sheShdslBondingGroupTable OBJECT-TYPE
			SYNTAX SEQUENCE OF SheShdslBondingGroupEntry
			MAX-ACCESS not-accessible
			STATUS obsolete
			DESCRIPTION
				"This table contains a fixed set of possible bondig group entrys.
				This table will not longer be supported."
			::= { sheShdslMIBObjects 6 }

		
--   1.3.6.1.4.1.231.7.1.2.2.1.12.1.2.6.1
		sheShdslBondingGroupEntry OBJECT-TYPE
			SYNTAX SheShdslBondingGroupEntry
			MAX-ACCESS not-accessible
			STATUS obsolete
			DESCRIPTION
				"This table contains a fixed set of possible bondig group entrys.
				Index is the ifIndex from if-table (used iftype is 143 - msdsl - multirate sdsl).
				Entry will be created and deleted during card create or delete for a shdsl-card.
				For one shdsl card with 48 shdsl lines, this table will contain 24 groups of type
				twoPortsBondingGroup and 12 entrys of type fourPortsBondingGroup."
			INDEX { ifIndex }
			::= { sheShdslBondingGroupTable 1 }

		
		SheShdslBondingGroupEntry ::=
			SEQUENCE { 
				sheShdslBondingGroupBridgePortList
					OCTET STRING,
				sheShdslBondingGroupType
					SheShdslBondingGroupType
			 }

--   1.3.6.1.4.1.231.7.1.2.2.1.12.1.2.6.1.1
		sheShdslBondingGroupBridgePortList OBJECT-TYPE
			SYNTAX OCTET STRING (SIZE (4..8))
			MAX-ACCESS read-only
			STATUS obsolete
			DESCRIPTION
				"Portlist for all member of this bonding group.
				The octet string is a list of pairs of octets each identify
				an sheBridgePortIndex. The least significant byte is the
				second octet."
			::= { sheShdslBondingGroupEntry 1 }

		
--   1.3.6.1.4.1.231.7.1.2.2.1.12.1.2.6.1.2
		sheShdslBondingGroupType OBJECT-TYPE
			SYNTAX SheShdslBondingGroupType
			MAX-ACCESS read-only
			STATUS obsolete
			DESCRIPTION
				"The type descripes if this group contain 2 or 4 shdsl - lines."
			::= { sheShdslBondingGroupEntry 2 }

		
--  All following tables are take from the standard.
-- This MIB module defines a collection of objects for managing
-- HDSL2/SHDSL lines.  An agent may reside at either end of the
-- line, however the MIB is designed to require no management
-- communication between the modems beyond that inherent in the
-- low-level EOC line protocol as defined in ANSI T1E1.4/2000-006
-- for HDSL2 lines), or in ITU G.991.2 (for SHDSL lines).
-- Adapted for RFC 4319.
-- 1.3.6.1.4.1.231.7.1.2.2.1.12.1.2.7
		shehdsl2ShdslMibObjects OBJECT IDENTIFIER ::= { sheShdslMIBObjects 7 }

		
--   1.3.6.1.4.1.231.7.1.2.2.1.12.1.2.7.1
		shehdsl2ShdslSpanConfTable OBJECT-TYPE
			SYNTAX SEQUENCE OF Shehdsl2ShdslSpanConfEntry
			MAX-ACCESS not-accessible
			STATUS current
			DESCRIPTION
				"This table supports overall configuration of HDSL2/SHDSL
				Spans.  Entries in this table MUST be maintained in a
				persistent manner."
			::= { shehdsl2ShdslMibObjects 1 }

		
--   1.3.6.1.4.1.231.7.1.2.2.1.12.1.2.7.1.1
		shehdsl2ShdslSpanConfEntry OBJECT-TYPE
			SYNTAX Shehdsl2ShdslSpanConfEntry
			MAX-ACCESS not-accessible
			STATUS current
			DESCRIPTION
				"An entry in the hdsl2ShdslSpanConfTable.  Each entry
				represents the complete Span in a single SHDSL line.
				It is indexed by the ifIndex of the associated HDSL2/SHDSL line."
			INDEX { ifIndex }
			::= { shehdsl2ShdslSpanConfTable 1 }

		
		Shehdsl2ShdslSpanConfEntry ::=
			SEQUENCE { 
				shehdsl2ShdslSpanConfNumRepeaters
					Unsigned32,
				shehdsl2ShdslSpanConfProfile
					SnmpAdminString,
				shehdsl2ShdslSpanConfAlarmProfile
					SnmpAdminString
			 }

--   1.3.6.1.4.1.231.7.1.2.2.1.12.1.2.7.1.1.1
		shehdsl2ShdslSpanConfNumRepeaters OBJECT-TYPE
			SYNTAX Unsigned32 (0)
			UNITS "repeaters"
			MAX-ACCESS read-only
			STATUS current
			DESCRIPTION
				"This object provisions the number of repeaters/regenerators
				in this HDSL2/SHDSL Span.
				The System will not support repeaters."
			DEFVAL { 0 }
			::= { shehdsl2ShdslSpanConfEntry 1 }

		
--   1.3.6.1.4.1.231.7.1.2.2.1.12.1.2.7.1.1.2
		shehdsl2ShdslSpanConfProfile OBJECT-TYPE
			SYNTAX SnmpAdminString (SIZE (1..32))
			MAX-ACCESS read-only
			STATUS current
			DESCRIPTION
				"This object is a pointer to a span configuration profile in
				the hdsl2ShdslSpanConfProfileTable, which applies to this span.
				The value of this object is the index of the referenced profile
				in the hdsl2ShdslSpanConfProfileTable.
				
				Any attempt to set this object to a value that is not the value
				of the index for an active entry in the profile table,
				hdsl2ShdslSpanConfProfileTable, MUST be rejected."
			::= { shehdsl2ShdslSpanConfEntry 2 }

		
--   1.3.6.1.4.1.231.7.1.2.2.1.12.1.2.7.1.1.3
		shehdsl2ShdslSpanConfAlarmProfile OBJECT-TYPE
			SYNTAX SnmpAdminString (SIZE (1..32))
			MAX-ACCESS read-only
			STATUS current
			DESCRIPTION
				"This object is a pointer to an Alarm configuration profile in
				the hdsl2ShdslEndpointAlarmConfProfileTable.  The value of this
				object is the index of the referenced profile in the
				hdsl2ShdslEndpointAlarmConfProfileTable.  The alarm threshold
				configuration in the referenced profile will be used by default
				for all segment endpoints in this span.  Individual endpoints
				may override this profile by explicitly specifying some other
				profile in the hdsl2ShdslEndpointConfTable.  By default, this
				object will have the value 'DEFVAL' (the index of the default
				profile).
				
				Any attempt to set this object to a value that is not the value
				of the index for an active entry in the profile table,
				hdsl2ShdslEndpointAlarmConfProfileTable, MUST be rejected."
			::= { shehdsl2ShdslSpanConfEntry 3 }

		
--   1.3.6.1.4.1.231.7.1.2.2.1.12.1.2.7.2
		shehdsl2ShdslSpanConfControl OBJECT IDENTIFIER ::= { shehdsl2ShdslMibObjects 2 }

		
--   1.3.6.1.4.1.231.7.1.2.2.1.12.1.2.7.2.1
		shehdsl2ShdslSpanConfControlRequest OBJECT-TYPE
			SYNTAX SheShdslControlRequestType
			MAX-ACCESS read-write
			STATUS current
			DESCRIPTION
				"modifyshehdsl2ShdslSpanConfEntry
				
				shehdsl2ShdslSpanConfControlNumRepeaters
				shehdsl2ShdslSpanConfControlProfile
				
				
				modifyshehdsl2ShdslSpanConfEntryAlarmProfile
				shehdsl2ShdslSpanConfControlAlarmProfile"
			::= { shehdsl2ShdslSpanConfControl 1 }

		
--   1.3.6.1.4.1.231.7.1.2.2.1.12.1.2.7.2.2
		shehdsl2ShdslSpanConfControlIndex OBJECT-TYPE
			SYNTAX InterfaceIndex
			MAX-ACCESS read-write
			STATUS current
			DESCRIPTION
				"Index of the modified entry."
			::= { shehdsl2ShdslSpanConfControl 2 }

		
--   1.3.6.1.4.1.231.7.1.2.2.1.12.1.2.7.2.3
		shehdsl2ShdslSpanConfControlStatus OBJECT-TYPE
			SYNTAX SheControlStatusType
			MAX-ACCESS read-only
			STATUS current
			DESCRIPTION
				"The status of a user command. 
				"
			::= { shehdsl2ShdslSpanConfControl 3 }

		
--   1.3.6.1.4.1.231.7.1.2.2.1.12.1.2.7.2.4
		shehdsl2ShdslSpanConfControlTimer OBJECT-TYPE
			SYNTAX Gauge32
			MAX-ACCESS read-only
			STATUS current
			DESCRIPTION
				"The maximum wait time for the manager for a long running user command. 
				"
			::= { shehdsl2ShdslSpanConfControl 4 }

		
--   1.3.6.1.4.1.231.7.1.2.2.1.12.1.2.7.2.5
		shehdsl2ShdslSpanConfControlReqResult OBJECT-TYPE
			SYNTAX SheShdslControlRequestResultType
			MAX-ACCESS read-only
			STATUS current
			DESCRIPTION
				"The result of the last user command."
			::= { shehdsl2ShdslSpanConfControl 5 }

		
--   1.3.6.1.4.1.231.7.1.2.2.1.12.1.2.7.2.6
		shehdsl2ShdslSpanConfControlTimeStamp OBJECT-TYPE
			SYNTAX Unsigned32
			UNITS "sec"
			MAX-ACCESS read-only
			STATUS current
			DESCRIPTION
				"The time stamp of the last command (end of command)."
			::= { shehdsl2ShdslSpanConfControl 6 }

		
--   1.3.6.1.4.1.231.7.1.2.2.1.12.1.2.7.2.7
		shehdsl2ShdslSpanConfControlNumRepeaters OBJECT-TYPE
			SYNTAX Unsigned32 (0)
			UNITS "repeaters"
			MAX-ACCESS read-write
			STATUS current
			DESCRIPTION
				"look at table."
			::= { shehdsl2ShdslSpanConfControl 7 }

		
--   1.3.6.1.4.1.231.7.1.2.2.1.12.1.2.7.2.8
		shehdsl2ShdslSpanConfControlProfile OBJECT-TYPE
			SYNTAX SnmpAdminString (SIZE (1..32))
			MAX-ACCESS read-write
			STATUS current
			DESCRIPTION
				"look at table."
			::= { shehdsl2ShdslSpanConfControl 8 }

		
--   1.3.6.1.4.1.231.7.1.2.2.1.12.1.2.7.2.9
		shehdsl2ShdslSpanConfControlAlarmProfile OBJECT-TYPE
			SYNTAX SnmpAdminString (SIZE (1..32))
			MAX-ACCESS read-write
			STATUS current
			DESCRIPTION
				"look at table."
			::= { shehdsl2ShdslSpanConfControl 9 }

		
--   1.3.6.1.4.1.231.7.1.2.2.1.12.1.2.7.3
		shehdsl2ShdslSpanStatusTable OBJECT-TYPE
			SYNTAX SEQUENCE OF Shehdsl2ShdslSpanStatusEntry
			MAX-ACCESS not-accessible
			STATUS current
			DESCRIPTION
				"This table provides overall status information of
				HDSL2/SHDSL spans.  This table contains live data from
				equipment.  As such, it is NOT persistent."
			::= { shehdsl2ShdslMibObjects 3 }

		
--   1.3.6.1.4.1.231.7.1.2.2.1.12.1.2.7.3.1
		shehdsl2ShdslSpanStatusEntry OBJECT-TYPE
			SYNTAX Shehdsl2ShdslSpanStatusEntry
			MAX-ACCESS not-accessible
			STATUS current
			DESCRIPTION
				"An entry in the hdsl2ShdslSpanStatusTable.  Each entry
				represents the complete span in a single HDSL2/SHDSL line.
				It is indexed by the ifIndex of the associated HDSL2/SHDSL
				line."
			INDEX { ifIndex }
			::= { shehdsl2ShdslSpanStatusTable 1 }

		
		Shehdsl2ShdslSpanStatusEntry ::=
			SEQUENCE { 
				shehdsl2ShdslStatusNumAvailRepeaters
					Unsigned32,
				shehdsl2ShdslStatusMaxAttainableLineRate
					Unsigned32,
				shehdsl2ShdslStatusActualLineRate
					Unsigned32,
				shehdsl2ShdslStatusTransmissionModeCurrent
					SheHdsl2ShdslTransmissionModeType,
				sheShdslStatusMaxAttainablePayloadRate
					Unsigned32,
				sheShdslStatusActualPayloadRate
					Unsigned32,
				sheShdslSpanStatusPAMModulation
					SheShdslPAMModeType
			 }

--   1.3.6.1.4.1.231.7.1.2.2.1.12.1.2.7.3.1.1
		shehdsl2ShdslStatusNumAvailRepeaters OBJECT-TYPE
			SYNTAX Unsigned32 (0..8)
			MAX-ACCESS read-only
			STATUS current
			DESCRIPTION
				"Contains the actual number of repeaters/regenerators
				discovered in this HDSL2/SHDSL span."
			::= { shehdsl2ShdslSpanStatusEntry 1 }

		
--   for shdsl.bis(4624000 -> 11408000)
-- 1.3.6.1.4.1.231.7.1.2.2.1.12.1.2.7.3.1.2
		shehdsl2ShdslStatusMaxAttainableLineRate OBJECT-TYPE
			SYNTAX Unsigned32 (0..11408000)
			UNITS "bps"
			MAX-ACCESS read-only
			STATUS current
			DESCRIPTION
				"Contains the maximum attainable line rate in this HDSL2/SHDSL
				span. This object provides the maximum rate the line is
				capable of achieving. This is based upon measurements made
				during line probing. This rate includes payload (user data)
				and any applicable framing overhead."
			::= { shehdsl2ShdslSpanStatusEntry 2 }

		
--  for shdsl.bis(4624000 -> 11408000) 
-- 1.3.6.1.4.1.231.7.1.2.2.1.12.1.2.7.3.1.3
		shehdsl2ShdslStatusActualLineRate OBJECT-TYPE
			SYNTAX Unsigned32 (0..11408000)
			UNITS "bps"
			MAX-ACCESS read-only
			STATUS current
			DESCRIPTION
				"Contains the actual line rate in this HDSL2/SHDSL span.  This
				should equal ifSpeed. This rate includes payload (user data)
				and any applicable framing overhead."
			::= { shehdsl2ShdslSpanStatusEntry 3 }

		
--   1.3.6.1.4.1.231.7.1.2.2.1.12.1.2.7.3.1.4
		shehdsl2ShdslStatusTransmissionModeCurrent OBJECT-TYPE
			SYNTAX SheHdsl2ShdslTransmissionModeType
			MAX-ACCESS read-only
			STATUS current
			DESCRIPTION
				"Contains the current Power Spectral Density (PSD) regional
				setting of the HDSL2/SHDSL span.
				
				Bit   Meaning      Description
				1     region 1     Indicates ITU-T G.991.2 Annex A/F.
				2     region 2     Indicates ITU-T G.991.2 Annex B/G."
			::= { shehdsl2ShdslSpanStatusEntry 4 }

		
--   for shdsl.bis(SGagMOShdslSpanStatusTableTbl.StatusMaxAttainablePayloadRate)
-- 1.3.6.1.4.1.231.7.1.2.2.1.12.1.2.7.3.1.5
		sheShdslStatusMaxAttainablePayloadRate OBJECT-TYPE
			SYNTAX Unsigned32 (0..11408000)
			UNITS "bps"
			MAX-ACCESS read-only
			STATUS current
			DESCRIPTION
				"This parameter contains the maximum attainable payload rate in this SHDSL span. This is based upon measurements made during line probing without including any framing overhead."
			::= { shehdsl2ShdslSpanStatusEntry 5 }

		
--   for shdsl.bis(SGagMOShdslSpanStatusTableTbl.StatusActualPayloadRate)
-- 1.3.6.1.4.1.231.7.1.2.2.1.12.1.2.7.3.1.6
		sheShdslStatusActualPayloadRate OBJECT-TYPE
			SYNTAX Unsigned32 (0..11408000)
			UNITS "bps"
			MAX-ACCESS read-only
			STATUS current
			DESCRIPTION
				"This parameter contains the actual payload rate in this SHDSL span. This is based upon measurements made during line probing without including any framing overhead."
			::= { shehdsl2ShdslSpanStatusEntry 6 }

		
--   1.3.6.1.4.1.231.7.1.2.2.1.12.1.2.7.14.1.17
		sheShdslSpanStatusPAMModulation OBJECT-TYPE
			SYNTAX SheShdslPAMModeType
			MAX-ACCESS read-only
			STATUS current
			DESCRIPTION
				"The parameter show the selected PAM constellation is to be used.
				 - SELECT_16_PAM   - Use 16 PAM only
				 - SELECT_32_PAM   - Use 32 PAM only
				Select 16Pam limits the data rates from 192 kbps to 3840 kbps
				Select 32Pam limits the data rates from 768 kbps to 5696 kbps
				
				This is propietary extension for interfaces of type shdsl (169) only.
				"
			::= { shehdsl2ShdslSpanStatusEntry 7 }

		
--   1.3.6.1.4.1.231.7.1.2.2.1.12.1.2.7.4
		shehdsl2ShdslInventoryTable OBJECT-TYPE
			SYNTAX SEQUENCE OF Shehdsl2ShdslInventoryEntry
			MAX-ACCESS not-accessible
			STATUS current
			DESCRIPTION
				"This table supports retrieval of unit inventory information
				available via the EOC from units in a HDSL2/SHDSL line.
				
				Entries in this table are dynamically created during the
				line discovery process.  The life cycle for these entries
				is as follows:
				
				   - xtu discovers a device, either a far-end xtu or an xru
				   - an inventory table entry is created for the device
				   - the line goes down for whatever reason
				   - inventory table entries for unreachable devices are
				     destroyed.
				
				As these entries are created/destroyed dynamically, they
				are NOT persistent."
			::= { shehdsl2ShdslMibObjects 4 }

		
--   1.3.6.1.4.1.231.7.1.2.2.1.12.1.2.7.4.1
		shehdsl2ShdslInventoryEntry OBJECT-TYPE
			SYNTAX Shehdsl2ShdslInventoryEntry
			MAX-ACCESS not-accessible
			STATUS current
			DESCRIPTION
				"An entry in the hdsl2ShdslInventoryTable.  Each entry
				represents inventory information for a single unit in a
				HDSL2/SHDSL line.  It is indexed by the ifIndex of the
				HDSL2/SHDSL line and the Hdsl2ShdslUnitId of the
				associated unit."
			INDEX { ifIndex, shehdsl2ShdslInvIndex }
			::= { shehdsl2ShdslInventoryTable 1 }

		
		Shehdsl2ShdslInventoryEntry ::=
			SEQUENCE { 
				shehdsl2ShdslInvIndex
					SheHdsl2ShdslUnitId,
				shehdsl2ShdslInvVendorID
					OCTET STRING,
				shehdsl2ShdslInvVendorModelNumber
					OCTET STRING,
				shehdsl2ShdslInvVendorSerialNumber
					OCTET STRING,
				shehdsl2ShdslInvVendorEOCSoftwareVersion
					Integer32,
				shehdsl2ShdslInvStandardVersion
					Integer32,
				shehdsl2ShdslInvVendorListNumber
					OCTET STRING,
				shehdsl2ShdslInvVendorIssueNumber
					OCTET STRING,
				shehdsl2ShdslInvVendorSoftwareVersion
					OCTET STRING,
				shehdsl2ShdslInvEquipmentCode
					OCTET STRING,
				shehdsl2ShdslInvVendorOther
					OCTET STRING,
				shehdsl2ShdslInvTransmissionModeCapability
					SheHdsl2ShdslTransmissionModeType
			 }

--   1.3.6.1.4.1.231.7.1.2.2.1.12.1.2.7.4.1.1
		shehdsl2ShdslInvIndex OBJECT-TYPE
			SYNTAX SheHdsl2ShdslUnitId
			MAX-ACCESS not-accessible
			STATUS current
			DESCRIPTION
				"Each entry in this table corresponds to a physical element
				in a HDSL2/SHDSL Span.  It is based on the EOC unit addressing
				scheme with reference to the xtuC."
			::= { shehdsl2ShdslInventoryEntry 1 }

		
--   1.3.6.1.4.1.231.7.1.2.2.1.12.1.2.7.4.1.2
		shehdsl2ShdslInvVendorID OBJECT-TYPE
			SYNTAX OCTET STRING (SIZE (8))
			MAX-ACCESS read-only
			STATUS current
			DESCRIPTION
				"Vendor ID as reported in an Inventory Response message."
			REFERENCE
				"G.991.2, Section 9.5.5.7.4, Inventory response - Message ID
				130, Octets 25-32."
			::= { shehdsl2ShdslInventoryEntry 2 }

		
--   1.3.6.1.4.1.231.7.1.2.2.1.12.1.2.7.4.1.3
		shehdsl2ShdslInvVendorModelNumber OBJECT-TYPE
			SYNTAX OCTET STRING (SIZE (12))
			MAX-ACCESS read-only
			STATUS current
			DESCRIPTION
				"Vendor model number as reported in an Inventory Response
				message."
			REFERENCE
				"G.991.2, Section 9.5.5.7.4, Inventory response - Message ID
				130, Octets 33-44."
			::= { shehdsl2ShdslInventoryEntry 3 }

		
--   1.3.6.1.4.1.231.7.1.2.2.1.12.1.2.7.4.1.4
		shehdsl2ShdslInvVendorSerialNumber OBJECT-TYPE
			SYNTAX OCTET STRING (SIZE (12))
			MAX-ACCESS read-only
			STATUS current
			DESCRIPTION
				"Vendor serial number as reported in an Inventory Response
				message."
			REFERENCE
				"G.991.2, Section 9.5.5.7.4, Inventory response - Message ID
				130, Octets 45-56."
			::= { shehdsl2ShdslInventoryEntry 4 }

		
--   1.3.6.1.4.1.231.7.1.2.2.1.12.1.2.7.4.1.5
		shehdsl2ShdslInvVendorEOCSoftwareVersion OBJECT-TYPE
			SYNTAX Integer32
			MAX-ACCESS read-only
			STATUS current
			DESCRIPTION
				"Vendor EOC version as reported in a Discovery Response
				message."
			REFERENCE
				"G.991.2, Section 9.5.5.7.2, Discovery response - Message ID
				129, Octet 12"
			::= { shehdsl2ShdslInventoryEntry 5 }

		
--   1.3.6.1.4.1.231.7.1.2.2.1.12.1.2.7.4.1.6
		shehdsl2ShdslInvStandardVersion OBJECT-TYPE
			SYNTAX Integer32
			MAX-ACCESS read-only
			STATUS current
			DESCRIPTION
				"Version of the HDSL2/SHDSL standard implemented, as reported
				in an Inventory Response message."
			REFERENCE
				"G.991.2, Section 9.5.5.7.4, Inventory response - Message ID
				130, Octet 2"
			::= { shehdsl2ShdslInventoryEntry 6 }

		
--   1.3.6.1.4.1.231.7.1.2.2.1.12.1.2.7.4.1.7
		shehdsl2ShdslInvVendorListNumber OBJECT-TYPE
			SYNTAX OCTET STRING (SIZE (3))
			MAX-ACCESS read-only
			STATUS current
			DESCRIPTION
				"Vendor list number as reported in an Inventory Response
				message."
			REFERENCE
				"G.991.2, Section 9.5.5.7.4, Inventory response - Message ID
				130, Octets 3-5"
			::= { shehdsl2ShdslInventoryEntry 7 }

		
--   1.3.6.1.4.1.231.7.1.2.2.1.12.1.2.7.4.1.8
		shehdsl2ShdslInvVendorIssueNumber OBJECT-TYPE
			SYNTAX OCTET STRING (SIZE (2))
			MAX-ACCESS read-only
			STATUS current
			DESCRIPTION
				"Vendor issue number as reported in an Inventory Response
				message."
			REFERENCE
				"G.991.2, Section 9.5.5.7.4, Inventory response - Message ID
				130, Octets 6-7."
			::= { shehdsl2ShdslInventoryEntry 8 }

		
--   1.3.6.1.4.1.231.7.1.2.2.1.12.1.2.7.4.1.9
		shehdsl2ShdslInvVendorSoftwareVersion OBJECT-TYPE
			SYNTAX OCTET STRING (SIZE (6))
			MAX-ACCESS read-only
			STATUS current
			DESCRIPTION
				"Vendor software version as reported in an Inventory Response
				message."
			REFERENCE
				"G.991.2, Section 9.5.5.7.4, Inventory response - Message ID
				130, Octets 8-13."
			::= { shehdsl2ShdslInventoryEntry 9 }

		
--   1.3.6.1.4.1.231.7.1.2.2.1.12.1.2.7.4.1.10
		shehdsl2ShdslInvEquipmentCode OBJECT-TYPE
			SYNTAX OCTET STRING (SIZE (10))
			MAX-ACCESS read-only
			STATUS current
			DESCRIPTION
				"Equipment code conforming to ANSI T1.213, Coded Identification
				of Equipment Entities."
			REFERENCE
				"G.991.2, Section 9.5.5.7.4, Inventory response - Message ID
				130, Octets 14-23."
			::= { shehdsl2ShdslInventoryEntry 10 }

		
--   1.3.6.1.4.1.231.7.1.2.2.1.12.1.2.7.4.1.11
		shehdsl2ShdslInvVendorOther OBJECT-TYPE
			SYNTAX OCTET STRING (SIZE (12))
			MAX-ACCESS read-only
			STATUS current
			DESCRIPTION
				"Other vendor information as reported in an Inventory Response
				message."
			REFERENCE
				"G.991.2, Section 9.5.5.7.4, Inventory response - Message ID
				130, Octets 57-68."
			::= { shehdsl2ShdslInventoryEntry 11 }

		
--   1.3.6.1.4.1.231.7.1.2.2.1.12.1.2.7.4.1.12
		shehdsl2ShdslInvTransmissionModeCapability OBJECT-TYPE
			SYNTAX SheHdsl2ShdslTransmissionModeType
			MAX-ACCESS read-only
			STATUS current
			DESCRIPTION
				"Contains the transmission mode capability of the SHDSL unit.
				
				Bit   Meaning      Description
				1     region 1     Indicates ITU-T G.991.2 Annex A/F.
				2     region 2     Indicates ITU-T G.991.2 Annex B/G."
			::= { shehdsl2ShdslInventoryEntry 12 }

		
--   1.3.6.1.4.1.231.7.1.2.2.1.12.1.2.7.5
		shehdsl2ShdslEndpointConfTable OBJECT-TYPE
			SYNTAX SEQUENCE OF Shehdsl2ShdslEndpointConfEntry
			MAX-ACCESS not-accessible
			STATUS current
			DESCRIPTION
				"This table supports configuration parameters for segment
				endpoints in a HDSL2/SHDSL line.  As this table is indexed
				by ifIndex, it MUST be maintained in a persistent manner."
			::= { shehdsl2ShdslMibObjects 5 }

		
--   1.3.6.1.4.1.231.7.1.2.2.1.12.1.2.7.5.1
		shehdsl2ShdslEndpointConfEntry OBJECT-TYPE
			SYNTAX Shehdsl2ShdslEndpointConfEntry
			MAX-ACCESS not-accessible
			STATUS current
			DESCRIPTION
				"An entry in the hdsl2ShdslEndpointConfTable.  Each entry
				represents a single segment endpoint in a HDSL2/SHDSL line.
				It is indexed by the ifIndex of the HDSL2/SHDSL line, the
				UnitId of the associated unit, the side of the unit, and the
				wire-pair of the associated modem."
			INDEX { ifIndex, shehdsl2ShdslInvIndex, shehdsl2ShdslEndpointSide, shehdsl2ShdslEndpointWirePair }
			::= { shehdsl2ShdslEndpointConfTable 1 }

		
		Shehdsl2ShdslEndpointConfEntry ::=
			SEQUENCE { 
				shehdsl2ShdslEndpointSide
					SheHdsl2ShdslUnitSide,
				shehdsl2ShdslEndpointWirePair
					SheHdsl2ShdslWirePair,
				shehdsl2ShdslEndpointAlarmConfProfile
					SnmpAdminString
			 }

--   1.3.6.1.4.1.231.7.1.2.2.1.12.1.2.7.5.1.1
		shehdsl2ShdslEndpointSide OBJECT-TYPE
			SYNTAX SheHdsl2ShdslUnitSide
			MAX-ACCESS not-accessible
			STATUS current
			DESCRIPTION
				"The side of the unit associated with this segment endpoint -
				Network/Customer side - as per the Hdsl2ShdslUnitSide textual
				convention."
			::= { shehdsl2ShdslEndpointConfEntry 1 }

		
--   1.3.6.1.4.1.231.7.1.2.2.1.12.1.2.7.5.1.2
		shehdsl2ShdslEndpointWirePair OBJECT-TYPE
			SYNTAX SheHdsl2ShdslWirePair
			MAX-ACCESS not-accessible
			STATUS current
			DESCRIPTION
				"The wire-pair of the modem associated with this segment
				endpoint as per the Hdsl2ShdslWirePair textual convention.
				
				wirePair1(1),  -> two wire
				wirePair2(2),  -> four wire
				wirePair3(3),  -> six wire
				wirePair4(4)   -> eight wire"
			::= { shehdsl2ShdslEndpointConfEntry 2 }

		
--   1.3.6.1.4.1.231.7.1.2.2.1.12.1.2.7.5.1.3
		shehdsl2ShdslEndpointAlarmConfProfile OBJECT-TYPE
			SYNTAX SnmpAdminString (SIZE (0..32))
			MAX-ACCESS read-only
			STATUS current
			DESCRIPTION
				"This object configures the alarm threshold values to be used
				for this segment endpoint.  The values are obtained from the
				alarm configuration profile referenced by this object.  The
				value of this object is the index of the referenced profile in
				the hdsl2ShdslEndpointAlarmConfProfileTable, or NULL (a zero-
				length SnmpAdminString).  If the value is a zero-length
				SnmpAdminString, the endpoint uses the default Alarm
				Configuration Profile for the associated span as per the
				hdsl2ShdslSpanConfAlarmProfile object in the
				hdsl2ShdslSpanConfTable.  The default value of this object is
				a zero-length SnmpAdminString.
				
				Any attempt to set this object to a value that is not the value
				of the index for an active entry in the profile table,
				hdsl2ShdslEndpointAlarmConfProfileTable, MUST be rejected."
			::= { shehdsl2ShdslEndpointConfEntry 3 }

		
--   1.3.6.1.4.1.231.7.1.2.2.1.12.1.2.7.6
		shehdsl2ShdslEndpointConfControl OBJECT IDENTIFIER ::= { shehdsl2ShdslMibObjects 6 }

		
--   1.3.6.1.4.1.231.7.1.2.2.1.12.1.2.7.6.1
		shehdsl2ShdslEndpointConfControlRequest OBJECT-TYPE
			SYNTAX SheShdslControlRequestType
			MAX-ACCESS read-write
			STATUS current
			DESCRIPTION
				"modifyshehdsl2ShdslEndpointConfEntry
				
				"
			::= { shehdsl2ShdslEndpointConfControl 1 }

		
--   1.3.6.1.4.1.231.7.1.2.2.1.12.1.2.7.6.2
		shehdsl2ShdslEndpointConfControlIndex OBJECT-TYPE
			SYNTAX InterfaceIndex
			MAX-ACCESS read-write
			STATUS current
			DESCRIPTION
				"First key for the modified entry. IfIndex of line."
			::= { shehdsl2ShdslEndpointConfControl 2 }

		
--   1.3.6.1.4.1.231.7.1.2.2.1.12.1.2.7.6.3
		shehdsl2ShdslEndpointConfControlStatus OBJECT-TYPE
			SYNTAX SheControlStatusType
			MAX-ACCESS read-only
			STATUS current
			DESCRIPTION
				"The status of a user command. 
				"
			::= { shehdsl2ShdslEndpointConfControl 3 }

		
--   1.3.6.1.4.1.231.7.1.2.2.1.12.1.2.7.6.4
		shehdsl2ShdslEndpointConfControlTimer OBJECT-TYPE
			SYNTAX Gauge32
			MAX-ACCESS read-only
			STATUS current
			DESCRIPTION
				"The maximum wait time for the manager for a long running user command. 
				"
			::= { shehdsl2ShdslEndpointConfControl 4 }

		
--   1.3.6.1.4.1.231.7.1.2.2.1.12.1.2.7.6.5
		shehdsl2ShdslEndpointConfControlReqResult OBJECT-TYPE
			SYNTAX SheShdslControlRequestResultType
			MAX-ACCESS read-only
			STATUS current
			DESCRIPTION
				"The result of the last user command."
			::= { shehdsl2ShdslEndpointConfControl 5 }

		
--   1.3.6.1.4.1.231.7.1.2.2.1.12.1.2.7.6.6
		shehdsl2ShdslEndpointConfControlTimeStamp OBJECT-TYPE
			SYNTAX Unsigned32
			UNITS "sec"
			MAX-ACCESS read-only
			STATUS current
			DESCRIPTION
				"The time stamp of the last command (end of command)."
			::= { shehdsl2ShdslEndpointConfControl 6 }

		
--   1.3.6.1.4.1.231.7.1.2.2.1.12.1.2.7.6.7
		shehdsl2ShdslEndpointConfControlInvIndex OBJECT-TYPE
			SYNTAX SheHdsl2ShdslUnitId
			MAX-ACCESS read-write
			STATUS current
			DESCRIPTION
				"Second key for modified entry."
			::= { shehdsl2ShdslEndpointConfControl 7 }

		
--   1.3.6.1.4.1.231.7.1.2.2.1.12.1.2.7.6.8
		shehdsl2ShdslEndpointConfControlSide OBJECT-TYPE
			SYNTAX SheHdsl2ShdslUnitSide
			MAX-ACCESS read-write
			STATUS current
			DESCRIPTION
				"Third key for the modified entry. "
			::= { shehdsl2ShdslEndpointConfControl 8 }

		
--   1.3.6.1.4.1.231.7.1.2.2.1.12.1.2.7.6.9
		shehdsl2ShdslEndpointConfControlWirePair OBJECT-TYPE
			SYNTAX SheHdsl2ShdslWirePair
			MAX-ACCESS read-write
			STATUS current
			DESCRIPTION
				"Forth key for the modified entry."
			::= { shehdsl2ShdslEndpointConfControl 9 }

		
--   1.3.6.1.4.1.231.7.1.2.2.1.12.1.2.7.6.10
		shehdsl2ShdslEndpointConfControlAlarmProfile OBJECT-TYPE
			SYNTAX SnmpAdminString (SIZE (1..32))
			MAX-ACCESS read-write
			STATUS current
			DESCRIPTION
				"Look at table."
			::= { shehdsl2ShdslEndpointConfControl 10 }

		
--   1.3.6.1.4.1.231.7.1.2.2.1.12.1.2.7.7
		shehdsl2ShdslEndpointCurrTable OBJECT-TYPE
			SYNTAX SEQUENCE OF Shehdsl2ShdslEndpointCurrEntry
			MAX-ACCESS not-accessible
			STATUS current
			DESCRIPTION
				"This table contains current status and performance information
				for segment endpoints in HDSL2/SHDSL Lines.  As with other
				tables in this MIB indexed by ifIndex, entries in this table
				MUST be maintained in a persistent manner."
			::= { shehdsl2ShdslMibObjects 7 }

		
--   1.3.6.1.4.1.231.7.1.2.2.1.12.1.2.7.7.1
		shehdsl2ShdslEndpointCurrEntry OBJECT-TYPE
			SYNTAX Shehdsl2ShdslEndpointCurrEntry
			MAX-ACCESS not-accessible
			STATUS current
			DESCRIPTION
				"An entry in the hdsl2ShdslEndpointCurrTable.  Each entry
				contains status and performance information relating to a
				single segment endpoint.  It is indexed by the ifIndex of the
				HDSL2/SHDSL line, the UnitId of the associated unit, the side
				of the unit, and the wire-pair of the associated modem."
			INDEX { ifIndex, shehdsl2ShdslInvIndex, shehdsl2ShdslEndpointSide, shehdsl2ShdslEndpointWirePair }
			::= { shehdsl2ShdslEndpointCurrTable 1 }

		
		Shehdsl2ShdslEndpointCurrEntry ::=
			SEQUENCE { 
				shehdsl2ShdslEndpointCurrAtn
					Integer32,
				shehdsl2ShdslEndpointCurrSnrMgn
					Integer32,
				shehdsl2ShdslEndpointCurrStatus
					Shehdsl2ShdslEndpointCurrStatusType,
				shehdsl2ShdslEndpointES
					Counter32,
				shehdsl2ShdslEndpointSES
					Counter32,
				shehdsl2ShdslEndpointCRCanomalies
					Counter32,
				shehdsl2ShdslEndpointLOSWS
					Counter32,
				shehdsl2ShdslEndpointUAS
					Counter32,
				shehdsl2ShdslEndpointCurr15MinTimeElapsed
					SheHdsl2ShdslPerfTimeElapsed,
				shehdsl2ShdslEndpointCurr15MinES
					PerfCurrentCount,
				shehdsl2ShdslEndpointCurr15MinSES
					PerfCurrentCount,
				shehdsl2ShdslEndpointCurr15MinCRCanomalies
					PerfCurrentCount,
				shehdsl2ShdslEndpointCurr15MinLOSWS
					PerfCurrentCount,
				shehdsl2ShdslEndpointCurr15MinUAS
					PerfCurrentCount,
				shehdsl2ShdslEndpointCurr1DayTimeElapsed
					SheHdsl2ShdslPerfTimeElapsed,
				shehdsl2ShdslEndpointCurr1DayES
					SheHdsl2ShdslPerfCurrDayCount,
				shehdsl2ShdslEndpointCurr1DaySES
					SheHdsl2ShdslPerfCurrDayCount,
				shehdsl2ShdslEndpointCurr1DayCRCanomalies
					SheHdsl2ShdslPerfCurrDayCount,
				shehdsl2ShdslEndpointCurr1DayLOSWS
					SheHdsl2ShdslPerfCurrDayCount,
				shehdsl2ShdslEndpointCurr1DayUAS
					SheHdsl2ShdslPerfCurrDayCount,
				shehdsl2ShdslEndpointCurrTipRingReversal
					Shehdsl2ShdslMaintTipRingReversalType,
				shehdsl2ShdslEndpointCurrActivationState
					SheHdsl2ShdslActivationStateType
			 }

--   1.3.6.1.4.1.231.7.1.2.2.1.12.1.2.7.7.1.1
		shehdsl2ShdslEndpointCurrAtn OBJECT-TYPE
			SYNTAX Integer32 (-127..128)
			UNITS "dB"
			MAX-ACCESS read-only
			STATUS current
			DESCRIPTION
				"The current loop attenuation for this endpoint as reported in
				a Network or Customer Side Performance Status message."
			REFERENCE
				"HDSL2 Section 7.5.3.7; SHDSL Section 9.5.5.7"
			::= { shehdsl2ShdslEndpointCurrEntry 1 }

		
--   1.3.6.1.4.1.231.7.1.2.2.1.12.1.2.7.7.1.2
		shehdsl2ShdslEndpointCurrSnrMgn OBJECT-TYPE
			SYNTAX Integer32 (-127..128)
			UNITS "dB"
			MAX-ACCESS read-only
			STATUS current
			DESCRIPTION
				"The current SNR margin for this endpoint as reported in a
				Status Response/SNR message."
			REFERENCE
				"HDSL2 Section 7.5.3.7; SHDSL Section 9.5.5.7"
			::= { shehdsl2ShdslEndpointCurrEntry 2 }

		
--   1.3.6.1.4.1.231.7.1.2.2.1.12.1.2.7.7.1.3
		shehdsl2ShdslEndpointCurrStatus OBJECT-TYPE
			SYNTAX Shehdsl2ShdslEndpointCurrStatusType
			MAX-ACCESS read-only
			STATUS current
			DESCRIPTION
				"Contains the current state of the endpoint.  This is a
				bitmap of possible conditions. The various bit positions
				are:
				
				noDefect               There no defects on the line.
				
				powerBackoff           Indicates enhanced Power Backoff.
				
				deviceFault            Indicates a vendor-dependent
				                       diagnostic or self-test fault
				                       has been detected.
				
				dcContinuityFault      Indicates vendor-dependent
				                       conditions that interfere with
				                       span powering such as short and
				                       open circuits.
				
				snrMarginAlarm         Indicates that the SNR margin
				                       has dropped below the alarm threshold.
				
				loopAttenuationAlarm   Indicates that the loop attenuation
				                       exceeds the alarm threshold.
				
				loswFailureAlarm       Indicates a forward LOSW alarm.
				
				configInitFailure      Endpoint failure during initialization
				                       due to paired endpoint not able to
				                       support requested configuration.
				
				protocolInitFailure    Endpoint failure during initialization
				                       due to incompatible protocol used by
				                       the paired endpoint.
				
				noNeighborPresent      Endpoint failure during initialization
				                       due to no activation sequence detected
				                       from paired endpoint.
				
				loopbackActive         A loopback is currently active at this
				                       Segment Endpoint.
				
				This is intended to supplement ifOperStatus.  Note that there
				is a 1-1 relationship between the status bits defined in this
				object and the notification thresholds defined elsewhere in
				this MIB."
			REFERENCE
				"HDSL2 Section 7.5.3.7; SHDSL Section 9.5.5.7"
			::= { shehdsl2ShdslEndpointCurrEntry 3 }

		
--   1.3.6.1.4.1.231.7.1.2.2.1.12.1.2.7.7.1.4
		shehdsl2ShdslEndpointES OBJECT-TYPE
			SYNTAX Counter32
			UNITS "seconds"
			MAX-ACCESS read-only
			STATUS current
			DESCRIPTION
				"Count of Errored Seconds (ES) on this endpoint since the xU
				was last restarted."
			REFERENCE
				"HDSL2 Section 7.5.3.7; SHDSL Section 9.5.5.7"
			::= { shehdsl2ShdslEndpointCurrEntry 4 }

		
--   1.3.6.1.4.1.231.7.1.2.2.1.12.1.2.7.7.1.5
		shehdsl2ShdslEndpointSES OBJECT-TYPE
			SYNTAX Counter32
			UNITS "seconds"
			MAX-ACCESS read-only
			STATUS current
			DESCRIPTION
				"Count of Severely Errored Seconds (SES) on this endpoint
				since the xU was last restarted."
			REFERENCE
				"HDSL2 Section 7.5.3.7; SHDSL Section 9.5.5.7"
			::= { shehdsl2ShdslEndpointCurrEntry 5 }

		
--   1.3.6.1.4.1.231.7.1.2.2.1.12.1.2.7.7.1.6
		shehdsl2ShdslEndpointCRCanomalies OBJECT-TYPE
			SYNTAX Counter32
			UNITS "detected CRC Anomalies"
			MAX-ACCESS read-only
			STATUS current
			DESCRIPTION
				"Count of CRC anomalies on this endpoint since the xU was
				last restarted."
			REFERENCE
				"HDSL2 Section 7.5.3.7; SHDSL Section 9.5.5.7"
			::= { shehdsl2ShdslEndpointCurrEntry 6 }

		
--   1.3.6.1.4.1.231.7.1.2.2.1.12.1.2.7.7.1.7
		shehdsl2ShdslEndpointLOSWS OBJECT-TYPE
			SYNTAX Counter32
			UNITS "seconds"
			MAX-ACCESS read-only
			STATUS current
			DESCRIPTION
				"Count of Loss of Sync Word (LOSW) Seconds on this endpoint
				since the xU was last restarted."
			REFERENCE
				"HDSL2 Section 7.5.3.7; SHDSL Section 9.5.5.7"
			::= { shehdsl2ShdslEndpointCurrEntry 7 }

		
--   1.3.6.1.4.1.231.7.1.2.2.1.12.1.2.7.7.1.8
		shehdsl2ShdslEndpointUAS OBJECT-TYPE
			SYNTAX Counter32
			UNITS "seconds"
			MAX-ACCESS read-only
			STATUS current
			DESCRIPTION
				"Count of Unavailable Seconds (UAS) on this endpoint since
				the xU was last restarted."
			REFERENCE
				"HDSL2 Section 7.5.3.7; SHDSL Section 9.5.5.7"
			::= { shehdsl2ShdslEndpointCurrEntry 8 }

		
--   1.3.6.1.4.1.231.7.1.2.2.1.12.1.2.7.7.1.9
		shehdsl2ShdslEndpointCurr15MinTimeElapsed OBJECT-TYPE
			SYNTAX SheHdsl2ShdslPerfTimeElapsed
			UNITS "seconds"
			MAX-ACCESS read-only
			STATUS current
			DESCRIPTION
				"Total elapsed seconds in the current 15-minute interval."
			::= { shehdsl2ShdslEndpointCurrEntry 9 }

		
--   1.3.6.1.4.1.231.7.1.2.2.1.12.1.2.7.7.1.10
		shehdsl2ShdslEndpointCurr15MinES OBJECT-TYPE
			SYNTAX PerfCurrentCount
			UNITS "seconds"
			MAX-ACCESS read-only
			STATUS current
			DESCRIPTION
				"Count of Errored Seconds (ES) in the current 15-minute
				interval."
			REFERENCE
				"HDSL2 Section 7.5.3.7; SHDSL Section 9.5.5.7"
			::= { shehdsl2ShdslEndpointCurrEntry 10 }

		
--   1.3.6.1.4.1.231.7.1.2.2.1.12.1.2.7.7.1.11
		shehdsl2ShdslEndpointCurr15MinSES OBJECT-TYPE
			SYNTAX PerfCurrentCount
			UNITS "seconds"
			MAX-ACCESS read-only
			STATUS current
			DESCRIPTION
				"Count of Severely Errored Seconds (SES) in the current
				15-minute interval."
			REFERENCE
				"HDSL2 Section 7.5.3.7; SHDSL Section 9.5.5.7"
			::= { shehdsl2ShdslEndpointCurrEntry 11 }

		
--   1.3.6.1.4.1.231.7.1.2.2.1.12.1.2.7.7.1.12
		shehdsl2ShdslEndpointCurr15MinCRCanomalies OBJECT-TYPE
			SYNTAX PerfCurrentCount
			UNITS "detected CRC Anomalies"
			MAX-ACCESS read-only
			STATUS current
			DESCRIPTION
				"Count of CRC anomalies in the current 15-minute interval."
			REFERENCE
				"HDSL2 Section 7.5.3.7; SHDSL Section 9.5.5.7"
			::= { shehdsl2ShdslEndpointCurrEntry 12 }

		
--   1.3.6.1.4.1.231.7.1.2.2.1.12.1.2.7.7.1.13
		shehdsl2ShdslEndpointCurr15MinLOSWS OBJECT-TYPE
			SYNTAX PerfCurrentCount
			UNITS "seconds"
			MAX-ACCESS read-only
			STATUS current
			DESCRIPTION
				"Count of Loss of Sync Word (LOSW) Seconds in the current
				15-minute interval."
			REFERENCE
				"HDSL2 Section 7.5.3.7; SHDSL Section 9.5.5.7"
			::= { shehdsl2ShdslEndpointCurrEntry 13 }

		
--   1.3.6.1.4.1.231.7.1.2.2.1.12.1.2.7.7.1.14
		shehdsl2ShdslEndpointCurr15MinUAS OBJECT-TYPE
			SYNTAX PerfCurrentCount
			UNITS "seconds"
			MAX-ACCESS read-only
			STATUS current
			DESCRIPTION
				"Count of Unavailable Seconds (UAS) in the current 15-minute
				interval."
			REFERENCE
				"HDSL2 Section 7.5.3.7; SHDSL Section 9.5.5.7"
			::= { shehdsl2ShdslEndpointCurrEntry 14 }

		
--   1.3.6.1.4.1.231.7.1.2.2.1.12.1.2.7.7.1.15
		shehdsl2ShdslEndpointCurr1DayTimeElapsed OBJECT-TYPE
			SYNTAX SheHdsl2ShdslPerfTimeElapsed
			UNITS "seconds"
			MAX-ACCESS read-only
			STATUS current
			DESCRIPTION
				"Number of seconds that have elapsed since the beginning of
				the current 1-day interval."
			::= { shehdsl2ShdslEndpointCurrEntry 15 }

		
--   1.3.6.1.4.1.231.7.1.2.2.1.12.1.2.7.7.1.16
		shehdsl2ShdslEndpointCurr1DayES OBJECT-TYPE
			SYNTAX SheHdsl2ShdslPerfCurrDayCount
			UNITS "seconds"
			MAX-ACCESS read-only
			STATUS current
			DESCRIPTION
				"Count of Errored Seconds (ES) during the current day as
				measured by hdsl2ShdslEndpointCurr1DayTimeElapsed."
			REFERENCE
				"HDSL2 Section 7.5.3.7; SHDSL Section 9.5.5.7"
			::= { shehdsl2ShdslEndpointCurrEntry 16 }

		
--   1.3.6.1.4.1.231.7.1.2.2.1.12.1.2.7.7.1.17
		shehdsl2ShdslEndpointCurr1DaySES OBJECT-TYPE
			SYNTAX SheHdsl2ShdslPerfCurrDayCount
			UNITS "seconds"
			MAX-ACCESS read-only
			STATUS current
			DESCRIPTION
				"Count of Severely Errored Seconds (SES) during the current
				day as measured by hdsl2ShdslEndpointCurr1DayTimeElapsed."
			REFERENCE
				"HDSL2 Section 7.5.3.7; SHDSL Section 9.5.5.7"
			::= { shehdsl2ShdslEndpointCurrEntry 17 }

		
--   1.3.6.1.4.1.231.7.1.2.2.1.12.1.2.7.7.1.18
		shehdsl2ShdslEndpointCurr1DayCRCanomalies OBJECT-TYPE
			SYNTAX SheHdsl2ShdslPerfCurrDayCount
			UNITS "detected CRC Anomalies"
			MAX-ACCESS read-only
			STATUS current
			DESCRIPTION
				"Count of CRC anomalies during the current day as measured
				by hdsl2ShdslEndpointCurr1DayTimeElapsed."
			REFERENCE
				"HDSL2 Section 7.5.3.7; SHDSL Section 9.5.5.7"
			::= { shehdsl2ShdslEndpointCurrEntry 18 }

		
--   1.3.6.1.4.1.231.7.1.2.2.1.12.1.2.7.7.1.19
		shehdsl2ShdslEndpointCurr1DayLOSWS OBJECT-TYPE
			SYNTAX SheHdsl2ShdslPerfCurrDayCount
			UNITS "seconds"
			MAX-ACCESS read-only
			STATUS current
			DESCRIPTION
				"Count of Loss of Sync Word (LOSW) Seconds during the current
				day as measured by hdsl2ShdslEndpointCurr1DayTimeElapsed."
			REFERENCE
				"HDSL2 Section 7.5.3.7; SHDSL Section 9.5.5.7"
			::= { shehdsl2ShdslEndpointCurrEntry 19 }

		
--   1.3.6.1.4.1.231.7.1.2.2.1.12.1.2.7.7.1.20
		shehdsl2ShdslEndpointCurr1DayUAS OBJECT-TYPE
			SYNTAX SheHdsl2ShdslPerfCurrDayCount
			UNITS "seconds"
			MAX-ACCESS read-only
			STATUS current
			DESCRIPTION
				"Count of Unavailable Seconds (UAS) during the current day as
				measured by hdsl2ShdslEndpointCurr1DayTimeElapsed."
			REFERENCE
				"HDSL2 Section 7.5.3.7; SHDSL Section 9.5.5.7"
			::= { shehdsl2ShdslEndpointCurrEntry 20 }

		
--   1.3.6.1.4.1.231.7.1.2.2.1.12.1.2.7.7.1.21
		shehdsl2ShdslEndpointCurrTipRingReversal OBJECT-TYPE
			SYNTAX Shehdsl2ShdslMaintTipRingReversalType
			MAX-ACCESS read-only
			STATUS current
			DESCRIPTION
				"This object indicates the state of the tip/ring for the wire pair.
				normal(1),
				reversed(2)"
			::= { shehdsl2ShdslEndpointCurrEntry 21 }

		
--   1.3.6.1.4.1.231.7.1.2.2.1.12.1.2.7.7.1.22
		shehdsl2ShdslEndpointCurrActivationState OBJECT-TYPE
			SYNTAX SheHdsl2ShdslActivationStateType
			MAX-ACCESS read-only
			STATUS current
			DESCRIPTION
				"This object indicates the activation or training state of the wire pair.
				preActivation(1),  -> PreTrain
				activation(2),     -> Training
				data(3)            -> Trained"
			REFERENCE
				"ITU-T G.991.2, Section 6.2 PMD Activation Sequence"
			::= { shehdsl2ShdslEndpointCurrEntry 22 }

		
--   1.3.6.1.4.1.231.7.1.2.2.1.12.1.2.7.8
		shehdsl2Shdsl15MinIntervalTable OBJECT-TYPE
			SYNTAX SEQUENCE OF Shehdsl2Shdsl15MinIntervalEntry
			MAX-ACCESS not-accessible
			STATUS current
			DESCRIPTION
				"This table provides one row for each HDSL2/SHDSL endpoint
				performance data collection interval.  This table contains
				live data from equipment.  As such, it is NOT persistent."
			::= { shehdsl2ShdslMibObjects 8 }

		
--   1.3.6.1.4.1.231.7.1.2.2.1.12.1.2.7.8.1
		shehdsl2Shdsl15MinIntervalEntry OBJECT-TYPE
			SYNTAX Shehdsl2Shdsl15MinIntervalEntry
			MAX-ACCESS not-accessible
			STATUS current
			DESCRIPTION
				"An entry in the hdsl2Shdsl15MinIntervalTable."
			INDEX { ifIndex, shehdsl2ShdslInvIndex, shehdsl2ShdslEndpointSide, shehdsl2ShdslEndpointWirePair, shehdsl2Shdsl15MinIntervalNumber
				 }
			::= { shehdsl2Shdsl15MinIntervalTable 1 }

		
		Shehdsl2Shdsl15MinIntervalEntry ::=
			SEQUENCE { 
				shehdsl2Shdsl15MinIntervalNumber
					Unsigned32,
				shehdsl2Shdsl15MinIntervalEndTime
					TimeTicks,
				shehdsl2Shdsl15MinIntervalES
					PerfIntervalCount,
				shehdsl2Shdsl15MinIntervalSES
					PerfIntervalCount,
				shehdsl2Shdsl15MinIntervalCRCanomalies
					PerfIntervalCount,
				shehdsl2Shdsl15MinIntervalLOSWS
					PerfIntervalCount,
				shehdsl2Shdsl15MinIntervalUAS
					PerfIntervalCount
			 }

--   1.3.6.1.4.1.231.7.1.2.2.1.12.1.2.7.8.1.1
		shehdsl2Shdsl15MinIntervalNumber OBJECT-TYPE
			SYNTAX Unsigned32 (1..96)
			MAX-ACCESS not-accessible
			STATUS current
			DESCRIPTION
				"Performance Data Interval number. 1 is the the most recent
				previous interval; interval 96 is 24 hours ago. Intervals
				2..96 are optional."
			::= { shehdsl2Shdsl15MinIntervalEntry 1 }

		
--   1.3.6.1.4.1.231.7.1.2.2.1.12.1.2.7.8.1.2
		shehdsl2Shdsl15MinIntervalEndTime OBJECT-TYPE
			SYNTAX TimeTicks
			MAX-ACCESS read-only
			STATUS current
			DESCRIPTION
				"This variable indicates the time of storing this interval."
			::= { shehdsl2Shdsl15MinIntervalEntry 2 }

		
--   1.3.6.1.4.1.231.7.1.2.2.1.12.1.2.7.8.1.3
		shehdsl2Shdsl15MinIntervalES OBJECT-TYPE
			SYNTAX PerfIntervalCount
			UNITS "seconds"
			MAX-ACCESS read-only
			STATUS current
			DESCRIPTION
				"Count of Errored Seconds (ES) during the interval."
			REFERENCE
				"HDSL2 Section 7.5.3.7; SHDSL Section 9.5.5.7"
			::= { shehdsl2Shdsl15MinIntervalEntry 3 }

		
--   1.3.6.1.4.1.231.7.1.2.2.1.12.1.2.7.8.1.4
		shehdsl2Shdsl15MinIntervalSES OBJECT-TYPE
			SYNTAX PerfIntervalCount
			UNITS "seconds"
			MAX-ACCESS read-only
			STATUS current
			DESCRIPTION
				"Count of Severely Errored Seconds (SES) during the interval."
			REFERENCE
				"HDSL2 Section 7.5.3.7; SHDSL Section 9.5.5.7"
			::= { shehdsl2Shdsl15MinIntervalEntry 4 }

		
--   1.3.6.1.4.1.231.7.1.2.2.1.12.1.2.7.8.1.5
		shehdsl2Shdsl15MinIntervalCRCanomalies OBJECT-TYPE
			SYNTAX PerfIntervalCount
			UNITS "detected CRC Anomalies"
			MAX-ACCESS read-only
			STATUS current
			DESCRIPTION
				"Count of CRC anomalies during the interval."
			REFERENCE
				"HDSL2 Section 7.5.3.7; SHDSL Section 9.5.5.7"
			::= { shehdsl2Shdsl15MinIntervalEntry 5 }

		
--   1.3.6.1.4.1.231.7.1.2.2.1.12.1.2.7.8.1.6
		shehdsl2Shdsl15MinIntervalLOSWS OBJECT-TYPE
			SYNTAX PerfIntervalCount
			UNITS "seconds"
			MAX-ACCESS read-only
			STATUS current
			DESCRIPTION
				"Count of Loss of Sync Word (LOSW) Seconds during the
				interval."
			REFERENCE
				"HDSL2 Section 7.5.3.7; SHDSL Section 9.5.5.7"
			::= { shehdsl2Shdsl15MinIntervalEntry 6 }

		
--   1.3.6.1.4.1.231.7.1.2.2.1.12.1.2.7.8.1.7
		shehdsl2Shdsl15MinIntervalUAS OBJECT-TYPE
			SYNTAX PerfIntervalCount
			UNITS "seconds"
			MAX-ACCESS read-only
			STATUS current
			DESCRIPTION
				"Count of Unavailable Seconds (UAS) during the interval."
			REFERENCE
				"HDSL2 Section 7.5.3.7; SHDSL Section 9.5.5.7"
			::= { shehdsl2Shdsl15MinIntervalEntry 7 }

		
--   1.3.6.1.4.1.231.7.1.2.2.1.12.1.2.7.9
		shehdsl2Shdsl1DayIntervalTable OBJECT-TYPE
			SYNTAX SEQUENCE OF Shehdsl2Shdsl1DayIntervalEntry
			MAX-ACCESS not-accessible
			STATUS current
			DESCRIPTION
				"This table provides one row for each HDSL2/SHDSL endpoint
				performance data collection interval.  This table contains
				live data from equipment.  As such, it is NOT persistent."
			::= { shehdsl2ShdslMibObjects 9 }

		
--   1.3.6.1.4.1.231.7.1.2.2.1.12.1.2.7.9.1
		shehdsl2Shdsl1DayIntervalEntry OBJECT-TYPE
			SYNTAX Shehdsl2Shdsl1DayIntervalEntry
			MAX-ACCESS not-accessible
			STATUS current
			DESCRIPTION
				"An entry in the hdsl2Shdsl1DayIntervalTable."
			INDEX { ifIndex, shehdsl2ShdslInvIndex, shehdsl2ShdslEndpointSide, shehdsl2ShdslEndpointWirePair, shehdsl2Shdsl1DayIntervalNumber
				 }
			::= { shehdsl2Shdsl1DayIntervalTable 1 }

		
		Shehdsl2Shdsl1DayIntervalEntry ::=
			SEQUENCE { 
				shehdsl2Shdsl1DayIntervalNumber
					Unsigned32,
				shehdsl2Shdsl1DayIntervalEndTime
					TimeTicks,
				shehdsl2Shdsl1DayIntervalMoniSecs
					SheHdsl2ShdslPerfTimeElapsed,
				shehdsl2Shdsl1DayIntervalES
					SheHdsl2Shdsl1DayIntervalCount,
				shehdsl2Shdsl1DayIntervalSES
					SheHdsl2Shdsl1DayIntervalCount,
				shehdsl2Shdsl1DayIntervalCRCanomalies
					SheHdsl2Shdsl1DayIntervalCount,
				shehdsl2Shdsl1DayIntervalLOSWS
					SheHdsl2Shdsl1DayIntervalCount,
				shehdsl2Shdsl1DayIntervalUAS
					SheHdsl2Shdsl1DayIntervalCount
			 }

--   1.3.6.1.4.1.231.7.1.2.2.1.12.1.2.7.9.1.1
		shehdsl2Shdsl1DayIntervalNumber OBJECT-TYPE
			SYNTAX Unsigned32 (1..30)
			MAX-ACCESS not-accessible
			STATUS current
			DESCRIPTION
				"History Data Interval number. Interval 1 is the the most
				recent previous day; interval 30 is 30 days ago. Intervals
				2..30 are optional."
			::= { shehdsl2Shdsl1DayIntervalEntry 1 }

		
--   1.3.6.1.4.1.231.7.1.2.2.1.12.1.2.7.9.1.2
		shehdsl2Shdsl1DayIntervalEndTime OBJECT-TYPE
			SYNTAX TimeTicks
			MAX-ACCESS read-only
			STATUS current
			DESCRIPTION
				"This variable indicates the time of storing this interval."
			::= { shehdsl2Shdsl1DayIntervalEntry 2 }

		
--   1.3.6.1.4.1.231.7.1.2.2.1.12.1.2.7.9.1.3
		shehdsl2Shdsl1DayIntervalMoniSecs OBJECT-TYPE
			SYNTAX SheHdsl2ShdslPerfTimeElapsed
			UNITS "seconds"
			MAX-ACCESS read-only
			STATUS current
			DESCRIPTION
				"The amount of time in the 1-day interval over which the
				performance monitoring information is actually counted.
				This value will be the same as the interval duration except
				in a situation where performance monitoring data could not
				be collected for any reason."
			::= { shehdsl2Shdsl1DayIntervalEntry 3 }

		
--   1.3.6.1.4.1.231.7.1.2.2.1.12.1.2.7.9.1.4
		shehdsl2Shdsl1DayIntervalES OBJECT-TYPE
			SYNTAX SheHdsl2Shdsl1DayIntervalCount
			UNITS "seconds"
			MAX-ACCESS read-only
			STATUS current
			DESCRIPTION
				"Count of Errored Seconds (ES) during the 1-day interval as
				measured by hdsl2Shdsl1DayIntervalMoniSecs."
			REFERENCE
				"HDSL2 Section 7.5.3.7; SHDSL Section 9.5.5.7"
			::= { shehdsl2Shdsl1DayIntervalEntry 4 }

		
--   1.3.6.1.4.1.231.7.1.2.2.1.12.1.2.7.9.1.5
		shehdsl2Shdsl1DayIntervalSES OBJECT-TYPE
			SYNTAX SheHdsl2Shdsl1DayIntervalCount
			UNITS "seconds"
			MAX-ACCESS read-only
			STATUS current
			DESCRIPTION
				"Count of Severely Errored Seconds (SES) during the 1-day
				interval as measured by hdsl2Shdsl1DayIntervalMoniSecs."
			REFERENCE
				"HDSL2 Section 7.5.3.7; SHDSL Section 9.5.5.7"
			::= { shehdsl2Shdsl1DayIntervalEntry 5 }

		
--   1.3.6.1.4.1.231.7.1.2.2.1.12.1.2.7.9.1.6
		shehdsl2Shdsl1DayIntervalCRCanomalies OBJECT-TYPE
			SYNTAX SheHdsl2Shdsl1DayIntervalCount
			UNITS "detected CRC Anomalies"
			MAX-ACCESS read-only
			STATUS current
			DESCRIPTION
				"Count of CRC anomalies during the 1-day interval as
				measured by hdsl2Shdsl1DayIntervalMoniSecs."
			REFERENCE
				"HDSL2 Section 7.5.3.7; SHDSL Section 9.5.5.7"
			::= { shehdsl2Shdsl1DayIntervalEntry 6 }

		
--   1.3.6.1.4.1.231.7.1.2.2.1.12.1.2.7.9.1.7
		shehdsl2Shdsl1DayIntervalLOSWS OBJECT-TYPE
			SYNTAX SheHdsl2Shdsl1DayIntervalCount
			UNITS "seconds"
			MAX-ACCESS read-only
			STATUS current
			DESCRIPTION
				"Count of Loss of Sync Word (LOSW) Seconds during the 1-day
				interval as measured by hdsl2Shdsl1DayIntervalMoniSecs."
			REFERENCE
				"HDSL2 Section 7.5.3.7; SHDSL Section 9.5.5.7"
			::= { shehdsl2Shdsl1DayIntervalEntry 7 }

		
--   1.3.6.1.4.1.231.7.1.2.2.1.12.1.2.7.9.1.8
		shehdsl2Shdsl1DayIntervalUAS OBJECT-TYPE
			SYNTAX SheHdsl2Shdsl1DayIntervalCount
			UNITS "seconds"
			MAX-ACCESS read-only
			STATUS current
			DESCRIPTION
				"Count of Unavailable Seconds (UAS) during the 1-day interval
				as measured by hdsl2Shdsl1DayIntervalMoniSecs."
			REFERENCE
				"HDSL2 Section 7.5.3.7; SHDSL Section 9.5.5.7"
			::= { shehdsl2Shdsl1DayIntervalEntry 8 }

		
--   1.3.6.1.4.1.231.7.1.2.2.1.12.1.2.7.10
		shehdsl2ShdslEndpointMaintTable OBJECT-TYPE
			SYNTAX SEQUENCE OF Shehdsl2ShdslEndpointMaintEntry
			MAX-ACCESS not-accessible
			STATUS current
			DESCRIPTION
				"This table supports maintenance operations (eg. loopbacks)
				to be performed on HDSL2/SHDSL segment endpoints.  This table
				contains live data from equipment.  As such, it is NOT
				persistent."
			::= { shehdsl2ShdslMibObjects 10 }

		
--   1.3.6.1.4.1.231.7.1.2.2.1.12.1.2.7.10.1
		shehdsl2ShdslEndpointMaintEntry OBJECT-TYPE
			SYNTAX Shehdsl2ShdslEndpointMaintEntry
			MAX-ACCESS not-accessible
			STATUS current
			DESCRIPTION
				"An entry in the hdsl2ShdslEndpointMaintTable.  Each entry
				corresponds to a single segment endpoint, and is indexed by the
				ifIndex of the HDSL2/SHDSL line, the UnitId of the associated
				unit and the side of the unit."
			INDEX { ifIndex, shehdsl2ShdslInvIndex, shehdsl2ShdslEndpointSide }
			::= { shehdsl2ShdslEndpointMaintTable 1 }

		
		Shehdsl2ShdslEndpointMaintEntry ::=
			SEQUENCE { 
				shehdsl2ShdslMaintLoopbackConfig
					Shehdsl2ShdslMaintLoopbackConfigType,
				shehdsl2ShdslMaintTipRingReversal
					Shehdsl2ShdslMaintTipRingReversalType,
				shehdsl2ShdslMaintPowerBackOff
					Shehdsl2ShdslMaintPowerBackOffType,
				shehdsl2ShdslMaintSoftRestart
					Shehdsl2ShdslMaintSoftRestartType
			 }

--   1.3.6.1.4.1.231.7.1.2.2.1.12.1.2.7.10.1.1
		shehdsl2ShdslMaintLoopbackConfig OBJECT-TYPE
			SYNTAX Shehdsl2ShdslMaintLoopbackConfigType
			MAX-ACCESS read-only
			STATUS current
			DESCRIPTION
				"This object controls configuration of loopbacks for the
				associated segment endpoint.  The status of the loopback
				is obtained via the hdsl2ShdslEndpointCurrStatus object.
				
				noLoopback(1),
				normalLoopback(2) is available for STU-C and STU-R.
				
				specialLoopback(3),
				normalLoopbackEocId9(8),
				specialLoopbackEocId9(9)  are only available for STU-R.
				
				digitalLoopback(4)
				analogLoopback(5)
				interfaceLoopBack(6)
				localFramerLoopback(7) are only available for STU-C.
				
				Loopmode 2 and 3 are standard defined. All other modes are proprietary
				and not supported by all lines.
				"
			::= { shehdsl2ShdslEndpointMaintEntry 1 }

		
--   1.3.6.1.4.1.231.7.1.2.2.1.12.1.2.7.10.1.2
		shehdsl2ShdslMaintTipRingReversal OBJECT-TYPE
			SYNTAX Shehdsl2ShdslMaintTipRingReversalType
			MAX-ACCESS read-only
			STATUS current
			DESCRIPTION
				"This object indicates the state of the tip/ring pair at the
				associated segment endpoint.
				
				normal(1),
				reversed(2)"
			::= { shehdsl2ShdslEndpointMaintEntry 2 }

		
--   1.3.6.1.4.1.231.7.1.2.2.1.12.1.2.7.10.1.3
		shehdsl2ShdslMaintPowerBackOff OBJECT-TYPE
			SYNTAX Shehdsl2ShdslMaintPowerBackOffType
			MAX-ACCESS read-only
			STATUS current
			DESCRIPTION
				"This object configures the receiver at the associated
				segment endpoint to operate in default or enhanced power
				backoff mode.
				
				default(1),
				enhanced(2) is actual not supported for STU-C
				disable(3) is actual not supported for STU-R
				"
			DEFVAL { 1 }
			::= { shehdsl2ShdslEndpointMaintEntry 3 }

		
--   1.3.6.1.4.1.231.7.1.2.2.1.12.1.2.7.10.1.4
		shehdsl2ShdslMaintSoftRestart OBJECT-TYPE
			SYNTAX Shehdsl2ShdslMaintSoftRestartType
			MAX-ACCESS read-only
			STATUS current
			DESCRIPTION
				"This object enables the manager to trigger a soft restart
				of the modem at the associated segment endpoint.  The manager
				may only set this object to the 'restart(2)' value, which
				initiates a restart.  The agent will perform a restart after
				approximately 5 seconds.  Following the 5 second period, the
				agent will restore the object to the 'ready(1)' state.
				"
			::= { shehdsl2ShdslEndpointMaintEntry 4 }

		
--   1.3.6.1.4.1.231.7.1.2.2.1.12.1.2.7.11
		shehdsl2ShdslEndpointMaintControl OBJECT IDENTIFIER ::= { shehdsl2ShdslMibObjects 11 }

		
--   1.3.6.1.4.1.231.7.1.2.2.1.12.1.2.7.11.1
		shehdsl2ShdslEndpointMaintControlRequest OBJECT-TYPE
			SYNTAX SheShdslControlRequestType
			MAX-ACCESS read-write
			STATUS current
			DESCRIPTION
				"modifyshehdsl2ShdslEndpointMaintEntry
				
				"
			::= { shehdsl2ShdslEndpointMaintControl 1 }

		
--   1.3.6.1.4.1.231.7.1.2.2.1.12.1.2.7.11.2
		shehdsl2ShdslEndpointMaintControlIndex OBJECT-TYPE
			SYNTAX InterfaceIndex
			MAX-ACCESS read-write
			STATUS current
			DESCRIPTION
				"First key for the modified entry. IfIndex of line."
			::= { shehdsl2ShdslEndpointMaintControl 2 }

		
--   1.3.6.1.4.1.231.7.1.2.2.1.12.1.2.7.11.3
		shehdsl2ShdslEndpointMaintControlStatus OBJECT-TYPE
			SYNTAX SheControlStatusType
			MAX-ACCESS read-only
			STATUS current
			DESCRIPTION
				"The status of a user command. 
				"
			::= { shehdsl2ShdslEndpointMaintControl 3 }

		
--   1.3.6.1.4.1.231.7.1.2.2.1.12.1.2.7.11.4
		shehdsl2ShdslEndpointMaintControlTimer OBJECT-TYPE
			SYNTAX Gauge32
			MAX-ACCESS read-only
			STATUS current
			DESCRIPTION
				"The maximum wait time for the manager for a long running user command. 
				"
			::= { shehdsl2ShdslEndpointMaintControl 4 }

		
--   1.3.6.1.4.1.231.7.1.2.2.1.12.1.2.7.11.5
		shehdsl2ShdslEndpointMaintControlReqResult OBJECT-TYPE
			SYNTAX SheShdslControlRequestResultType
			MAX-ACCESS read-only
			STATUS current
			DESCRIPTION
				"The result of the last user command."
			::= { shehdsl2ShdslEndpointMaintControl 5 }

		
--   1.3.6.1.4.1.231.7.1.2.2.1.12.1.2.7.11.6
		shehdsl2ShdslEndpointMaintControlTimeStamp OBJECT-TYPE
			SYNTAX Unsigned32
			UNITS "sec"
			MAX-ACCESS read-only
			STATUS current
			DESCRIPTION
				"The time stamp of the last command (end of command)."
			::= { shehdsl2ShdslEndpointMaintControl 6 }

		
--   1.3.6.1.4.1.231.7.1.2.2.1.12.1.2.7.11.7
		shehdsl2ShdslEndpointMaintControlInvIndex OBJECT-TYPE
			SYNTAX SheHdsl2ShdslUnitId
			MAX-ACCESS read-write
			STATUS current
			DESCRIPTION
				"Second key for modified entry."
			::= { shehdsl2ShdslEndpointMaintControl 7 }

		
--   1.3.6.1.4.1.231.7.1.2.2.1.12.1.2.7.11.8
		shehdsl2ShdslEndpointMaintControlSide OBJECT-TYPE
			SYNTAX SheHdsl2ShdslUnitSide
			MAX-ACCESS read-write
			STATUS current
			DESCRIPTION
				"Third key for the modified entry. "
			::= { shehdsl2ShdslEndpointMaintControl 8 }

		
--   1.3.6.1.4.1.231.7.1.2.2.1.12.1.2.7.11.9
		shehdsl2ShdslEndpointMaintControlLoopbackConfig OBJECT-TYPE
			SYNTAX Shehdsl2ShdslMaintLoopbackConfigType
			MAX-ACCESS read-write
			STATUS current
			DESCRIPTION
				"Look at table."
			::= { shehdsl2ShdslEndpointMaintControl 9 }

		
--   1.3.6.1.4.1.231.7.1.2.2.1.12.1.2.7.11.10
		shehdsl2ShdslEndpointMaintControlPowerBackOff OBJECT-TYPE
			SYNTAX Shehdsl2ShdslMaintPowerBackOffType
			MAX-ACCESS read-write
			STATUS current
			DESCRIPTION
				"Look at table."
			::= { shehdsl2ShdslEndpointMaintControl 10 }

		
--   1.3.6.1.4.1.231.7.1.2.2.1.12.1.2.7.11.11
		shehdsl2ShdslEndpointMaintControlSoftRestart OBJECT-TYPE
			SYNTAX Shehdsl2ShdslMaintSoftRestartType
			MAX-ACCESS read-write
			STATUS current
			DESCRIPTION
				"Look at table."
			::= { shehdsl2ShdslEndpointMaintControl 11 }

		
--   1.3.6.1.4.1.231.7.1.2.2.1.12.1.2.7.12
		shehdsl2ShdslUnitMaintTable OBJECT-TYPE
			SYNTAX SEQUENCE OF Shehdsl2ShdslUnitMaintEntry
			MAX-ACCESS not-accessible
			STATUS current
			DESCRIPTION
				"This table supports maintenance operations for units in a
				HDSL2/SHDSL line.  Entries in this table MUST be maintained
				in a persistent manner."
			::= { shehdsl2ShdslMibObjects 12 }

		
--   1.3.6.1.4.1.231.7.1.2.2.1.12.1.2.7.12.1
		shehdsl2ShdslUnitMaintEntry OBJECT-TYPE
			SYNTAX Shehdsl2ShdslUnitMaintEntry
			MAX-ACCESS not-accessible
			STATUS current
			DESCRIPTION
				"An entry in the hdsl2ShdslUnitMaintTable.  Each entry
				corresponds to a single unit, and is indexed by the ifIndex
				of the HDSL2/SHDSL line and the UnitId of the associated
				unit."
			INDEX { ifIndex, shehdsl2ShdslInvIndex }
			::= { shehdsl2ShdslUnitMaintTable 1 }

		
		Shehdsl2ShdslUnitMaintEntry ::=
			SEQUENCE { 
				shehdsl2ShdslMaintLoopbackTimeout
					Integer32,
				shehdsl2ShdslMaintUnitPowerSource
					Shehdsl2ShdslMaintUnitPowerSourceType
			 }

--   1.3.6.1.4.1.231.7.1.2.2.1.12.1.2.7.12.1.1
		shehdsl2ShdslMaintLoopbackTimeout OBJECT-TYPE
			SYNTAX Integer32 (0..4095)
			UNITS "minutes"
			MAX-ACCESS read-only
			STATUS current
			DESCRIPTION
				"This object configures the timeout value for loopbacks
				initiated at segments endpoints contained in the associated
				unit.  A value of 0 disables the timeout."
			::= { shehdsl2ShdslUnitMaintEntry 1 }

		
--   1.3.6.1.4.1.231.7.1.2.2.1.12.1.2.7.12.1.2
		shehdsl2ShdslMaintUnitPowerSource OBJECT-TYPE
			SYNTAX Shehdsl2ShdslMaintUnitPowerSourceType
			MAX-ACCESS read-only
			STATUS current
			DESCRIPTION
				"This object indicates the DC power source being used by the
				associated unit.
				
				local(1),
				span(2)"
			::= { shehdsl2ShdslUnitMaintEntry 2 }

		
--   1.3.6.1.4.1.231.7.1.2.2.1.12.1.2.7.13
		shehdsl2ShdslUnitMaintControl OBJECT IDENTIFIER ::= { shehdsl2ShdslMibObjects 13 }

		
--   1.3.6.1.4.1.231.7.1.2.2.1.12.1.2.7.13.1
		shehdsl2ShdslUnitMaintControlRequest OBJECT-TYPE
			SYNTAX SheShdslControlRequestType
			MAX-ACCESS read-write
			STATUS current
			DESCRIPTION
				"modifyshehdsl2ShdslUnitMaintEntry
				
				"
			::= { shehdsl2ShdslUnitMaintControl 1 }

		
--   1.3.6.1.4.1.231.7.1.2.2.1.12.1.2.7.13.2
		shehdsl2ShdslUnitMaintControlIndex OBJECT-TYPE
			SYNTAX InterfaceIndex
			MAX-ACCESS read-write
			STATUS current
			DESCRIPTION
				"First key for the modified entry. IfIndex of line."
			::= { shehdsl2ShdslUnitMaintControl 2 }

		
--   1.3.6.1.4.1.231.7.1.2.2.1.12.1.2.7.13.3
		shehdsl2ShdslUnitMaintControlStatus OBJECT-TYPE
			SYNTAX SheControlStatusType
			MAX-ACCESS read-only
			STATUS current
			DESCRIPTION
				"The status of a user command. 
				"
			::= { shehdsl2ShdslUnitMaintControl 3 }

		
--   1.3.6.1.4.1.231.7.1.2.2.1.12.1.2.7.13.4
		shehdsl2ShdslUnitMaintControlTimer OBJECT-TYPE
			SYNTAX Gauge32
			MAX-ACCESS read-only
			STATUS current
			DESCRIPTION
				"The maximum wait time for the manager for a long running user command. 
				"
			::= { shehdsl2ShdslUnitMaintControl 4 }

		
--   1.3.6.1.4.1.231.7.1.2.2.1.12.1.2.7.13.5
		shehdsl2ShdslUnitMaintControlReqResult OBJECT-TYPE
			SYNTAX SheShdslControlRequestResultType
			MAX-ACCESS read-only
			STATUS current
			DESCRIPTION
				"The result of the last user command."
			::= { shehdsl2ShdslUnitMaintControl 5 }

		
--   1.3.6.1.4.1.231.7.1.2.2.1.12.1.2.7.13.6
		shehdsl2ShdslUnitMaintControlTimeStamp OBJECT-TYPE
			SYNTAX Unsigned32
			UNITS "sec"
			MAX-ACCESS read-only
			STATUS current
			DESCRIPTION
				"The time stamp of the last command (end of command)."
			::= { shehdsl2ShdslUnitMaintControl 6 }

		
--   1.3.6.1.4.1.231.7.1.2.2.1.12.1.2.7.13.7
		shehdsl2ShdslUnitMaintControlInvIndex OBJECT-TYPE
			SYNTAX SheHdsl2ShdslUnitId
			MAX-ACCESS read-write
			STATUS current
			DESCRIPTION
				"Second key for modified entry."
			::= { shehdsl2ShdslUnitMaintControl 7 }

		
--   1.3.6.1.4.1.231.7.1.2.2.1.12.1.2.7.13.8
		shehdsl2ShdslUnitMaintControlLoopbackTimeout OBJECT-TYPE
			SYNTAX Integer32 (0..4095)
			UNITS "minutes"
			MAX-ACCESS read-write
			STATUS current
			DESCRIPTION
				"Look at table."
			::= { shehdsl2ShdslUnitMaintControl 8 }

		
--   1.3.6.1.4.1.231.7.1.2.2.1.12.1.2.7.14
		shehdsl2ShdslSpanConfProfileTable OBJECT-TYPE
			SYNTAX SEQUENCE OF Shehdsl2ShdslSpanConfProfileEntry
			MAX-ACCESS not-accessible
			STATUS current
			DESCRIPTION
				"This table supports definitions of span configuration
				profiles for SHDSL lines.  HDSL2 does not support these
				configuration options.  This table MUST be maintained
				in a persistent manner."
			::= { shehdsl2ShdslMibObjects 14 }

		
--   1.3.6.1.4.1.231.7.1.2.2.1.12.1.2.7.14.1
		shehdsl2ShdslSpanConfProfileEntry OBJECT-TYPE
			SYNTAX Shehdsl2ShdslSpanConfProfileEntry
			MAX-ACCESS not-accessible
			STATUS current
			DESCRIPTION
				"Each entry corresponds to a single span configuration
				profile.  Each profile contains a set of span configuration
				parameters.  The configuration parameters in a profile are
				applied to those lines referencing that profile (see the
				hdsl2ShdslSpanConfProfile object). If an active
				entry is referenced in hdsl2ShdslSpanConfProfile, the
				entry MUST remain active until all references are removed."
			INDEX { shehdsl2ShdslSpanConfProfileIndex }
			::= { shehdsl2ShdslSpanConfProfileTable 1 }

		
		Shehdsl2ShdslSpanConfProfileEntry ::=
			SEQUENCE { 
				shehdsl2ShdslSpanConfProfileIndex
					Unsigned32,
				shehdsl2ShdslSpanConfProfileName
					SnmpAdminString,
				shehdsl2ShdslSpanConfWireInterface
					Shehdsl2ShdslSpanConfWireInterfaceType,
				shehdsl2ShdslSpanConfMinLineRate
					Unsigned32,
				shehdsl2ShdslSpanConfMaxLineRate
					Unsigned32,
				shehdsl2ShdslSpanConfPSD
					Shehdsl2ShdslSpanConfPSDType,
				shehdsl2ShdslSpanConfTransmissionMode
					SheHdsl2ShdslTransmissionModeType,
				shehdsl2ShdslSpanConfRemoteEnabled
					SheShdslEnableType,
				shehdsl2ShdslSpanConfPowerFeeding
					Shehdsl2ShdslSpanConfPowerFeedingType,
				shehdsl2ShdslSpanConfCurrCondTargetMarginDown
					Integer32,
				shehdsl2ShdslSpanConfWorstCaseTargetMarginDown
					Integer32,
				shehdsl2ShdslSpanConfCurrCondTargetMarginUp
					Integer32,
				shehdsl2ShdslSpanConfWorstCaseTargetMarginUp
					Integer32,
				shehdsl2ShdslSpanConfUsedTargetMargins
					Shehdsl2ShdslSpanConfUsedTargetMarginsType,
				shehdsl2ShdslSpanConfReferenceClock
					SheHdsl2ShdslClockReferenceType,
				shehdsl2ShdslSpanConfLineProbeEnable
					Shehdsl2ShdslSpanConfLineProbeEnableType,
				shehdsl2ShdslSpanConfPAMConstellation
					SheShdslPAMModeType,
				shehdsl2ShdslSpanConfTCLayerSupported
					SheHdsl2ShdslTCLayerType
			 }

--   1.3.6.1.4.1.231.7.1.2.2.1.12.1.2.7.14.1.1
		shehdsl2ShdslSpanConfProfileIndex OBJECT-TYPE
			SYNTAX Unsigned32 (1..64)
			MAX-ACCESS read-only
			STATUS current
			DESCRIPTION
				"A free running index for this table."
			::= { shehdsl2ShdslSpanConfProfileEntry 1 }

		
--   1.3.6.1.4.1.231.7.1.2.2.1.12.1.2.7.14.1.2
		shehdsl2ShdslSpanConfProfileName OBJECT-TYPE
			SYNTAX SnmpAdminString (SIZE (1..32))
			MAX-ACCESS read-only
			STATUS current
			DESCRIPTION
				"This object is the unique index associated with this profile.
				Entries in this table are referenced via the object
				hdsl2ShdslSpanConfProfile in Hdsl2ShdslSpanConfEntry.
				
				This characters are not allowed:  space : ?"
			::= { shehdsl2ShdslSpanConfProfileEntry 2 }

		
--   1.3.6.1.4.1.231.7.1.2.2.1.12.1.2.7.14.1.3
		shehdsl2ShdslSpanConfWireInterface OBJECT-TYPE
			SYNTAX Shehdsl2ShdslSpanConfWireInterfaceType
			MAX-ACCESS read-only
			STATUS current
			DESCRIPTION
				"This object configures the wire-interface operation for SHDSL Lines.
				
				twoWire(1),
				fourWire(2),
				fourWireBitInterleaved(3),
				fourWireByteInterleaveEnhanced(4),
				fourWireBitInterleaveEnhanced(5),
				sixWire(6),
				eightWire(7)
				
				Interfaces of type sdsl (96) support modes 1..5 and mode 3..5 are proprietary!
				Interfaces of type shdsl (169) will support mode 1..2 and 6..7!"
			DEFVAL { 1 }
			::= { shehdsl2ShdslSpanConfProfileEntry 3 }

		
--   for shdsl.bis(4624000 -> 11408000)
-- 1.3.6.1.4.1.231.7.1.2.2.1.12.1.2.7.14.1.4
		shehdsl2ShdslSpanConfMinLineRate OBJECT-TYPE
			SYNTAX Unsigned32 (0..22816000)
			UNITS "bps"
			MAX-ACCESS read-only
			STATUS current
			DESCRIPTION
				"This object configures the minimum transmission rate for the associated SHDSL Line
				in bits-per-second (bps). If the minimum line rate equals the maximum line rate
				(hdsl2ShdslSpanMaxLineRate), the line rate is considered 'fixed'.
				If the minimum line rate is less than the maximum line rate, the line rate is considered
				'rate-adaptive'. The minimum linerate should never be higher then the maximum linerate.
				Note:
				Technical usefull minium and maximum values depend on the configured WireInterface mode:
				twoWire mode -> minimum should be 200 kBits  ->  maximum should be 5704 kBits
				fourWire mode -> minimum should be 400 kBits  ->  maximum should be 11408 kBits
				sixWire mode -> minimum should be 600 kBits  ->  maximum should be 17112 kBits
				eigthWire mode -> minimum should be 800 kBits  ->  maximum should be 22816 kBits"
			DEFVAL { 1552000 }
			::= { shehdsl2ShdslSpanConfProfileEntry 4 }

		
--   for shdsl.bis(4624000 -> 11408000) 
-- 1.3.6.1.4.1.231.7.1.2.2.1.12.1.2.7.14.1.5
		shehdsl2ShdslSpanConfMaxLineRate OBJECT-TYPE
			SYNTAX Unsigned32 (0..22816000)
			UNITS "bps"
			MAX-ACCESS read-only
			STATUS current
			DESCRIPTION
				"This object configures the maximum transmission rate for the associated SHDSL Line in
				bits-per-second (bps). If the minimum line rate equals the maximum line rate (hdsl2ShdslSpanMaxLineRate),
				the line rate is considered 'fixed'. If the minimum line rate is less than the maximum line rate,
				the line rate is considered 'rate-adaptive'. The maximum linerate should never be less then the minimum linerate.
				Note:
				Technical usefull minium and maximum values depend on the configured WireInterface mode:
				twoWire mode -> minimum should be 200 kBits  ->  maximum should be 5704 kBits
				fourWire mode -> minimum should be 400 kBits  ->  maximum should be 11408 kBits
				sixWire mode -> minimum should be 600 kBits  ->  maximum should be 17112 kBits
				eigthWire mode -> minimum should be 800 kBits  ->  maximum should be 22816 kBits"
			DEFVAL { 1552000 }
			::= { shehdsl2ShdslSpanConfProfileEntry 5 }

		
--   1.3.6.1.4.1.231.7.1.2.2.1.12.1.2.7.14.1.6
		shehdsl2ShdslSpanConfPSD OBJECT-TYPE
			SYNTAX Shehdsl2ShdslSpanConfPSDType
			MAX-ACCESS read-only
			STATUS current
			DESCRIPTION
				"This object configures use of symmetric/asymmetric PSD (Power
				Spectral Density) Mask for the associated SHDSL Line.  Support
				for symmetric PSD is mandatory for all supported data rates.
				Support for asymmetric PSD is optional.
				
				symmetric(1),
				asymmetric(2),
				r1Asymmetric(3),
				r2Asymmetric(4)
				
				Mode 3..4 are propietary and only supported by interfaces of type sdsl (96)."
			DEFVAL { 1 }
			::= { shehdsl2ShdslSpanConfProfileEntry 6 }

		
--   1.3.6.1.4.1.231.7.1.2.2.1.12.1.2.7.14.1.7
		shehdsl2ShdslSpanConfTransmissionMode OBJECT-TYPE
			SYNTAX SheHdsl2ShdslTransmissionModeType
			MAX-ACCESS read-only
			STATUS current
			DESCRIPTION
				"This object specifies the regional setting for the SHDSL
				line. Minimum of one bit should always be set!
				
				Bit   Meaning      Description
				1     region 1     Indicates ITU-T G.991.2 Annex A/F.
				2     region 2     Indicates ITU-T G.991.2 Annex B/G."
			DEFVAL { { region1 } }
			::= { shehdsl2ShdslSpanConfProfileEntry 7 }

		
--   1.3.6.1.4.1.231.7.1.2.2.1.12.1.2.7.14.1.8
		shehdsl2ShdslSpanConfRemoteEnabled OBJECT-TYPE
			SYNTAX SheShdslEnableType
			MAX-ACCESS read-only
			STATUS current
			DESCRIPTION
				"This object enables/disables support for remote management
				of the units in a SHDSL line from the STU-R via the EOC.
				
				enabled(1),
				disabled(2)"
			DEFVAL { 1 }
			::= { shehdsl2ShdslSpanConfProfileEntry 8 }

		
--   1.3.6.1.4.1.231.7.1.2.2.1.12.1.2.7.14.1.9
		shehdsl2ShdslSpanConfPowerFeeding OBJECT-TYPE
			SYNTAX Shehdsl2ShdslSpanConfPowerFeedingType
			MAX-ACCESS read-only
			STATUS current
			DESCRIPTION
				"This object enables/disables support for optional power feeding in a SHDSL line.
				
				noPower(1),
				powerFeed(2),
				wettingCurrent(3)"
			DEFVAL { 1 }
			::= { shehdsl2ShdslSpanConfProfileEntry 9 }

		
--   1.3.6.1.4.1.231.7.1.2.2.1.12.1.2.7.14.1.10
		shehdsl2ShdslSpanConfCurrCondTargetMarginDown OBJECT-TYPE
			SYNTAX Integer32 (-10..21)
			UNITS "dB"
			MAX-ACCESS read-only
			STATUS current
			DESCRIPTION
				"This object specifies the downstream current condition target
				SNR margin for a SHDSL line.  The SNR margin is the difference
				between the desired SNR and the actual SNR.  Target SNR margin
				is the desired SNR margin for a unit."
			DEFVAL { 0 }
			::= { shehdsl2ShdslSpanConfProfileEntry 10 }

		
--   1.3.6.1.4.1.231.7.1.2.2.1.12.1.2.7.14.1.11
		shehdsl2ShdslSpanConfWorstCaseTargetMarginDown OBJECT-TYPE
			SYNTAX Integer32 (-10..21)
			UNITS "dB"
			MAX-ACCESS read-only
			STATUS current
			DESCRIPTION
				"This object specifies the downstream worst case target SNR
				margin for a SHDSL line.  The SNR margin is the difference
				between the desired SNR and the actual SNR.  Target SNR
				margin is the desired SNR margin for a unit."
			DEFVAL { 0 }
			::= { shehdsl2ShdslSpanConfProfileEntry 11 }

		
--   1.3.6.1.4.1.231.7.1.2.2.1.12.1.2.7.14.1.12
		shehdsl2ShdslSpanConfCurrCondTargetMarginUp OBJECT-TYPE
			SYNTAX Integer32 (-10..21)
			UNITS "dB"
			MAX-ACCESS read-only
			STATUS current
			DESCRIPTION
				"This object specifies the upstream current condition target
				SNR margin for a SHDSL line.  The SNR margin is the difference
				between the desired SNR and the actual SNR.  Target SNR margin
				is the desired SNR margin for a unit."
			DEFVAL { 0 }
			::= { shehdsl2ShdslSpanConfProfileEntry 12 }

		
--   1.3.6.1.4.1.231.7.1.2.2.1.12.1.2.7.14.1.13
		shehdsl2ShdslSpanConfWorstCaseTargetMarginUp OBJECT-TYPE
			SYNTAX Integer32 (-10..21)
			UNITS "dB"
			MAX-ACCESS read-only
			STATUS current
			DESCRIPTION
				"This object specifies the upstream worst case target SNR
				margin for a SHDSL line.  The SNR margin is the difference
				between the desired SNR and the actual SNR.  Target SNR margin
				is the desired SNR margin for a unit."
			DEFVAL { 0 }
			::= { shehdsl2ShdslSpanConfProfileEntry 13 }

		
--   1.3.6.1.4.1.231.7.1.2.2.1.12.1.2.7.14.1.14
		shehdsl2ShdslSpanConfUsedTargetMargins OBJECT-TYPE
			SYNTAX Shehdsl2ShdslSpanConfUsedTargetMarginsType
			MAX-ACCESS read-only
			STATUS current
			DESCRIPTION
				"Contains indicates whether a target SNR margin is enabled or
				disabled.  This is a bit-map of possible settings. Minimum of one bit should always be set!
				The various bit positions are:
				
				currCondDown     current condition downstream target SNR
				                 margin enabled
				
				worstCaseDown    worst case downstream target SNR margin
				                 enabled
				
				currCondUp       current condition upstream target SNR
				                 margin enabled
				
				worstCaseUp      worst case upstream target SNR margin
				                 enabled."
			DEFVAL { { currCondDown } }
			::= { shehdsl2ShdslSpanConfProfileEntry 14 }

		
--   1.3.6.1.4.1.231.7.1.2.2.1.12.1.2.7.14.1.15
		shehdsl2ShdslSpanConfReferenceClock OBJECT-TYPE
			SYNTAX SheHdsl2ShdslClockReferenceType
			MAX-ACCESS read-only
			STATUS current
			DESCRIPTION
				"This object configures the clock reference for the STU-C
				in a SHDSL Line. 
				Note:
				Interfaces of type sdsl (96) support only value localClk(1).
				Interfaces of type shdsl (169) support also the mode networkClk(2)."
			DEFVAL { localClk }
			::= { shehdsl2ShdslSpanConfProfileEntry 15 }

		
--   1.3.6.1.4.1.231.7.1.2.2.1.12.1.2.7.14.1.16
		shehdsl2ShdslSpanConfLineProbeEnable OBJECT-TYPE
			SYNTAX Shehdsl2ShdslSpanConfLineProbeEnableType
			MAX-ACCESS read-only
			STATUS current
			DESCRIPTION
				"This object enables/disables support for Line Probe of
				the units in a SHDSL line.  When Line Probe is enabled, the
				system performs Line Probing to find the best possible
				rate.  If Line probe is disabled, the rate adaptation phase
				is skipped to shorten set up time.
				
				disable(1),
				enable(2)"
			DEFVAL { 1 }
			::= { shehdsl2ShdslSpanConfProfileEntry 16 }

		
--   1.3.6.1.4.1.231.7.1.2.2.1.12.1.2.7.14.1.17
		shehdsl2ShdslSpanConfPAMConstellation OBJECT-TYPE
			SYNTAX SheShdslPAMModeType
			MAX-ACCESS read-only
			STATUS current
			DESCRIPTION
				"The parameter allows the selection of which PAM constellation is
				to be used.
				 - AUTO_PAM_SELECT - Automatic PAM selection
				 - SELECT_16_PAM   - Use 16 PAM only
				 - SELECT_32_PAM   - Use 32 PAM only
				Select 16Pam limits the data rates from 192 kbps to 3840 kbps
				Select 32Pam limits the data rates from 768 kbps to 5696 kbps
				+a--------------------------------------------------------+
				| Soc4e-Dsl-API : SHDSL_LineTcPamSelModeGet               |
				+---------------------------------------------------------+
				| SHDSL_TcPamSelMode_t * pMode                            |
				| pointer to store current TC-PAM selection mode          | 
				++--------------------------------------------------------+     
				| extented                                                |
				+---------------------------------------------------------+
				
				This is propietary extension for interfaces of type shdsl (169) only.
				"
			::= { shehdsl2ShdslSpanConfProfileEntry 17 }

		
--   1.3.6.1.4.1.231.7.1.2.2.1.12.1.2.7.14.1.20
		shehdsl2ShdslSpanConfTCLayerSupported OBJECT-TYPE
			SYNTAX SheHdsl2ShdslTCLayerType
			MAX-ACCESS read-only
			STATUS current
			DESCRIPTION
				"Specifies the TC-Layer. Set fix to 80)/ DSL_TC_ATM.
				(0) - DSL_TC_ATM
				(1) - DSL_TC_EFM
				(2) - DSL_TC_HDLC
				+a--------------------------------------------------------+
				| Soc4e-Dsl-API : DSL_SystemInterfaceConfigGet            |
				+---------------------------------------------------------+
				| DSL_SystemInterfaceConfig_t * pData                     |
				|                               DSL_TcLayerSelection_t    |
				+d--------------------------------------------------------+
				| Soc4e-Drv-Cmd : ACK_PMD_EndpointAlarmConfig             |
				+x--------------------------------------------------------+
				| sics <line> <nTcLayer> <nSystemIf>                      |
				+---------------------------------------------------------+
				
				This is propietary extension for interfaces of type shdsl (169) only.
				"
			REFERENCE
				"[WT-159] 5.5.3.1"
			::= { shehdsl2ShdslSpanConfProfileEntry 18 }

		
--   1.3.6.1.4.1.231.7.1.2.2.1.12.1.2.7.15
		shehdsl2ShdslSpanConfProfileControl OBJECT IDENTIFIER ::= { shehdsl2ShdslMibObjects 15 }

		
--   1.3.6.1.4.1.231.7.1.2.2.1.12.1.2.7.15.1
		shehdsl2ShdslSpanConfProfileControlRequest OBJECT-TYPE
			SYNTAX SheShdslControlRequestType
			MAX-ACCESS read-write
			STATUS current
			DESCRIPTION
				"createshehdsl2ShdslSpanConfProfile
				modifyshehdsl2ShdslSpanConfProfile
				deleteshehdsl2ShdslSpanConfProfile
				"
			::= { shehdsl2ShdslSpanConfProfileControl 1 }

		
--   1.3.6.1.4.1.231.7.1.2.2.1.12.1.2.7.15.2
		shehdsl2ShdslSpanConfProfileControlIndex OBJECT-TYPE
			SYNTAX Unsigned32 (1..64)
			MAX-ACCESS read-write
			STATUS current
			DESCRIPTION
				"Key for the modified or deleted entry. NE will choose this number during create. "
			::= { shehdsl2ShdslSpanConfProfileControl 2 }

		
--   1.3.6.1.4.1.231.7.1.2.2.1.12.1.2.7.15.3
		shehdsl2ShdslSpanConfProfileControlStatus OBJECT-TYPE
			SYNTAX SheControlStatusType
			MAX-ACCESS read-only
			STATUS current
			DESCRIPTION
				"The status of a user command. 
				"
			::= { shehdsl2ShdslSpanConfProfileControl 3 }

		
--   1.3.6.1.4.1.231.7.1.2.2.1.12.1.2.7.15.4
		shehdsl2ShdslSpanConfProfileControlTimer OBJECT-TYPE
			SYNTAX Gauge32
			MAX-ACCESS read-only
			STATUS current
			DESCRIPTION
				"The maximum wait time for the manager for a long running user command. 
				"
			::= { shehdsl2ShdslSpanConfProfileControl 4 }

		
--   1.3.6.1.4.1.231.7.1.2.2.1.12.1.2.7.15.5
		shehdsl2ShdslSpanConfProfileControlReqResult OBJECT-TYPE
			SYNTAX SheShdslControlRequestResultType
			MAX-ACCESS read-only
			STATUS current
			DESCRIPTION
				"The result of the last user command."
			::= { shehdsl2ShdslSpanConfProfileControl 5 }

		
--   1.3.6.1.4.1.231.7.1.2.2.1.12.1.2.7.15.6
		shehdsl2ShdslSpanConfProfileControlTimeStamp OBJECT-TYPE
			SYNTAX Unsigned32
			UNITS "sec"
			MAX-ACCESS read-only
			STATUS current
			DESCRIPTION
				"The time stamp of the last command (end of command)."
			::= { shehdsl2ShdslSpanConfProfileControl 6 }

		
--   1.3.6.1.4.1.231.7.1.2.2.1.12.1.2.7.15.7
		shehdsl2ShdslSpanConfProfileControlProfileName OBJECT-TYPE
			SYNTAX SnmpAdminString (SIZE (0..32))
			MAX-ACCESS read-write
			STATUS current
			DESCRIPTION
				"Name for new profile."
			::= { shehdsl2ShdslSpanConfProfileControl 7 }

		
--   1.3.6.1.4.1.231.7.1.2.2.1.12.1.2.7.15.8
		shehdsl2ShdslSpanConfProfileControlWireInterface OBJECT-TYPE
			SYNTAX Shehdsl2ShdslSpanConfWireInterfaceType
			MAX-ACCESS read-write
			STATUS current
			DESCRIPTION
				"Look at table.
				twoWire(1),
				fourWire(2),
				fourWireBitInterleaved(3),
				fourWireByteInterleaveEnhanced(4),
				fourWireBitInterleaveEnhanced(5),
				sixWire(6),
				eightWire(7)
				
				Interfaces of type sdsl (96) support modes 1..5 and mode 3..5 are proprietary!
				Interfaces of type shdsl (169) will support mode 1..2 and 6..7!"
			::= { shehdsl2ShdslSpanConfProfileControl 8 }

		
--   for shdsl.bis(4624000 -> 11408000)
-- 1.3.6.1.4.1.231.7.1.2.2.1.12.1.2.7.15.9
		shehdsl2ShdslSpanConfProfileControlMinLineRate OBJECT-TYPE
			SYNTAX Unsigned32 (0..22816000)
			UNITS "bps"
			MAX-ACCESS read-write
			STATUS current
			DESCRIPTION
				"Look at table.
				Note:
				Technical usefull minium and maximum values depend on the configured WireInterface mode:
				twoWire mode -> minimum should be 200 kBits  ->  maximum should be 5704 kBits
				fourWire mode -> minimum should be 400 kBits  ->  maximum should be 11408 kBits
				sixWire mode -> minimum should be 600 kBits  ->  maximum should be 17112 kBits
				eigthWire mode -> minimum should be 800 kBits  ->  maximum should be 22816 kBits"
			::= { shehdsl2ShdslSpanConfProfileControl 9 }

		
--   for shdsl.bis(4624000 -> 11408000)
-- 1.3.6.1.4.1.231.7.1.2.2.1.12.1.2.7.15.10
		shehdsl2ShdslSpanConfProfileControlMaxLineRate OBJECT-TYPE
			SYNTAX Unsigned32 (0..22816000)
			UNITS "bps"
			MAX-ACCESS read-write
			STATUS current
			DESCRIPTION
				"Look at table.
				Note:
				Technical usefull minium and maximum values depend on the configured WireInterface mode:
				twoWire mode -> minimum should be 200 kBits  ->  maximum should be 5704 kBits
				fourWire mode -> minimum should be 400 kBits  ->  maximum should be 11408 kBits
				sixWire mode -> minimum should be 600 kBits  ->  maximum should be 17112 kBits
				eigthWire mode -> minimum should be 800 kBits  ->  maximum should be 22816 kBits"
			::= { shehdsl2ShdslSpanConfProfileControl 10 }

		
--   1.3.6.1.4.1.231.7.1.2.2.1.12.1.2.7.15.11
		shehdsl2ShdslSpanConfProfileControlPSD OBJECT-TYPE
			SYNTAX Shehdsl2ShdslSpanConfPSDType
			MAX-ACCESS read-write
			STATUS current
			DESCRIPTION
				"Look at table."
			::= { shehdsl2ShdslSpanConfProfileControl 11 }

		
--   1.3.6.1.4.1.231.7.1.2.2.1.12.1.2.7.15.12
		shehdsl2ShdslSpanConfProfileControlTransmissionMode OBJECT-TYPE
			SYNTAX SheHdsl2ShdslTransmissionModeType
			MAX-ACCESS read-write
			STATUS current
			DESCRIPTION
				"Look at table."
			::= { shehdsl2ShdslSpanConfProfileControl 12 }

		
--   1.3.6.1.4.1.231.7.1.2.2.1.12.1.2.7.15.13
		shehdsl2ShdslSpanConfProfileControlRemoteEnabled OBJECT-TYPE
			SYNTAX SheShdslEnableType
			MAX-ACCESS read-write
			STATUS current
			DESCRIPTION
				"Look at table."
			::= { shehdsl2ShdslSpanConfProfileControl 13 }

		
--   1.3.6.1.4.1.231.7.1.2.2.1.12.1.2.7.15.14
		shehdsl2ShdslSpanConfProfileControlPowerFeeding OBJECT-TYPE
			SYNTAX Shehdsl2ShdslSpanConfPowerFeedingType
			MAX-ACCESS read-write
			STATUS current
			DESCRIPTION
				"Look at table."
			::= { shehdsl2ShdslSpanConfProfileControl 14 }

		
--   1.3.6.1.4.1.231.7.1.2.2.1.12.1.2.7.15.15
		shehdsl2ShdslSpanConfProfileControlCurrCondTargetMarginDown OBJECT-TYPE
			SYNTAX Integer32 (-10..21)
			UNITS "dB"
			MAX-ACCESS read-write
			STATUS current
			DESCRIPTION
				"Look at table."
			::= { shehdsl2ShdslSpanConfProfileControl 15 }

		
--   1.3.6.1.4.1.231.7.1.2.2.1.12.1.2.7.15.16
		shehdsl2ShdslSpanConfProfileControlWorstCaseTargetMarginDown OBJECT-TYPE
			SYNTAX Integer32 (-10..21)
			UNITS "dB"
			MAX-ACCESS read-write
			STATUS current
			DESCRIPTION
				"Look at table."
			::= { shehdsl2ShdslSpanConfProfileControl 16 }

		
--   1.3.6.1.4.1.231.7.1.2.2.1.12.1.2.7.15.17
		shehdsl2ShdslSpanConfProfileControlCurrCondTargetMarginUp OBJECT-TYPE
			SYNTAX Integer32 (-10..21)
			UNITS "dB"
			MAX-ACCESS read-write
			STATUS current
			DESCRIPTION
				"Look at table."
			::= { shehdsl2ShdslSpanConfProfileControl 17 }

		
--   1.3.6.1.4.1.231.7.1.2.2.1.12.1.2.7.15.18
		shehdsl2ShdslSpanConfProfileControlWorstCaseTargetMarginUp OBJECT-TYPE
			SYNTAX Integer32 (-10..21)
			UNITS "dB"
			MAX-ACCESS read-write
			STATUS current
			DESCRIPTION
				"Look at table."
			::= { shehdsl2ShdslSpanConfProfileControl 18 }

		
--   1.3.6.1.4.1.231.7.1.2.2.1.12.1.2.7.15.19
		shehdsl2ShdslSpanConfProfileControlUsedTargetMargins OBJECT-TYPE
			SYNTAX Shehdsl2ShdslSpanConfUsedTargetMarginsType
			MAX-ACCESS read-write
			STATUS current
			DESCRIPTION
				"Look at table."
			::= { shehdsl2ShdslSpanConfProfileControl 19 }

		
--   1.3.6.1.4.1.231.7.1.2.2.1.12.1.2.7.15.20
		shehdsl2ShdslSpanConfProfileControlReferenceClock OBJECT-TYPE
			SYNTAX SheHdsl2ShdslClockReferenceType
			MAX-ACCESS read-write
			STATUS current
			DESCRIPTION
				"Look at table.
				Note:
				Interfaces of type sdsl (96) support only value localClk(1).
				Interfaces of type shdsl (169) support also the mode networkClk(2)."
			::= { shehdsl2ShdslSpanConfProfileControl 20 }

		
--   1.3.6.1.4.1.231.7.1.2.2.1.12.1.2.7.15.21
		shehdsl2ShdslSpanConfProfileControlLineProbeEnable OBJECT-TYPE
			SYNTAX Shehdsl2ShdslSpanConfLineProbeEnableType
			MAX-ACCESS read-write
			STATUS current
			DESCRIPTION
				"Look at table."
			::= { shehdsl2ShdslSpanConfProfileControl 21 }

		
--   1.3.6.1.4.1.231.7.1.2.2.1.12.1.2.7.15.22
		shehdsl2ShdslSpanConfProfileControlPAMConstellation OBJECT-TYPE
			SYNTAX SheShdslPAMModeType
			MAX-ACCESS read-write
			STATUS current
			DESCRIPTION
				"Look at table.
				
				This is propietary extension for interfaces of type shdsl (169) only."
			::= { shehdsl2ShdslSpanConfProfileControl 22 }

		
--   1.3.6.1.4.1.231.7.1.2.2.1.12.1.2.7.15.24
		shehdsl2ShdslSpanConfProfileControlTCLayerSupported OBJECT-TYPE
			SYNTAX SheHdsl2ShdslTCLayerType
			MAX-ACCESS read-write
			STATUS current
			DESCRIPTION
				"Look at table.
				
				This is propietary extension for interfaces of type shdsl (169) only."
			::= { shehdsl2ShdslSpanConfProfileControl 23 }

		
--   1.3.6.1.4.1.231.7.1.2.2.1.12.1.2.7.16
		shehdsl2ShdslEndpointAlarmConfProfileTable OBJECT-TYPE
			SYNTAX SEQUENCE OF Shehdsl2ShdslEndpointAlarmConfProfileEntry
			MAX-ACCESS not-accessible
			STATUS current
			DESCRIPTION
				"This table supports definitions of alarm configuration
				profiles for HDSL2/SHDSL segment endpoints.  This table
				MUST be maintained in a persistent manner."
			::= { shehdsl2ShdslMibObjects 16 }

		
--   1.3.6.1.4.1.231.7.1.2.2.1.12.1.2.7.16.1
		shehdsl2ShdslEndpointAlarmConfProfileEntry OBJECT-TYPE
			SYNTAX Shehdsl2ShdslEndpointAlarmConfProfileEntry
			MAX-ACCESS not-accessible
			STATUS current
			DESCRIPTION
				"Each entry corresponds to a single alarm configuration profile.
				Each profile contains a set of parameters for setting alarm
				thresholds for various performance attributes monitored at
				HDSL2/SHDSL segment endpoints.  Profiles may be created/deleted
				using the row creation/deletion mechanism via
				hdsl2ShdslEndpointAlarmConfProfileRowStatus.  If an active
				entry is referenced in either hdsl2ShdslSpanConfAlarmProfile
				or hdsl2ShdslEndpointAlarmConfProfile, the entry MUST remain
				active until all references are removed."
			INDEX { shehdsl2ShdslEndpointAlarmConfProfileIndex }
			::= { shehdsl2ShdslEndpointAlarmConfProfileTable 1 }

		
		Shehdsl2ShdslEndpointAlarmConfProfileEntry ::=
			SEQUENCE { 
				shehdsl2ShdslEndpointAlarmConfProfileIndex
					Integer32,
				shehdsl2ShdslEndpointAlarmConfProfileName
					SnmpAdminString,
				shehdsl2ShdslEndpointThreshLoopAttenuation
					Integer32,
				shehdsl2ShdslEndpointThreshSNRMargin
					Integer32,
				shehdsl2ShdslEndpointThreshES
					SheHdsl2ShdslPerfIntervalThreshold,
				shehdsl2ShdslEndpointThreshSES
					SheHdsl2ShdslPerfIntervalThreshold,
				shehdsl2ShdslEndpointThreshCRCanomalies
					Integer32,
				shehdsl2ShdslEndpointThreshLOSWS
					SheHdsl2ShdslPerfIntervalThreshold,
				shehdsl2ShdslEndpointThreshUAS
					SheHdsl2ShdslPerfIntervalThreshold
			 }

--   1.3.6.1.4.1.231.7.1.2.2.1.12.1.2.7.16.1.1
		shehdsl2ShdslEndpointAlarmConfProfileIndex OBJECT-TYPE
			SYNTAX Integer32 (1..64)
			MAX-ACCESS read-only
			STATUS current
			DESCRIPTION
				"A free running index for this table."
			::= { shehdsl2ShdslEndpointAlarmConfProfileEntry 1 }

		
--   1.3.6.1.4.1.231.7.1.2.2.1.12.1.2.7.16.1.2
		shehdsl2ShdslEndpointAlarmConfProfileName OBJECT-TYPE
			SYNTAX SnmpAdminString (SIZE (1..32))
			MAX-ACCESS read-only
			STATUS current
			DESCRIPTION
				"This object is the unique index associated with this profile.
				
				This characters are not allowed:  space : ?"
			::= { shehdsl2ShdslEndpointAlarmConfProfileEntry 2 }

		
--   1.3.6.1.4.1.231.7.1.2.2.1.12.1.2.7.16.1.3
		shehdsl2ShdslEndpointThreshLoopAttenuation OBJECT-TYPE
			SYNTAX Integer32 (-127..128)
			UNITS "dB"
			MAX-ACCESS read-only
			STATUS current
			DESCRIPTION
				"This object configures the loop attenuation alarm threshold.
				When the current value of hdsl2ShdslEndpointCurrAtn reaches
				or exceeds this threshold, a hdsl2ShdslLoopAttenCrossing
				MAY be generated."
			DEFVAL { 0 }
			::= { shehdsl2ShdslEndpointAlarmConfProfileEntry 3 }

		
--   1.3.6.1.4.1.231.7.1.2.2.1.12.1.2.7.16.1.4
		shehdsl2ShdslEndpointThreshSNRMargin OBJECT-TYPE
			SYNTAX Integer32 (-127..128)
			UNITS "dB"
			MAX-ACCESS read-only
			STATUS current
			DESCRIPTION
				"This object configures the SNR margin alarm threshold.
				When the current value of hdsl2ShdslEndpointCurrSnrMgn
				reaches or drops below this threshold, a
				hdsl2ShdslSNRMarginCrossing MAY be generated."
			DEFVAL { 0 }
			::= { shehdsl2ShdslEndpointAlarmConfProfileEntry 4 }

		
--   1.3.6.1.4.1.231.7.1.2.2.1.12.1.2.7.16.1.5
		shehdsl2ShdslEndpointThreshES OBJECT-TYPE
			SYNTAX SheHdsl2ShdslPerfIntervalThreshold
			UNITS "seconds"
			MAX-ACCESS read-only
			STATUS current
			DESCRIPTION
				"This object configures the threshold for the number of
				errored seconds (ES) within any given 15-minute performance
				data collection interval.  If the value of errored seconds
				in a particular 15-minute collection interval reaches/
				exceeds this value, a hdsl2ShdslPerfESThresh MAY be
				generated.  At most one notification will be sent per
				interval per endpoint."
			DEFVAL { 0 }
			::= { shehdsl2ShdslEndpointAlarmConfProfileEntry 5 }

		
--   1.3.6.1.4.1.231.7.1.2.2.1.12.1.2.7.16.1.6
		shehdsl2ShdslEndpointThreshSES OBJECT-TYPE
			SYNTAX SheHdsl2ShdslPerfIntervalThreshold
			UNITS "seconds"
			MAX-ACCESS read-only
			STATUS current
			DESCRIPTION
				"This object configures the threshold for the number of
				severely errored seconds (SES) within any given 15-minute
				performance data collection interval.  If the value of
				severely errored seconds in a particular 15-minute collection
				interval reaches/exceeds this value, a hdsl2ShdslPerfSESThresh
				MAY be generated.  At most one notification will be sent per
				interval per endpoint."
			::= { shehdsl2ShdslEndpointAlarmConfProfileEntry 6 }

		
--   1.3.6.1.4.1.231.7.1.2.2.1.12.1.2.7.16.1.7
		shehdsl2ShdslEndpointThreshCRCanomalies OBJECT-TYPE
			SYNTAX Integer32
			UNITS "detected CRC Anomalies"
			MAX-ACCESS read-only
			STATUS current
			DESCRIPTION
				"This object configures the threshold for the number of
				CRC anomalies within any given 15-minute performance data
				collection interval.  If the value of CRC anomalies in a
				particular 15-minute collection interval reaches/exceeds
				this value, a hdsl2ShdslPerfCRCanomaliesThresh MAY be
				generated.  At most one notification will be sent per
				interval per endpoint."
			DEFVAL { 0 }
			::= { shehdsl2ShdslEndpointAlarmConfProfileEntry 7 }

		
--   1.3.6.1.4.1.231.7.1.2.2.1.12.1.2.7.16.1.8
		shehdsl2ShdslEndpointThreshLOSWS OBJECT-TYPE
			SYNTAX SheHdsl2ShdslPerfIntervalThreshold
			UNITS "seconds"
			MAX-ACCESS read-only
			STATUS current
			DESCRIPTION
				"This object configures the threshold for the number of
				Loss of Sync Word (LOSW) Seconds within any given 15-minute
				performance data collection interval.  If the value of LOSW
				in a particular 15-minute collection interval reaches/exceeds
				this value, a hdsl2ShdslPerfLOSWSThresh MAY be generated.
				At most one notification will be sent per interval per
				endpoint."
			::= { shehdsl2ShdslEndpointAlarmConfProfileEntry 8 }

		
--   1.3.6.1.4.1.231.7.1.2.2.1.12.1.2.7.16.1.9
		shehdsl2ShdslEndpointThreshUAS OBJECT-TYPE
			SYNTAX SheHdsl2ShdslPerfIntervalThreshold
			UNITS "seconds"
			MAX-ACCESS read-only
			STATUS current
			DESCRIPTION
				"This object configures the threshold for the number of
				unavailable seconds (UAS) within any given 15-minute
				performance data collection interval.  If the value of UAS
				in a particular 15-minute collection interval reaches/exceeds
				this value, a hdsl2ShdslPerfUASThresh MAY be generated.
				At most one notification will be sent per interval per
				endpoint."
			::= { shehdsl2ShdslEndpointAlarmConfProfileEntry 9 }

		
--   1.3.6.1.4.1.231.7.1.2.2.1.12.1.2.7.17
		shehdsl2ShdslEndpointAlarmConfProfileControl OBJECT IDENTIFIER ::= { shehdsl2ShdslMibObjects 17 }

		
--   1.3.6.1.4.1.231.7.1.2.2.1.12.1.2.7.17.1
		shehdsl2ShdslEndpointAlarmConfProfileControlRequest OBJECT-TYPE
			SYNTAX SheShdslControlRequestType
			MAX-ACCESS read-write
			STATUS current
			DESCRIPTION
				"createshehdsl2ShdslEndpointAlarmConfProfile
				modifyshehdsl2ShdslEndpointAlarmConfProfile
				deleteshehdsl2ShdslEndpointAlarmConfProfile
				"
			::= { shehdsl2ShdslEndpointAlarmConfProfileControl 1 }

		
--   1.3.6.1.4.1.231.7.1.2.2.1.12.1.2.7.17.2
		shehdsl2ShdslEndpointAlarmConfProfileControlIndex OBJECT-TYPE
			SYNTAX Unsigned32 (1..64)
			MAX-ACCESS read-write
			STATUS current
			DESCRIPTION
				"Key for the modified or deleted entry. NE will choose this number during create. "
			::= { shehdsl2ShdslEndpointAlarmConfProfileControl 2 }

		
--   1.3.6.1.4.1.231.7.1.2.2.1.12.1.2.7.17.3
		shehdsl2ShdslEndpointAlarmConfProfileControlStatus OBJECT-TYPE
			SYNTAX SheControlStatusType
			MAX-ACCESS read-only
			STATUS current
			DESCRIPTION
				"The status of a user command. 
				"
			::= { shehdsl2ShdslEndpointAlarmConfProfileControl 3 }

		
--   1.3.6.1.4.1.231.7.1.2.2.1.12.1.2.7.17.4
		shehdsl2ShdslEndpointAlarmConfProfileControlTimer OBJECT-TYPE
			SYNTAX Gauge32
			MAX-ACCESS read-only
			STATUS current
			DESCRIPTION
				"The maximum wait time for the manager for a long running user command. 
				"
			::= { shehdsl2ShdslEndpointAlarmConfProfileControl 4 }

		
--   1.3.6.1.4.1.231.7.1.2.2.1.12.1.2.7.17.5
		shehdsl2ShdslEndpointAlarmConfProfileControlReqResult OBJECT-TYPE
			SYNTAX SheShdslControlRequestResultType
			MAX-ACCESS read-only
			STATUS current
			DESCRIPTION
				"The result of the last user command."
			::= { shehdsl2ShdslEndpointAlarmConfProfileControl 5 }

		
--   1.3.6.1.4.1.231.7.1.2.2.1.12.1.2.7.17.6
		shehdsl2ShdslEndpointAlarmConfProfileControlTimeStamp OBJECT-TYPE
			SYNTAX Unsigned32
			UNITS "sec"
			MAX-ACCESS read-only
			STATUS current
			DESCRIPTION
				"The time stamp of the last command (end of command)."
			::= { shehdsl2ShdslEndpointAlarmConfProfileControl 6 }

		
--   1.3.6.1.4.1.231.7.1.2.2.1.12.1.2.7.17.7
		shehdsl2ShdslEndpointAlarmConfProfileControlProfileName OBJECT-TYPE
			SYNTAX SnmpAdminString (SIZE (0..32))
			MAX-ACCESS read-write
			STATUS current
			DESCRIPTION
				"Name for new profile."
			::= { shehdsl2ShdslEndpointAlarmConfProfileControl 7 }

		
--   1.3.6.1.4.1.231.7.1.2.2.1.12.1.2.7.17.8
		shehdsl2ShdslEndpointConfProfileControlThreshLoopAttenuation OBJECT-TYPE
			SYNTAX Integer32 (-127..128)
			UNITS "dB"
			MAX-ACCESS read-write
			STATUS current
			DESCRIPTION
				"Look at table."
			::= { shehdsl2ShdslEndpointAlarmConfProfileControl 8 }

		
--   1.3.6.1.4.1.231.7.1.2.2.1.12.1.2.7.17.9
		shehdsl2ShdslEndpointConfProfileControlThreshSNRMargin OBJECT-TYPE
			SYNTAX Integer32 (-127..128)
			UNITS "dB"
			MAX-ACCESS read-write
			STATUS current
			DESCRIPTION
				"Look at table."
			::= { shehdsl2ShdslEndpointAlarmConfProfileControl 9 }

		
--   1.3.6.1.4.1.231.7.1.2.2.1.12.1.2.7.17.10
		shehdsl2ShdslEndpointConfProfileControlThreshES OBJECT-TYPE
			SYNTAX SheHdsl2ShdslPerfIntervalThreshold
			UNITS "seconds"
			MAX-ACCESS read-write
			STATUS current
			DESCRIPTION
				"Look at table."
			::= { shehdsl2ShdslEndpointAlarmConfProfileControl 10 }

		
--   1.3.6.1.4.1.231.7.1.2.2.1.12.1.2.7.17.11
		shehdsl2ShdslEndpointConfProfileControlThreshSES OBJECT-TYPE
			SYNTAX SheHdsl2ShdslPerfIntervalThreshold
			UNITS "seconds"
			MAX-ACCESS read-write
			STATUS current
			DESCRIPTION
				"Look at table."
			::= { shehdsl2ShdslEndpointAlarmConfProfileControl 11 }

		
--   1.3.6.1.4.1.231.7.1.2.2.1.12.1.2.7.17.12
		shehdsl2ShdslEndpointConfProfileControlThreshCRCanomalies OBJECT-TYPE
			SYNTAX Integer32
			UNITS "detected CRC Anomalies"
			MAX-ACCESS read-write
			STATUS current
			DESCRIPTION
				"Look at table."
			::= { shehdsl2ShdslEndpointAlarmConfProfileControl 12 }

		
--   1.3.6.1.4.1.231.7.1.2.2.1.12.1.2.7.17.13
		shehdsl2ShdslEndpointConfProfileControlThreshLOSWS OBJECT-TYPE
			SYNTAX SheHdsl2ShdslPerfIntervalThreshold
			UNITS "seconds"
			MAX-ACCESS read-write
			STATUS current
			DESCRIPTION
				"Look at table."
			::= { shehdsl2ShdslEndpointAlarmConfProfileControl 13 }

		
--   1.3.6.1.4.1.231.7.1.2.2.1.12.1.2.7.17.14
		shehdsl2ShdslEndpointConfProfileControlThreshUAS OBJECT-TYPE
			SYNTAX SheHdsl2ShdslPerfIntervalThreshold
			UNITS "seconds"
			MAX-ACCESS read-write
			STATUS current
			DESCRIPTION
				"Look at table."
			::= { shehdsl2ShdslEndpointAlarmConfProfileControl 14 }

		
--   1.3.6.1.4.1.231.7.1.2.2.1.12.1.2.8
		shehdsl2ShdslNotifications OBJECT IDENTIFIER ::= { sheShdslMIBObjects 8 }

		
--   1.3.6.1.4.1.231.7.1.2.2.1.12.1.2.8.1
		shehdsl2ShdslLoopAttenCrossing NOTIFICATION-TYPE
			OBJECTS { shehdsl2ShdslEndpointCurrAtn, shehdsl2ShdslEndpointThreshLoopAttenuation }
			STATUS current
			DESCRIPTION 
				"This notification indicates that the loop attenuation
				threshold (as per the hdsl2ShdslEndpointThreshLoopAttenuation
				value) has been reached/exceeded for the HDSL2/SHDSL segment
				endpoint."
			::= { shehdsl2ShdslNotifications 1 }

		
--   1.3.6.1.4.1.231.7.1.2.2.1.12.1.2.8.2
		shehdsl2ShdslSNRMarginCrossing NOTIFICATION-TYPE
			OBJECTS { shehdsl2ShdslEndpointCurrSnrMgn, shehdsl2ShdslEndpointThreshSNRMargin }
			STATUS current
			DESCRIPTION 
				"This notification indicates that the SNR margin threshold (as
				per the hdsl2ShdslEndpointThreshSNRMargin value) has been
				reached/exceeded for the HDSL2/SHDSL segment endpoint."
			::= { shehdsl2ShdslNotifications 2 }

		
--   1.3.6.1.4.1.231.7.1.2.2.1.12.1.2.8.3
		shehdsl2ShdslPerfESThresh NOTIFICATION-TYPE
			OBJECTS { shehdsl2ShdslEndpointCurr15MinES, shehdsl2ShdslEndpointThreshES }
			STATUS current
			DESCRIPTION 
				"This notification indicates that the errored seconds threshold
				(as per the hdsl2ShdslEndpointThreshES value) has been reached/
				exceeded for the HDSL2/SHDSL segment endpoint."
			::= { shehdsl2ShdslNotifications 3 }

		
--   1.3.6.1.4.1.231.7.1.2.2.1.12.1.2.8.4
		shehdsl2ShdslPerfSESThresh NOTIFICATION-TYPE
			OBJECTS { shehdsl2ShdslEndpointCurr15MinSES, shehdsl2ShdslEndpointThreshSES }
			STATUS current
			DESCRIPTION 
				"This notification indicates that the severely errored seconds
				threshold (as per the hdsl2ShdslEndpointThreshSES value) has
				been reached/exceeded for the HDSL2/SHDSL Segment Endpoint."
			::= { shehdsl2ShdslNotifications 4 }

		
--   1.3.6.1.4.1.231.7.1.2.2.1.12.1.2.8.5
		shehdsl2ShdslPerfCRCanomaliesThresh NOTIFICATION-TYPE
			OBJECTS { shehdsl2ShdslEndpointCurr15MinCRCanomalies, shehdsl2ShdslEndpointThreshCRCanomalies }
			STATUS current
			DESCRIPTION 
				"This notification indicates that the CRC anomalies threshold
				(as per the hdsl2ShdslEndpointThreshCRCanomalies value) has
				been reached/exceeded for the HDSL2/SHDSL Segment Endpoint."
			::= { shehdsl2ShdslNotifications 5 }

		
--   1.3.6.1.4.1.231.7.1.2.2.1.12.1.2.8.6
		shehdsl2ShdslPerfLOSWSThresh NOTIFICATION-TYPE
			OBJECTS { shehdsl2ShdslEndpointCurr15MinLOSWS, shehdsl2ShdslEndpointThreshLOSWS }
			STATUS current
			DESCRIPTION 
				"This notification indicates that the LOSW seconds threshold
				(as per the hdsl2ShdslEndpointThreshLOSWS value) has been
				reached/exceeded for the HDSL2/SHDSL segment endpoint."
			::= { shehdsl2ShdslNotifications 6 }

		
--   1.3.6.1.4.1.231.7.1.2.2.1.12.1.2.8.7
		shehdsl2ShdslPerfUASThresh NOTIFICATION-TYPE
			OBJECTS { shehdsl2ShdslEndpointCurr15MinUAS, shehdsl2ShdslEndpointThreshUAS }
			STATUS current
			DESCRIPTION 
				"This notification indicates that the unavailable seconds
				threshold (as per the hdsl2ShdslEndpointThreshUAS value) has
				been reached/exceeded for the HDSL2/SHDSL segment endpoint."
			::= { shehdsl2ShdslNotifications 7 }

		
--   1.3.6.1.4.1.231.7.1.2.2.1.12.1.2.8.8
		shehdsl2ShdslSpanInvalidNumRepeaters NOTIFICATION-TYPE
			OBJECTS { sheAlarmTimeAndDate, sheAlarmReportingSource, sheAlarmReportingSourceType, sheAlarmSeverity }
			STATUS current
			DESCRIPTION 
				"This notification indicates that a mismatch has been detected
				between the number of repeater/regenerator units configured
				for a HDSL2/SHDSL line via the hdsl2ShdslSpanConfNumRepeaters
				object and the actual number of repeater/regenerator units
				discovered via the EOC."
			::= { shehdsl2ShdslNotifications 8 }

		
--   1.3.6.1.4.1.231.7.1.2.2.1.12.1.2.8.9
		shehdsl2ShdslLoopbackFailure NOTIFICATION-TYPE
			OBJECTS { shehdsl2ShdslMaintLoopbackConfig }
			STATUS current
			DESCRIPTION 
				"This notification indicates that an endpoint maintenance
				loopback command failed for an HDSL2/SHDSL segment."
			::= { shehdsl2ShdslNotifications 9 }

		
--   1.3.6.1.4.1.231.7.1.2.2.1.12.1.2.8.10
		shehdsl2ShdslpowerBackoff NOTIFICATION-TYPE
			OBJECTS { shehdsl2ShdslEndpointCurrStatus }
			STATUS current
			DESCRIPTION 
				"This notification indicates that the bit setting for
				powerBackoff in the hdsl2ShdslEndpointCurrStatus object for
				this endpoint has changed."
			::= { shehdsl2ShdslNotifications 10 }

		
--   1.3.6.1.4.1.231.7.1.2.2.1.12.1.2.8.11
		shehdsl2ShdsldeviceFault NOTIFICATION-TYPE
			OBJECTS { shehdsl2ShdslEndpointCurrStatus }
			STATUS current
			DESCRIPTION 
				"This notification indicates that the bit setting for
				deviceFault in the hdsl2ShdslEndpointCurrStatus object for
				this endpoint has changed."
			::= { shehdsl2ShdslNotifications 11 }

		
--   1.3.6.1.4.1.231.7.1.2.2.1.12.1.2.8.12
		shehdsl2ShdsldcContinuityFault NOTIFICATION-TYPE
			OBJECTS { shehdsl2ShdslEndpointCurrStatus }
			STATUS current
			DESCRIPTION 
				"This notification indicates that the bit setting for
				dcContinuityFault in the hdsl2ShdslEndpointCurrStatus object
				for this endpoint has changed."
			::= { shehdsl2ShdslNotifications 12 }

		
--   1.3.6.1.4.1.231.7.1.2.2.1.12.1.2.8.13
		shehdsl2ShdslconfigInitFailure NOTIFICATION-TYPE
			OBJECTS { shehdsl2ShdslEndpointCurrStatus }
			STATUS current
			DESCRIPTION 
				"This notification indicates that the bit setting for
				configInitFailure in the hdsl2ShdslEndpointCurrStatus object
				for this endpoint has changed."
			::= { shehdsl2ShdslNotifications 13 }

		
--   1.3.6.1.4.1.231.7.1.2.2.1.12.1.2.8.14
		shehdsl2ShdslprotocolInitFailure NOTIFICATION-TYPE
			OBJECTS { shehdsl2ShdslEndpointCurrStatus }
			STATUS current
			DESCRIPTION 
				"This notification indicates that the bit setting for
				protocolInitFailure in the hdsl2ShdslEndpointCurrStatus
				object for this endpoint has changed."
			::= { shehdsl2ShdslNotifications 14 }

		
--   1.3.6.1.4.1.231.7.1.2.2.1.12.1.2.8.15
		shehdsl2ShdslnoNeighborPresent NOTIFICATION-TYPE
			OBJECTS { shehdsl2ShdslEndpointCurrStatus }
			STATUS current
			DESCRIPTION 
				"This notification indicates that the bit setting for
				noNeighborPresent in the hdsl2ShdslEndpointCurrStatus object
				for this endpoint has changed."
			::= { shehdsl2ShdslNotifications 15 }

		
--   1.3.6.1.4.1.231.7.1.2.2.1.12.1.2.8.16
		shehdsl2ShdslLocalPowerLoss NOTIFICATION-TYPE
			OBJECTS { sheAlarmTimeAndDate, sheAlarmReportingSource, sheAlarmReportingSourceType, sheAlarmSeverity }
			STATUS current
			DESCRIPTION 
				"This notification indicates impending unit failure due to
				loss of local power (last gasp)."
			::= { shehdsl2ShdslNotifications 16 }

		
--   1.3.6.1.4.1.231.7.1.2.2.1.12.1.2.8.17
		shehdsl2ShdslAtucPerfLol NOTIFICATION-TYPE
			OBJECTS { sheAlarmTimeAndDate, sheAlarmReportingSource, sheAlarmReportingSourceType, sheAlarmSeverity }
			STATUS current
			DESCRIPTION 
				"This alarm informs the link between the line card and modem is disconnected for unidentied reason, not dying gasp. "
			::= { shehdsl2ShdslNotifications 17 }

		
--   1.3.6.1.4.1.231.7.1.2.2.1.12.1.2.8.18
		shehdsl2ShdslAtucPerfLpr NOTIFICATION-TYPE
			OBJECTS { sheAlarmTimeAndDate, sheAlarmReportingSource, sheAlarmReportingSourceType, sheAlarmSeverity }
			STATUS current
			DESCRIPTION 
				"This alarm informs the link between the line card and modem is disconnected for dying gasp. "
			::= { shehdsl2ShdslNotifications 18 }

		
--   1.3.6.1.4.1.231.7.1.2.2.1.12.1.2.8.19
		shehdsl2ShdslAtucPerfLos NOTIFICATION-TYPE
			OBJECTS { sheAlarmTimeAndDate, sheAlarmReportingSource, sheAlarmReportingSourceType, sheAlarmSeverity }
			STATUS current
			DESCRIPTION 
				"This alarm informs the link between the line card and modem is disconnected for loss of signal."
			::= { shehdsl2ShdslNotifications 19 }

		
--   1.3.6.1.4.1.231.7.1.2.2.1.12.1.2.8.20
		shehdsl2ShdslAtucPerfLof NOTIFICATION-TYPE
			OBJECTS { sheAlarmTimeAndDate, sheAlarmReportingSource, sheAlarmReportingSourceType, sheAlarmSeverity }
			STATUS current
			DESCRIPTION 
				"This alarm informs the link between the line card and modem is disconnected for loss of frame."
			::= { shehdsl2ShdslNotifications 20 }

		
--   1.3.6.1.4.1.231.7.1.2.2.1.12.1.2.9
		sheShdslConfigurationNotifications OBJECT IDENTIFIER ::= { sheShdslMIBObjects 9 }

		
--   1.3.6.1.4.1.231.7.1.2.2.1.12.1.2.9.1
		sheShdslLineParamsEntryModified NOTIFICATION-TYPE
			OBJECTS { sheShdslLineParamsControlIndex, sheShdslLineParamsControlTimeStamp, sheShdslLineParamsControlReqResult, sheShdslLineParamsControlPAMMode }
			STATUS current
			DESCRIPTION 
				"Notification for a complete LineParamsEntry-Modify-Command."
			::= { sheShdslConfigurationNotifications 1 }

		
--   1.3.6.1.4.1.231.7.1.2.2.1.12.1.2.9.2
		shehdsl2ShdslSpanConfEntryModified NOTIFICATION-TYPE
			OBJECTS { shehdsl2ShdslSpanConfControlIndex, shehdsl2ShdslSpanConfControlTimeStamp, shehdsl2ShdslSpanConfControlNumRepeaters, shehdsl2ShdslSpanConfControlProfile }
			STATUS current
			DESCRIPTION 
				"Notification for a complete SpanConfEntry-Modify-Command."
			::= { sheShdslConfigurationNotifications 2 }

		
--   1.3.6.1.4.1.231.7.1.2.2.1.12.1.2.9.3
		shehdsl2ShdslSpanConfEntryAlarmProfileModified NOTIFICATION-TYPE
			OBJECTS { shehdsl2ShdslSpanConfControlIndex, shehdsl2ShdslSpanConfControlTimeStamp, shehdsl2ShdslSpanConfControlAlarmProfile }
			STATUS current
			DESCRIPTION 
				"Notification for a complete SpanConfEntry-Modify-Command."
			::= { sheShdslConfigurationNotifications 3 }

		
--   1.3.6.1.4.1.231.7.1.2.2.1.12.1.2.9.4
		shehdsl2ShdslEndpointConfEntryModified NOTIFICATION-TYPE
			OBJECTS { shehdsl2ShdslEndpointConfControlIndex, shehdsl2ShdslEndpointConfControlTimeStamp, shehdsl2ShdslEndpointConfControlInvIndex, shehdsl2ShdslEndpointConfControlSide, shehdsl2ShdslEndpointConfControlWirePair, 
				shehdsl2ShdslEndpointConfControlAlarmProfile }
			STATUS current
			DESCRIPTION 
				"Notification for a complete EndPointConfEntry-Modify-Command."
			::= { sheShdslConfigurationNotifications 4 }

		
--   1.3.6.1.4.1.231.7.1.2.2.1.12.1.2.9.5
		shehdsl2ShdslEndpointMaintEntryModified NOTIFICATION-TYPE
			OBJECTS { shehdsl2ShdslEndpointMaintControlIndex, shehdsl2ShdslEndpointMaintControlTimeStamp, shehdsl2ShdslEndpointMaintControlInvIndex, shehdsl2ShdslEndpointMaintControlSide, shehdsl2ShdslEndpointMaintControlLoopbackConfig, 
				shehdsl2ShdslEndpointMaintControlPowerBackOff, shehdsl2ShdslEndpointMaintControlSoftRestart }
			STATUS current
			DESCRIPTION 
				"Notification for a complete EndPointMaintEntry-Modify-Command."
			::= { sheShdslConfigurationNotifications 5 }

		
--   1.3.6.1.4.1.231.7.1.2.2.1.12.1.2.9.6
		shehdsl2ShdslUnitMaintEntryModified NOTIFICATION-TYPE
			OBJECTS { shehdsl2ShdslUnitMaintControlIndex, shehdsl2ShdslUnitMaintControlTimeStamp, shehdsl2ShdslUnitMaintControlInvIndex, shehdsl2ShdslUnitMaintControlLoopbackTimeout }
			STATUS current
			DESCRIPTION 
				"Notification for a complete UnitMaintEntry-Modify-Command."
			::= { sheShdslConfigurationNotifications 6 }

		
--   1.3.6.1.4.1.231.7.1.2.2.1.12.1.2.9.7
		shehdsl2ShdslSpanConfProfileCreated NOTIFICATION-TYPE
			OBJECTS { shehdsl2ShdslSpanConfProfileControlIndex, shehdsl2ShdslSpanConfProfileControlTimeStamp, shehdsl2ShdslSpanConfProfileControlProfileName, shehdsl2ShdslSpanConfProfileControlWireInterface, shehdsl2ShdslSpanConfProfileControlMinLineRate, 
				shehdsl2ShdslSpanConfProfileControlMaxLineRate, shehdsl2ShdslSpanConfProfileControlPSD, shehdsl2ShdslSpanConfProfileControlTransmissionMode, shehdsl2ShdslSpanConfProfileControlRemoteEnabled, shehdsl2ShdslSpanConfProfileControlPowerFeeding, 
				shehdsl2ShdslSpanConfProfileControlCurrCondTargetMarginDown, shehdsl2ShdslSpanConfProfileControlWorstCaseTargetMarginDown, shehdsl2ShdslSpanConfProfileControlCurrCondTargetMarginUp, shehdsl2ShdslSpanConfProfileControlWorstCaseTargetMarginUp, shehdsl2ShdslSpanConfProfileControlUsedTargetMargins, 
				shehdsl2ShdslSpanConfProfileControlReferenceClock, shehdsl2ShdslSpanConfProfileControlLineProbeEnable, shehdsl2ShdslSpanConfProfileControlPAMConstellation, shehdsl2ShdslSpanConfProfileControlTCLayerSupported }
			STATUS current
			DESCRIPTION 
				"Notification for a complete SpanConfProfileEntry-Create-Command."
			::= { sheShdslConfigurationNotifications 7 }

		
--   1.3.6.1.4.1.231.7.1.2.2.1.12.1.2.9.8
		shehdsl2ShdslSpanConfProfileModified NOTIFICATION-TYPE
			OBJECTS { shehdsl2ShdslSpanConfProfileControlIndex, shehdsl2ShdslSpanConfProfileControlTimeStamp, shehdsl2ShdslSpanConfProfileControlProfileName, shehdsl2ShdslSpanConfProfileControlWireInterface, shehdsl2ShdslSpanConfProfileControlMinLineRate, 
				shehdsl2ShdslSpanConfProfileControlMaxLineRate, shehdsl2ShdslSpanConfProfileControlPSD, shehdsl2ShdslSpanConfProfileControlTransmissionMode, shehdsl2ShdslSpanConfProfileControlRemoteEnabled, shehdsl2ShdslSpanConfProfileControlPowerFeeding, 
				shehdsl2ShdslSpanConfProfileControlCurrCondTargetMarginDown, shehdsl2ShdslSpanConfProfileControlWorstCaseTargetMarginDown, shehdsl2ShdslSpanConfProfileControlCurrCondTargetMarginUp, shehdsl2ShdslSpanConfProfileControlWorstCaseTargetMarginUp, shehdsl2ShdslSpanConfProfileControlUsedTargetMargins, 
				shehdsl2ShdslSpanConfProfileControlReferenceClock, shehdsl2ShdslSpanConfProfileControlLineProbeEnable, shehdsl2ShdslSpanConfProfileControlPAMConstellation, shehdsl2ShdslSpanConfProfileControlTCLayerSupported }
			STATUS current
			DESCRIPTION 
				"Notification for a complete SpanConfProfileEntry-Modify-Command."
			::= { sheShdslConfigurationNotifications 8 }

		
--   1.3.6.1.4.1.231.7.1.2.2.1.12.1.2.9.9
		shehdsl2ShdslSpanConfProfileDeleted NOTIFICATION-TYPE
			OBJECTS { shehdsl2ShdslSpanConfProfileControlIndex, shehdsl2ShdslSpanConfProfileControlTimeStamp }
			STATUS current
			DESCRIPTION 
				"Notification for a complete SpanConfProfileEntry-Delete-Command."
			::= { sheShdslConfigurationNotifications 9 }

		
--   1.3.6.1.4.1.231.7.1.2.2.1.12.1.2.9.10
		shehdsl2ShdslEndpointAlarmConfProfileCreated NOTIFICATION-TYPE
			OBJECTS { shehdsl2ShdslEndpointAlarmConfProfileControlIndex, shehdsl2ShdslEndpointAlarmConfProfileControlTimeStamp, shehdsl2ShdslEndpointAlarmConfProfileControlProfileName, shehdsl2ShdslEndpointConfProfileControlThreshLoopAttenuation, shehdsl2ShdslEndpointConfProfileControlThreshSNRMargin, 
				shehdsl2ShdslEndpointConfProfileControlThreshES, shehdsl2ShdslEndpointConfProfileControlThreshSES, shehdsl2ShdslEndpointConfProfileControlThreshCRCanomalies, shehdsl2ShdslEndpointConfProfileControlThreshLOSWS, shehdsl2ShdslEndpointConfProfileControlThreshUAS
				 }
			STATUS current
			DESCRIPTION 
				"Notification for a complete EndPointAlarmProfileEntry-Create-Command."
			::= { sheShdslConfigurationNotifications 10 }

		
--   1.3.6.1.4.1.231.7.1.2.2.1.12.1.2.9.11
		shehdsl2ShdslEndpointAlarmConfProfileModified NOTIFICATION-TYPE
			OBJECTS { shehdsl2ShdslEndpointAlarmConfProfileControlIndex, shehdsl2ShdslEndpointAlarmConfProfileControlTimeStamp, shehdsl2ShdslEndpointAlarmConfProfileControlProfileName, shehdsl2ShdslEndpointConfProfileControlThreshLoopAttenuation, shehdsl2ShdslEndpointConfProfileControlThreshSNRMargin, 
				shehdsl2ShdslEndpointConfProfileControlThreshES, shehdsl2ShdslEndpointConfProfileControlThreshSES, shehdsl2ShdslEndpointConfProfileControlThreshCRCanomalies, shehdsl2ShdslEndpointConfProfileControlThreshLOSWS, shehdsl2ShdslEndpointConfProfileControlThreshUAS
				 }
			STATUS current
			DESCRIPTION 
				"Notification for a complete EndPointAlarmProfileEntry-Modify-Command."
			::= { sheShdslConfigurationNotifications 11 }

		
--   1.3.6.1.4.1.231.7.1.2.2.1.12.1.2.9.12
		shehdsl2ShdslEndpointAlarmConfProfileDeleted NOTIFICATION-TYPE
			OBJECTS { shehdsl2ShdslEndpointAlarmConfProfileControlIndex, shehdsl2ShdslEndpointAlarmConfProfileControlTimeStamp }
			STATUS current
			DESCRIPTION 
				"Notification for a complete EndPointAlarmProfileEntry-Delete-Command."
			::= { sheShdslConfigurationNotifications 12 }

		
--   1.3.6.1.4.1.231.7.1.2.2.1.12.1.2.9.13
		shehdsl2ShdslSpanConfProfileReqResult NOTIFICATION-TYPE
			OBJECTS { shehdsl2ShdslSpanConfProfileControlIndex, shehdsl2ShdslSpanConfProfileControlStatus, shehdsl2ShdslSpanConfProfileControlReqResult, shehdsl2ShdslSpanConfProfileControlTimeStamp }
			STATUS current
			DESCRIPTION 
				"Trap for long running profile modification result."
			::= { sheShdslConfigurationNotifications 13 }

		
--   1.3.6.1.4.1.231.7.1.2.2.1.12.1.2.9.14
		shehdsl2ShdslEndpointAlarmConfProfileReqResult NOTIFICATION-TYPE
			OBJECTS { shehdsl2ShdslEndpointAlarmConfProfileControlIndex, shehdsl2ShdslEndpointAlarmConfProfileControlTimeStamp, shehdsl2ShdslEndpointAlarmConfProfileControlReqResult }
			STATUS current
			DESCRIPTION 
				"Trap for long running profile modification result."
			::= { sheShdslConfigurationNotifications 14 }

		
--   1.3.6.1.4.1.231.7.1.2.2.1.12.1.2.10
		sheShdslVccTpTable OBJECT-TYPE
			SYNTAX SEQUENCE OF SheShdslVccTpEntry
			MAX-ACCESS not-accessible
			STATUS current
			DESCRIPTION
				"The VccTp-Table."
			::= { sheShdslMIBObjects 10 }

		
--   1.3.6.1.4.1.231.7.1.2.2.1.12.1.2.10.1
		sheShdslVccTpEntry OBJECT-TYPE
			SYNTAX SheShdslVccTpEntry
			MAX-ACCESS not-accessible
			STATUS current
			DESCRIPTION
				"This table contains the VccTp-Configurations. There will be one
				entry for every shdsl-interface available per default. This default
				entry should never be deleted."
			INDEX { sheShdslVccTpIndex }
			::= { sheShdslVccTpTable 1 }

		
		SheShdslVccTpEntry ::=
			SEQUENCE { 
				sheShdslVccTpIndex
					Integer32,
				sheShdslVccTpSubLayerIndex
					InterfaceIndex,
				sheShdslVccTpNumber
					Integer32,
				sheShdslVccTpVpi
					Integer32,
				sheShdslVccTpVci
					Integer32,
				sheShdslVccTpOamLevel
					SheAtmOamLevelType,
				sheShdslVccTpLoopTest
					SheAtmOamLoopTestType,
				sheShdslVccTpLoopTestResult
					SheAtmOamLoopTestResultType,
				sheShdslVccTpLoopLocId
					OCTET STRING,
				sheShdslVccTpAlarmSeverityIndex
					Integer32
			 }

--   1.3.6.1.4.1.231.7.1.2.2.1.12.1.2.10.1.1
		sheShdslVccTpIndex OBJECT-TYPE
			SYNTAX Integer32 (1..65565)
			MAX-ACCESS read-only
			STATUS current
			DESCRIPTION
				"Index for that table. The index will follow this rule:
				VccTpIndex = (VccTpSubLayerIndex << 4) + VccTpNumber"
			::= { sheShdslVccTpEntry 1 }

		
--   1.3.6.1.4.1.231.7.1.2.2.1.12.1.2.10.1.2
		sheShdslVccTpSubLayerIndex OBJECT-TYPE
			SYNTAX InterfaceIndex
			MAX-ACCESS read-only
			STATUS current
			DESCRIPTION
				"ifIndex of the underlaying shdsl-interface."
			::= { sheShdslVccTpEntry 2 }

		
--   1.3.6.1.4.1.231.7.1.2.2.1.12.1.2.10.1.3
		sheShdslVccTpNumber OBJECT-TYPE
			SYNTAX Integer32 (1..8)
			MAX-ACCESS read-only
			STATUS current
			DESCRIPTION
				"This is the logical number of VccTP on the corresponding interface. Maximum value is 1."
			::= { sheShdslVccTpEntry 3 }

		
--   1.3.6.1.4.1.231.7.1.2.2.1.12.1.2.10.1.4
		sheShdslVccTpVpi OBJECT-TYPE
			SYNTAX Integer32 (0..255)
			MAX-ACCESS read-only
			STATUS current
			DESCRIPTION
				"The VPI - Value."
			DEFVAL { 0 }
			::= { sheShdslVccTpEntry 4 }

		
--   1.3.6.1.4.1.231.7.1.2.2.1.12.1.2.10.1.5
		sheShdslVccTpVci OBJECT-TYPE
			SYNTAX Integer32 (32..65535)
			MAX-ACCESS read-only
			STATUS current
			DESCRIPTION
				"The Vci - Value."
			DEFVAL { 32 }
			::= { sheShdslVccTpEntry 5 }

		
--   1.3.6.1.4.1.231.7.1.2.2.1.12.1.2.10.1.6
		sheShdslVccTpOamLevel OBJECT-TYPE
			SYNTAX SheAtmOamLevelType (4..5)
			MAX-ACCESS read-only
			STATUS current
			DESCRIPTION
				"The OAM level for loop test on VP/VC level.
				Valid:    f5 (for VC). "
			DEFVAL { 5 }
			::= { sheShdslVccTpEntry 6 }

		
--   1.3.6.1.4.1.231.7.1.2.2.1.12.1.2.10.1.7
		sheShdslVccTpLoopTest OBJECT-TYPE
			SYNTAX SheAtmOamLoopTestType
			MAX-ACCESS read-only
			STATUS current
			DESCRIPTION
				"The type of loop test .
				For EndToEnd loop test loop location ID is FF..FF."
			DEFVAL { 0 }
			::= { sheShdslVccTpEntry 7 }

		
--   1.3.6.1.4.1.231.7.1.2.2.1.12.1.2.10.1.8
		sheShdslVccTpLoopTestResult OBJECT-TYPE
			SYNTAX SheAtmOamLoopTestResultType
			MAX-ACCESS read-only
			STATUS current
			DESCRIPTION
				"Possible values:
				segSuccess(0),
				segFailure(1),
				endToEndSuccess(2),
				endToEndFailure(3),
				aborted(4),
				progress(5),
				notAvailable(65535)
				"
			::= { sheShdslVccTpEntry 8 }

		
--   1.3.6.1.4.1.231.7.1.2.2.1.12.1.2.10.1.9
		sheShdslVccTpLoopLocId OBJECT-TYPE
			SYNTAX OCTET STRING (SIZE (0..16))
			MAX-ACCESS read-only
			STATUS current
			DESCRIPTION
				"Test cell loopback location. It is an identifier known
				by the crafts person identifying a ATM node in the ATM
				network.  For EndToEnd loop test the default value is valid. "
			DEFVAL { 'FFFFFFFFFFFFFFFFFFFFFFFFFFFFFFFF'h }
			::= { sheShdslVccTpEntry 9 }

		
--   1.3.6.1.4.1.231.7.1.2.2.1.12.1.2.10.1.10
		sheShdslVccTpAlarmSeverityIndex OBJECT-TYPE
			SYNTAX Integer32
			MAX-ACCESS read-only
			STATUS current
			DESCRIPTION
				"Index to the AlarmSeverityProfileTable. Defines the actual 
				AlarmSeverities for all alarms per VccTp."
			DEFVAL { 1 }
			::= { sheShdslVccTpEntry 10 }

		
--   1.3.6.1.4.1.231.7.1.2.2.1.12.1.2.11
		sheShdslVccTpControl OBJECT IDENTIFIER ::= { sheShdslMIBObjects 11 }

		
--   1.3.6.1.4.1.231.7.1.2.2.1.12.1.2.11.1
		sheShdslVccTpControlRequest OBJECT-TYPE
			SYNTAX SheShdslControlRequestType
			MAX-ACCESS read-write
			STATUS current
			DESCRIPTION
				"modifyShdslVccTp:
				sheShdslVccTpControlIndex
				sheShdslVccTpControlVpi
				sheShdslVccTpControlVci
				sheShdslVccTpControlAlarmSeverityIndex
				
				modifyShdslVccTpLoopTest:
				sheShdslVccTpControlIndex
				sheShdslVccTpControlLoopTest
				
				createShdslVccTp:
				sheShdslVccTpControlSubLayerIndex
				sheShdslVccTpControlVpi
				sheShdslVccTpControlVci
				
				deleteShdslVccTp:
				sheShdslVccTpControlIndex
				"
			::= { sheShdslVccTpControl 1 }

		
--   1.3.6.1.4.1.231.7.1.2.2.1.12.1.2.11.2
		sheShdslVccTpControlIndex OBJECT-TYPE
			SYNTAX Integer32
			MAX-ACCESS read-write
			STATUS current
			DESCRIPTION
				"Index of the Table-entry to be configured."
			::= { sheShdslVccTpControl 2 }

		
--   1.3.6.1.4.1.231.7.1.2.2.1.12.1.2.11.3
		sheShdslVccTpControlStatus OBJECT-TYPE
			SYNTAX SheControlStatusType
			MAX-ACCESS read-only
			STATUS current
			DESCRIPTION
				"The status of a user command. 
				"
			::= { sheShdslVccTpControl 3 }

		
--   1.3.6.1.4.1.231.7.1.2.2.1.12.1.2.11.4
		sheShdslVccTpControlTimer OBJECT-TYPE
			SYNTAX Gauge32
			MAX-ACCESS read-only
			STATUS current
			DESCRIPTION
				"The maximum wait time for the manager for a long running user command. 
				"
			::= { sheShdslVccTpControl 4 }

		
--   1.3.6.1.4.1.231.7.1.2.2.1.12.1.2.11.5
		sheShdslVccTpControlReqResult OBJECT-TYPE
			SYNTAX SheShdslControlRequestResultType
			MAX-ACCESS read-only
			STATUS current
			DESCRIPTION
				"The result of the last user command."
			::= { sheShdslVccTpControl 5 }

		
--   1.3.6.1.4.1.231.7.1.2.2.1.12.1.2.11.6
		sheShdslVccTpControlTimeStamp OBJECT-TYPE
			SYNTAX Unsigned32
			UNITS "sec"
			MAX-ACCESS read-only
			STATUS current
			DESCRIPTION
				"The time stamp of the last command (end of command)."
			::= { sheShdslVccTpControl 6 }

		
--   1.3.6.1.4.1.231.7.1.2.2.1.12.1.2.11.7
		sheShdslVccTpControlSubLayerIndex OBJECT-TYPE
			SYNTAX InterfaceIndex
			MAX-ACCESS read-write
			STATUS current
			DESCRIPTION
				"Description."
			::= { sheShdslVccTpControl 7 }

		
--   1.3.6.1.4.1.231.7.1.2.2.1.12.1.2.11.9
		sheShdslVccTpControlVpi OBJECT-TYPE
			SYNTAX Integer32 (0..255)
			MAX-ACCESS read-write
			STATUS current
			DESCRIPTION
				"Vpi"
			::= { sheShdslVccTpControl 9 }

		
--   1.3.6.1.4.1.231.7.1.2.2.1.12.1.2.11.10
		sheShdslVccTpControlVci OBJECT-TYPE
			SYNTAX Integer32 (32..65535)
			MAX-ACCESS read-write
			STATUS current
			DESCRIPTION
				"Vci"
			::= { sheShdslVccTpControl 10 }

		
--   1.3.6.1.4.1.231.7.1.2.2.1.12.1.2.11.11
		sheShdslVccTpControlLoopTest OBJECT-TYPE
			SYNTAX SheAtmOamLoopTestType
			MAX-ACCESS read-write
			STATUS current
			DESCRIPTION
				"Actual LoopTest-Value. Only None or endToEnd will be accepted."
			::= { sheShdslVccTpControl 11 }

		
--   1.3.6.1.4.1.231.7.1.2.2.1.12.1.2.11.12
		sheShdslVccTpControlAlarmSeverityIndex OBJECT-TYPE
			SYNTAX Integer32
			MAX-ACCESS read-write
			STATUS current
			DESCRIPTION
				"Index of the used AlarmSeverityProfile."
			::= { sheShdslVccTpControl 12 }

		
--   1.3.6.1.4.1.231.7.1.2.2.1.12.1.2.12
		sheShdslVccTpNotifications OBJECT IDENTIFIER ::= { sheShdslMIBObjects 12 }

		
--   1.3.6.1.4.1.231.7.1.2.2.1.12.1.2.12.2
		sheShdslVccTpModified NOTIFICATION-TYPE
			OBJECTS { sheShdslVccTpControlIndex, sheShdslVccTpControlTimeStamp, sheShdslVccTpControlVpi, sheShdslVccTpControlVci, sheShdslVccTpControlLoopTest, 
				sheShdslVccTpControlAlarmSeverityIndex }
			STATUS current
			DESCRIPTION 
				"Configuration notification."
			::= { sheShdslVccTpNotifications 2 }

		
--   1.3.6.1.4.1.231.7.1.2.2.1.12.1.2.12.4
		sheShdslVccRDIAlarm NOTIFICATION-TYPE
			OBJECTS { sheAlarmTimeAndDate, sheAlarmReportingSource, sheAlarmReportingSourceType, sheAlarmSeverity }
			STATUS current
			DESCRIPTION 
				"RDI detected."
			::= { sheShdslVccTpNotifications 4 }

		
--   1.3.6.1.4.1.231.7.1.2.2.1.12.1.2.12.5
		sheShdslVccAISAlarm NOTIFICATION-TYPE
			OBJECTS { sheAlarmTimeAndDate, sheAlarmReportingSource, sheAlarmReportingSourceType, sheAlarmSeverity }
			STATUS current
			DESCRIPTION 
				"AIS detected. "
			::= { sheShdslVccTpNotifications 5 }

		
--   1.3.6.1.4.1.231.7.1.2.2.1.12.1.2.12.6
		sheShdslVccTpConfigurationFailed NOTIFICATION-TYPE
			OBJECTS { sheShdslVccTpControlRequest, sheShdslVccTpControlIndex, sheShdslVccTpControlStatus, sheShdslVccTpControlReqResult, sheShdslVccTpControlTimeStamp, 
				sheShdslVccTpControlSubLayerIndex }
			STATUS current
			DESCRIPTION 
				"Notification in case of failed VccTp-Configuration."
			::= { sheShdslVccTpNotifications 6 }

		
--   1.3.6.1.4.1.231.7.1.2.2.1.12.1.2.12.7
		sheShdslVccTpCreated NOTIFICATION-TYPE
			OBJECTS { sheShdslVccTpControlIndex, sheShdslVccTpNumber, sheShdslVccTpControlTimeStamp, sheShdslVccTpControlVpi, sheShdslVccTpControlVci, 
				sheShdslVccTpControlAlarmSeverityIndex, sheShdslVccTpControlSubLayerIndex, sheShdslVccTpControlLoopTest }
			STATUS current
			DESCRIPTION 
				"Configuration notification."
			::= { sheShdslVccTpNotifications 7 }

		
--   1.3.6.1.4.1.231.7.1.2.2.1.12.1.2.12.8
		sheShdslVccTpDeleted NOTIFICATION-TYPE
			OBJECTS { sheShdslVccTpControlIndex, sheShdslVccTpControlTimeStamp }
			STATUS current
			DESCRIPTION 
				"Configuration notification."
			::= { sheShdslVccTpNotifications 8 }

		
--   1.3.6.1.4.1.231.7.1.2.2.1.12.1.2.100
		sheShdslConformance OBJECT IDENTIFIER ::= { sheShdslMIBObjects 100 }

		
--   1.3.6.1.4.1.231.7.1.2.2.1.12.1.2.100.1
		sheShdslCompliances OBJECT IDENTIFIER ::= { sheShdslConformance 1 }

		
--   1.3.6.1.4.1.231.7.1.2.2.1.12.1.2.100.1.1
-- this module
-- this module
		sheShdslCompliance MODULE-COMPLIANCE
			STATUS current
			DESCRIPTION 
				"Description."
			MODULE -- this module
				MANDATORY-GROUPS { sheShdslGroup, sheShdslControlGroup, sheShdslNotificationGroup }
			::= { sheShdslCompliances 1 }

		
--   1.3.6.1.4.1.231.7.1.2.2.1.12.1.2.100.2
		sheShdslGroups OBJECT IDENTIFIER ::= { sheShdslConformance 2 }

		
--   1.3.6.1.4.1.231.7.1.2.2.1.12.1.2.100.2.1
		sheShdslGroup OBJECT-GROUP
			OBJECTS { sheShdslOpState, sheShdslStartProgress, sheShdslFwRelease, sheShdslLineSwap, sheShdslRmtCountryCode, 
				sheShdslRmtEncoderA, sheShdslRmtEncoderB, sheShdslRmtProviderCode, sheShdslLocDetect, sheShdslTxPower, 
				sheShdslFramerSync, sheShdslRmtTomData, sheShdslDriftAlarm, sheShdslReceiverGain, sheShdslBertError, 
				sheShdslFramerOHAndDefects, sheShdslRmtFwVersion, sheShdslUtopiaCellDelineation, sheShdslUtopiaRxCellCnt, sheShdslUtopiaCellDropCnt, 
				sheShdslUtopiaRxHecErrorCnt, sheShdslUtopiaTxCellCnt, sheShdslRmtNsfCusId, sheShdslRmtNsfCusData, sheShdslLocalHandshake, 
				sheShdslRemoteHandshake, sheShdslActualHandshake, sheShdslRmtTxPower, sheShdslRmtPowerBackoff, sheShdslAutoRetrainCount, 
				sheShdslEocState, sheShdslFramerOneSecondCnt, sheShdslNtrFault, sheShdslCpeMasterCore, sheShdslParametricTestResult, 
				sheShdslParametricTestArray, sheShdslStartUpInfo, sheShdslBisModeLocalHandshake, sheShdslBisModeRemoteHandshake, sheShdslBisModeActualHandshake, 
				sheShdslAction, sheShdslMode, sheShdslPowerScale, sheShdslEncodeCoeffA, sheShdslEncodeCoeffB, 
				sheShdslTxEOCBufferLen, sheShdslRxEOCBufferLen, sheShdslNTR, sheShdslRxUpstreamFrameSync, sheShdslRxDownstreamFrameSync, 
				sheShdslRxUpstreamStuffBits, sheShdslRxDownstreamStuffBits, sheShdslInitiate, sheShdslFramerRxClockMode, sheShdslFramerRxPllMode, 
				sheShdslSerialAtmCiuBufferSize, sheShdslTxFramerPulseDelay, sheShdslRxFramerPulseDelay, sheShdslMultiFrameMode, sheShdslEnable4or6MbpsBitrate, 
				sheShdslTomDataWord1, sheShdslTomDataWord2, sheShdslTomDataWord3, sheShdslTomDataWord4, sheShdslSetReqSilenceMode, 
				sheShdslSetIndividualRates1, sheShdslSetIndividualRates2, sheShdslSetIndividualRates3, sheShdslSatmCellDelineation, sheShdslFramerCellDropOnError, 
				sheShdslGearShiftType, sheShdslHsNsf, sheShdslHsMaxBitsPerBaud, sheShdslHsCusId, sheShdslHsCusData0, 
				sheShdslHsCusData1, sheShdslHsAnnexBType, sheShdslAutoRetrain, sheShdslArCrcCheck, sheShdslArFramerSyncCheck, 
				sheShdslArSnrMarginCheck, sheShdslArCrcThreshold, sheShdslArSnrMarginThreshold, sheShdslArRetrainTime, sheShdslOpStateTrapEnable, 
				sheShdslTxFrmrDataClkEdge, sheShdslRxFrmrDataClkEdge, sheShdslTxFrmrPulseClkEdge, sheShdslRxFrmrPulseClkEdge, sheShdslTxFrmrPulseLvl, 
				sheShdslRxFrmrPulseLvl, sheShdslFrmrOH, sheShdslLoopAttenCrossingTrapEnable, sheShdslSNRMarginCrossingTrapEnable, sheShdslFramerOHAndDefectsTrapEnable, 
				sheShdslParametricTestInputFile, sheShdslParamHybridLossTestStart, sheShdslParamHybridLossTestEnd, sheShdslFramerType, sheShdslAFEType, 
				sheShdslUtopiaL2TxAddress, sheShdslUtopiaL2RxAddress, sheShdslUtopiaDataBusWidth, sheShdslPAMMode, shehdsl2ShdslStatusNumAvailRepeaters, 
				shehdsl2ShdslStatusMaxAttainableLineRate, shehdsl2ShdslStatusActualLineRate, shehdsl2ShdslStatusTransmissionModeCurrent, sheShdslStatusMaxAttainablePayloadRate, sheShdslStatusActualPayloadRate, 
				shehdsl2ShdslInvVendorID, shehdsl2ShdslInvVendorModelNumber, shehdsl2ShdslInvVendorSerialNumber, shehdsl2ShdslInvVendorEOCSoftwareVersion, shehdsl2ShdslInvStandardVersion, 
				shehdsl2ShdslInvVendorListNumber, shehdsl2ShdslInvVendorIssueNumber, shehdsl2ShdslInvVendorSoftwareVersion, shehdsl2ShdslInvEquipmentCode, shehdsl2ShdslInvVendorOther, 
				shehdsl2ShdslInvTransmissionModeCapability, shehdsl2ShdslEndpointAlarmConfProfile, sheShdslStatusPMMSMaxLineRate, sheShdslStatus4WireHsMode, shehdsl2ShdslSpanConfNumRepeaters, 
				shehdsl2ShdslSpanConfProfile, shehdsl2ShdslSpanConfAlarmProfile, shehdsl2ShdslEndpointCurrAtn, shehdsl2ShdslEndpointCurrSnrMgn, shehdsl2ShdslEndpointCurrStatus, 
				shehdsl2ShdslEndpointES, shehdsl2ShdslEndpointSES, shehdsl2ShdslEndpointCRCanomalies, shehdsl2ShdslEndpointLOSWS, shehdsl2ShdslEndpointUAS, 
				shehdsl2ShdslEndpointCurr15MinTimeElapsed, shehdsl2ShdslEndpointCurr15MinES, shehdsl2ShdslEndpointCurr15MinSES, shehdsl2ShdslEndpointCurr15MinCRCanomalies, shehdsl2ShdslEndpointCurr15MinLOSWS, 
				shehdsl2ShdslEndpointCurr15MinUAS, shehdsl2ShdslEndpointCurr1DayTimeElapsed, shehdsl2ShdslEndpointCurr1DayES, shehdsl2ShdslEndpointCurr1DaySES, shehdsl2ShdslEndpointCurr1DayCRCanomalies, 
				shehdsl2ShdslEndpointCurr1DayLOSWS, shehdsl2ShdslEndpointCurr1DayUAS, shehdsl2Shdsl15MinIntervalEndTime, shehdsl2Shdsl15MinIntervalES, shehdsl2Shdsl15MinIntervalSES, 
				shehdsl2Shdsl15MinIntervalCRCanomalies, shehdsl2Shdsl15MinIntervalLOSWS, shehdsl2Shdsl15MinIntervalUAS, shehdsl2Shdsl1DayIntervalEndTime, shehdsl2Shdsl1DayIntervalMoniSecs, 
				shehdsl2Shdsl1DayIntervalES, shehdsl2Shdsl1DayIntervalSES, shehdsl2Shdsl1DayIntervalCRCanomalies, shehdsl2Shdsl1DayIntervalLOSWS, shehdsl2Shdsl1DayIntervalUAS, 
				shehdsl2ShdslMaintLoopbackConfig, shehdsl2ShdslMaintTipRingReversal, shehdsl2ShdslMaintPowerBackOff, shehdsl2ShdslMaintSoftRestart, shehdsl2ShdslSpanConfProfileIndex, 
				shehdsl2ShdslSpanConfProfileName, shehdsl2ShdslSpanConfWireInterface, shehdsl2ShdslSpanConfMinLineRate, shehdsl2ShdslSpanConfMaxLineRate, shehdsl2ShdslSpanConfPSD, 
				shehdsl2ShdslSpanConfTransmissionMode, shehdsl2ShdslSpanConfRemoteEnabled, shehdsl2ShdslSpanConfPowerFeeding, shehdsl2ShdslSpanConfCurrCondTargetMarginDown, shehdsl2ShdslSpanConfWorstCaseTargetMarginDown, 
				shehdsl2ShdslSpanConfCurrCondTargetMarginUp, shehdsl2ShdslSpanConfWorstCaseTargetMarginUp, shehdsl2ShdslSpanConfUsedTargetMargins, shehdsl2ShdslSpanConfReferenceClock, shehdsl2ShdslSpanConfLineProbeEnable, 
				shehdsl2ShdslEndpointAlarmConfProfileIndex, shehdsl2ShdslEndpointAlarmConfProfileName, shehdsl2ShdslEndpointThreshLoopAttenuation, shehdsl2ShdslEndpointThreshSNRMargin, shehdsl2ShdslEndpointThreshES, 
				shehdsl2ShdslEndpointThreshSES, shehdsl2ShdslEndpointThreshCRCanomalies, shehdsl2ShdslEndpointThreshLOSWS, shehdsl2ShdslEndpointThreshUAS, sheShdslVccTpIndex, 
				sheShdslVccTpSubLayerIndex, sheShdslVccTpNumber, sheShdslVccTpVpi, sheShdslVccTpVci, sheShdslVccTpOamLevel, 
				sheShdslVccTpLoopTest, sheShdslVccTpLoopTestResult, sheShdslVccTpLoopLocId, shehdsl2ShdslSpanConfPAMConstellation, shehdsl2ShdslSpanConfTCLayerSupported, 
				shehdsl2ShdslEndpointCurrTipRingReversal, shehdsl2ShdslEndpointCurrActivationState, sheShdslSpanStatusPAMModulation, sheShdslVccTpAlarmSeverityIndex, shehdsl2ShdslMaintLoopbackTimeout, 
				shehdsl2ShdslMaintUnitPowerSource }
			STATUS current
			DESCRIPTION 
				"Description."
			::= { sheShdslGroups 1 }

		
--   1.3.6.1.4.1.231.7.1.2.2.1.12.1.2.100.2.2
		sheShdslControlGroup OBJECT-GROUP
			OBJECTS { sheShdslCapabilityLineTxCap, sheShdslLineParamsControlRequest, sheShdslLineParamsControlIndex, sheShdslLineParamsControlStatus, sheShdslLineParamsControlTimer, 
				sheShdslLineParamsControlReqResult, sheShdslLineParamsControlTimeStamp, sheShdslLineParamsControlAction, sheShdslLineParamsControlMode, sheShdslLineParamsControlPowerScale, 
				sheShdslLineParamsControlEncodeCoeffA, sheShdslLineParamsControlEncodeCoeffB, sheShdslLineParamsControlTxEOCBufferLen, sheShdslLineParamsControlRxEOCBufferLen, sheShdslLineParamsControlNTR, 
				sheShdslLineParamsControlRxUpstreamFrameSync, sheShdslLineParamsControlRxDownstreamFrameSync, sheShdslLineParamsControlRxUpstreamStuffBits, sheShdslLineParamsControlRxDownstreamStuffBits, sheShdslLineParamsControlInitiate, 
				sheShdslLineParamsControlFramerRxClockMode, sheShdslLineParamsControlFramerRxPllMode, sheShdslLineParamsControlSerialAtmCiuBufferSize, sheShdslLineParamsControlTxFramerPulseDelay, sheShdslLineParamsControlRxFramerPulseDelay, 
				sheShdslLineParamsControlMultiFrameMode, sheShdslLineParamsControlEnable4or6MbpsBitrate, sheShdslLineParamsControlTomDataWord1, sheShdslLineParamsControlTomDataWord2, sheShdslLineParamsControlTomDataWord3, 
				sheShdslLineParamsControlTomDataWord4, sheShdslLineParamsControlSetReqSilenceMode, sheShdslLineParamsControlSetIndividualRates1, sheShdslLineParamsControlSetIndividualRates2, sheShdslLineParamsControlSetIndividualRates3, 
				sheShdslLineParamsControlSatmCellDelineation, sheShdslLineParamsControlFramerCellDropOnError, sheShdslLineParamsControlGearShiftType, sheShdslLineParamsControlHsNsf, sheShdslLineParamsControlHsMaxBitsPerBaud, 
				sheShdslLineParamsControlHsCusId, sheShdslLineParamsControlHsCusData0, sheShdslLineParamsControlHsCusData1, sheShdslLineParamsControlHsAnnexBType, sheShdslLineParamsControlAutoRetrain, 
				sheShdslLineParamsControlArCrcCheck, sheShdslLineParamsControlArFramerSyncCheck, sheShdslLineParamsControlArSnrMarginCheck, sheShdslLineParamsControlArCrcThreshold, sheShdslLineParamsControlArSnrMarginThreshold, 
				sheShdslLineParamsControlArRetrainTime, sheShdslLineParamsControlOpStateTrapEnable, sheShdslLineParamsControlTxFrmrDataClkEdge, sheShdslLineParamsControlRxFrmrDataClkEdge, sheShdslLineParamsControlTxFrmrPulseClkEdge, 
				sheShdslLineParamsControlRxFrmrPulseClkEdge, sheShdslLineParamsControlTxFrmrPulseLvl, sheShdslLineParamsControlRxFrmrPulseLvl, sheShdslLineParamsControlFrmrOH, sheShdslLineParamsControlLoopAttenCrossingTrapEnable, 
				sheShdslLineParamsControlSNRMarginCrossingTrapEnable, sheShdslLineParamsControlFramerOHAndDefectsTrapEnable, sheShdslLineParamsControlParametricTestInputFile, sheShdslLineParamsControlHybridLossTestStart, sheShdslLineParamsControlHybridLossTestEnd, 
				sheShdslLineParamsControlPAMMode, shehdsl2ShdslSpanConfControlRequest, shehdsl2ShdslSpanConfControlIndex, shehdsl2ShdslSpanConfControlStatus, shehdsl2ShdslSpanConfControlTimer, 
				shehdsl2ShdslSpanConfControlReqResult, shehdsl2ShdslSpanConfControlTimeStamp, shehdsl2ShdslSpanConfControlNumRepeaters, shehdsl2ShdslSpanConfControlProfile, shehdsl2ShdslSpanConfControlAlarmProfile, 
				shehdsl2ShdslEndpointConfControlRequest, shehdsl2ShdslEndpointConfControlIndex, shehdsl2ShdslEndpointConfControlStatus, shehdsl2ShdslEndpointConfControlTimer, shehdsl2ShdslEndpointConfControlReqResult, 
				shehdsl2ShdslEndpointConfControlTimeStamp, shehdsl2ShdslEndpointConfControlInvIndex, shehdsl2ShdslEndpointConfControlSide, shehdsl2ShdslEndpointConfControlWirePair, shehdsl2ShdslEndpointConfControlAlarmProfile, 
				shehdsl2ShdslEndpointMaintControlRequest, shehdsl2ShdslEndpointMaintControlIndex, shehdsl2ShdslEndpointMaintControlStatus, shehdsl2ShdslEndpointMaintControlTimer, shehdsl2ShdslEndpointMaintControlReqResult, 
				shehdsl2ShdslEndpointMaintControlTimeStamp, shehdsl2ShdslEndpointMaintControlInvIndex, shehdsl2ShdslEndpointMaintControlSide, shehdsl2ShdslEndpointMaintControlLoopbackConfig, shehdsl2ShdslEndpointMaintControlPowerBackOff, 
				shehdsl2ShdslEndpointMaintControlSoftRestart, shehdsl2ShdslUnitMaintControlRequest, shehdsl2ShdslUnitMaintControlIndex, shehdsl2ShdslUnitMaintControlStatus, shehdsl2ShdslUnitMaintControlTimer, 
				shehdsl2ShdslUnitMaintControlReqResult, shehdsl2ShdslUnitMaintControlTimeStamp, shehdsl2ShdslUnitMaintControlInvIndex, shehdsl2ShdslUnitMaintControlLoopbackTimeout, shehdsl2ShdslSpanConfProfileControlRequest, 
				shehdsl2ShdslSpanConfProfileControlIndex, shehdsl2ShdslSpanConfProfileControlStatus, shehdsl2ShdslSpanConfProfileControlTimer, shehdsl2ShdslSpanConfProfileControlReqResult, shehdsl2ShdslSpanConfProfileControlTimeStamp, 
				shehdsl2ShdslSpanConfProfileControlProfileName, shehdsl2ShdslSpanConfProfileControlWireInterface, shehdsl2ShdslSpanConfProfileControlMinLineRate, shehdsl2ShdslSpanConfProfileControlMaxLineRate, shehdsl2ShdslSpanConfProfileControlPSD, 
				shehdsl2ShdslSpanConfProfileControlTransmissionMode, shehdsl2ShdslSpanConfProfileControlRemoteEnabled, shehdsl2ShdslSpanConfProfileControlPowerFeeding, shehdsl2ShdslSpanConfProfileControlCurrCondTargetMarginDown, shehdsl2ShdslSpanConfProfileControlWorstCaseTargetMarginDown, 
				shehdsl2ShdslSpanConfProfileControlCurrCondTargetMarginUp, shehdsl2ShdslSpanConfProfileControlWorstCaseTargetMarginUp, shehdsl2ShdslSpanConfProfileControlUsedTargetMargins, shehdsl2ShdslSpanConfProfileControlReferenceClock, shehdsl2ShdslSpanConfProfileControlLineProbeEnable, 
				shehdsl2ShdslEndpointAlarmConfProfileControlRequest, shehdsl2ShdslEndpointAlarmConfProfileControlIndex, shehdsl2ShdslEndpointAlarmConfProfileControlStatus, shehdsl2ShdslEndpointAlarmConfProfileControlTimer, shehdsl2ShdslEndpointAlarmConfProfileControlReqResult, 
				shehdsl2ShdslEndpointAlarmConfProfileControlTimeStamp, shehdsl2ShdslEndpointAlarmConfProfileControlProfileName, shehdsl2ShdslEndpointConfProfileControlThreshLoopAttenuation, shehdsl2ShdslEndpointConfProfileControlThreshSNRMargin, shehdsl2ShdslEndpointConfProfileControlThreshES, 
				shehdsl2ShdslEndpointConfProfileControlThreshSES, shehdsl2ShdslEndpointConfProfileControlThreshCRCanomalies, shehdsl2ShdslEndpointConfProfileControlThreshLOSWS, shehdsl2ShdslEndpointConfProfileControlThreshUAS, sheShdslVccTpControlRequest, 
				sheShdslVccTpControlIndex, sheShdslVccTpControlStatus, sheShdslVccTpControlTimer, sheShdslVccTpControlReqResult, sheShdslVccTpControlTimeStamp, 
				sheShdslVccTpControlSubLayerIndex, sheShdslVccTpControlVpi, sheShdslVccTpControlVci, sheShdslVccTpControlLoopTest, sheShdslVccTpControlAlarmSeverityIndex, 
				shehdsl2ShdslSpanConfProfileControlPAMConstellation, shehdsl2ShdslSpanConfProfileControlTCLayerSupported }
			STATUS current
			DESCRIPTION 
				"Description."
			::= { sheShdslGroups 2 }

		
--   1.3.6.1.4.1.231.7.1.2.2.1.12.1.2.100.2.3
		sheShdslNotificationGroup NOTIFICATION-GROUP
			NOTIFICATIONS { shehdsl2ShdslLoopAttenCrossing, shehdsl2ShdslSNRMarginCrossing, shehdsl2ShdslPerfESThresh, shehdsl2ShdslPerfSESThresh, shehdsl2ShdslPerfCRCanomaliesThresh, 
				shehdsl2ShdslPerfLOSWSThresh, shehdsl2ShdslPerfUASThresh, shehdsl2ShdslSpanInvalidNumRepeaters, shehdsl2ShdslLoopbackFailure, shehdsl2ShdslpowerBackoff, 
				shehdsl2ShdsldeviceFault, shehdsl2ShdsldcContinuityFault, shehdsl2ShdslconfigInitFailure, shehdsl2ShdslprotocolInitFailure, shehdsl2ShdslnoNeighborPresent, 
				shehdsl2ShdslLocalPowerLoss, shehdsl2ShdslAtucPerfLol, shehdsl2ShdslAtucPerfLpr, sheShdslLineParamsEntryModified, shehdsl2ShdslSpanConfEntryModified, 
				shehdsl2ShdslSpanConfEntryAlarmProfileModified, shehdsl2ShdslEndpointConfEntryModified, shehdsl2ShdslEndpointMaintEntryModified, shehdsl2ShdslUnitMaintEntryModified, shehdsl2ShdslSpanConfProfileCreated, 
				shehdsl2ShdslSpanConfProfileModified, shehdsl2ShdslSpanConfProfileDeleted, shehdsl2ShdslEndpointAlarmConfProfileCreated, shehdsl2ShdslEndpointAlarmConfProfileModified, shehdsl2ShdslEndpointAlarmConfProfileDeleted, 
				sheShdslVccTpModified, sheShdslVccRDIAlarm, sheShdslVccAISAlarm, sheShdslVccTpConfigurationFailed, sheShdslVccTpCreated, 
				shehdsl2ShdslAtucPerfLos, shehdsl2ShdslAtucPerfLof, shehdsl2ShdslEndpointAlarmConfProfileReqResult, sheShdslVccTpDeleted, shehdsl2ShdslSpanConfProfileReqResult
				 }
			STATUS current
			DESCRIPTION 
				"Description."
			::= { sheShdslGroups 3 }

		
--   1.3.6.1.4.1.231.7.1.2.2.1.12.1.2.100.2.4
		sheShdslObsoleteGroup OBJECT-GROUP
			OBJECTS { sheShdslBondingGroupBridgePortList, sheShdslBondingGroupType }
			STATUS obsolete
			DESCRIPTION 
				"Description."
			::= { sheShdslGroups 4 }

		
	
	END

--
-- she-shdsl-mib.mib
--
