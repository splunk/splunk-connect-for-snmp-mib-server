--
-- AVAYA-SAA-TRACK-MIB.my
-- MIB generated by MG-SOFT Visual MIB Builder Version 3.0 Build 253
-- Wednesday, May 04, 2005 at 11:52:58
--

-- Copyright © 2004 by Avaya Inc. All rights reserved.
-- 
-- This AVAYA SNMP Management Information Base Specification (Specification) 
-- embodies AVAYA confidential and Proprietary intellectual property.  
-- AVAYA retains all Title and ownership in the Specification, including any 
-- revisions.
-- 
-- It is AVAYA's intent to encourage the widespread use of this Specification 
-- in connection with the management of AVAYA products. AVAYA grants vendors, 
-- end-users, and other interested parties a non-exclusive license to use this 
-- Specification in connection with the management of AVAYA products.
-- 
-- This Specification is supplied "as is," and AVAYA makes no warranty, either 
-- express or implied, as to the use, operation, condition, or performance of 
-- the Specification.
-- 
-- ========================================================
-- SourceSafe Version Information:
-- $Revision: 18 $
-- Check in $Date: 11/01/07 12:27p $
-- $Author: Sbiton $
-- $Archive: /MIBs/Version 1.0/Source/Avaya/AVAYA-SAA-TRACK-MIB.my $
-- ========================================================

	AVAYA-SAA-TRACK-MIB DEFINITIONS ::= BEGIN
 
		IMPORTS
			avGatewayMibs			
				FROM AVAYAGEN-MIB			
			InterfaceIndex			
				FROM IF-MIB			
			OBJECT-GROUP, MODULE-COMPLIANCE			
				FROM SNMPv2-CONF			
			TimeTicks, IpAddress, Unsigned32, OBJECT-TYPE, MODULE-IDENTITY, 
			NOTIFICATION-TYPE			
				FROM SNMPv2-SMI			
			RowStatus, DisplayString, TruthValue, MacAddress			
				FROM SNMPv2-TC;
	
	
		avayaSaaTrackMib MODULE-IDENTITY 
			LAST-UPDATED "200701081657Z"
			ORGANIZATION 
				"Avaya, Inc."
			CONTACT-INFO 
				"    Avaya Customer Services
				
				Postal: Avaya, Inc.
				        211 Mt Airy Rd.
				        Basking Ridge, NJ 07920
				        USA
				
				Tel:    +1 908 953 6000
				
				E-mail: executiveoffic@avaya.com
				
				WWW:    http://www.avaya.com"
			DESCRIPTION 
				"The MIB module for configuring SAA and Object Tracking
				functionality in Avaya converged Gateways."
			REVISION "200701081657Z"		
			DESCRIPTION 
				"Shlomi Biton - Add avstrRtrDestHostName and avstrRtrResolvedIp
				for rtr configuration with destination hostname.
				Add avstrTrackerPermanentTrackState for keeping track status
				after reboot. "
	    	::= { avGatewayMibs 2 }
		
--
-- Node definitions
--
	
		-- 1.3.6.1.4.1.6889.2.6.2.1
		avstrMIBObjects OBJECT IDENTIFIER ::= { avayaSaaTrackMib 1 }
		
		-- 1.3.6.1.4.1.6889.2.6.2.1.1
		avstrRtrMIBObjects OBJECT IDENTIFIER ::= { avstrMIBObjects 1 }
		
		-- 1.3.6.1.4.1.6889.2.6.2.1.1.1
		avstrRtrTable OBJECT-TYPE
			SYNTAX SEQUENCE OF AvstrRtrEntry
			MAX-ACCESS not-accessible
			STATUS current
			DESCRIPTION
				"This table contains all the rtr's configured on the device."
			::= { avstrRtrMIBObjects 1 }
		
		-- 1.3.6.1.4.1.6889.2.6.2.1.2.4.1
		avstrRtrEntry OBJECT-TYPE
			SYNTAX AvstrRtrEntry
			MAX-ACCESS not-accessible
			STATUS current
			DESCRIPTION
				"A specific entry."
			INDEX { avstrRtrId }
			::= { avstrRtrTable 1 }
		
		AvstrRtrEntry ::=
			SEQUENCE { 
				avstrRtrId
					Unsigned32,
				avstrRtrType
					INTEGER,
				avstrRtrDestIp
					IpAddress,
				avstrRtrDestPort
					INTEGER,
				avstrRtrFrequencyMs
					Unsigned32,
				avstrRtrWaitIntervalMs
					Unsigned32,
				avstrRtrFailRetries
					Unsigned32,
				avstrRtrSuccessRetries
					Unsigned32,
				avstrRtrProbeDscp
					Unsigned32,
				avstrRtrProbeSrcIpAddr
					IpAddress,
				avstrRtrProbeNextHopIf
					InterfaceIndex,
				avstrRtrProbeNextHopMac
					MacAddress,
				avstrRtrSchedule
					INTEGER,
				avstrRtrOperState
					INTEGER,
				avstrRtrOperStateLastChange
					TimeTicks,
				avstrRtrRowStatus
					RowStatus,
				avstrRtrProbeNextHopIp
					IpAddress,
				avstrRtrIfKpaliveBypass
					TruthValue,
				avstrRtrDestHostName
					DisplayString, 
				avstrRtrResolvedIp
					IpAddress
			 }

		-- 1.3.6.1.4.1.6889.2.6.2.1.2.4.1.1
		avstrRtrId OBJECT-TYPE
			SYNTAX Unsigned32
			MAX-ACCESS not-accessible
			STATUS current
			DESCRIPTION
				"The ID of the RTR.
				
				This is also the index component of this table."
			::= { avstrRtrEntry 1 }
		
		-- 1.3.6.1.4.1.6889.2.6.2.1.2.4.1.2
		avstrRtrType OBJECT-TYPE
			SYNTAX INTEGER
				{
				none(1),
				ipIcmpEcho(2),
				tcpConnect(3)
				}
			MAX-ACCESS read-write
			STATUS current
			DESCRIPTION
				"The type of test this rtr object maintains."
			DEFVAL { none }
			::= { avstrRtrEntry 2 }
		
		-- 1.3.6.1.4.1.6889.2.6.2.1.2.4.1.3
		avstrRtrDestIp OBJECT-TYPE
			SYNTAX IpAddress
			MAX-ACCESS read-write
			STATUS current
			DESCRIPTION
				"The destination IP address of SAA probes generated by this 
				entry."
			::= { avstrRtrEntry 3 }
		
		-- 1.3.6.1.4.1.6889.2.6.2.1.2.4.1.4
		avstrRtrDestPort OBJECT-TYPE
			SYNTAX INTEGER (0..65535)
			MAX-ACCESS read-write
			STATUS current
			DESCRIPTION
				"The destination port of SAA probes generated by this entry.
				
				This object is meaningfull only when avstrRtrType is set to
				tcpConnect(3)."
			::= { avstrRtrEntry 4 }
		
		-- 1.3.6.1.4.1.6889.2.6.2.1.2.4.1.5
		avstrRtrFrequencyMs OBJECT-TYPE
			SYNTAX Unsigned32
			MAX-ACCESS read-write
			STATUS current
			DESCRIPTION
				"The frequency, in milliseconds, between one SAA probe
				and the next."
			DEFVAL { 5000 }
			::= { avstrRtrEntry 5 }
		
		-- 1.3.6.1.4.1.6889.2.6.2.1.2.4.1.6
		avstrRtrWaitIntervalMs OBJECT-TYPE
			SYNTAX Unsigned32
			MAX-ACCESS read-write
			STATUS current
			DESCRIPTION
				"The interval, in milliseconds, from the time an SAA probe
				is sent until the device waits for a reply for that SAA
				probe."
			DEFVAL { 5000 }
			::= { avstrRtrEntry 6 }
		
		-- 1.3.6.1.4.1.6889.2.6.2.1.2.4.1.7
		avstrRtrFailRetries OBJECT-TYPE
			SYNTAX Unsigned32
			MAX-ACCESS read-write
			STATUS current
			DESCRIPTION
				"When the current state of this entry is 'up', the value
				of this object determines the number of successive 
				failed probes after which the state of this entry moves 
				to 'down'."
			DEFVAL { 5 }
			::= { avstrRtrEntry 7 }
		
		-- 1.3.6.1.4.1.6889.2.6.2.1.2.4.1.8
		avstrRtrSuccessRetries OBJECT-TYPE
			SYNTAX Unsigned32
			MAX-ACCESS read-write
			STATUS current
			DESCRIPTION
				"When the current state of this entry is 'down', the value
				of this object determines the number of successive 
				successful probes after which the state of this entry 
				moves to 'up'."
			DEFVAL { 1 }
			::= { avstrRtrEntry 8 }
		
		-- 1.3.6.1.4.1.6889.2.6.2.1.2.4.1.9
		avstrRtrProbeDscp OBJECT-TYPE
			SYNTAX Unsigned32 (0..63)
			MAX-ACCESS read-write
			STATUS current
			DESCRIPTION
				"The DSCP value of SAA probes generated by this entry."
			::= { avstrRtrEntry 9 }
		
		-- 1.3.6.1.4.1.6889.2.6.2.1.2.4.1.10
		avstrRtrProbeSrcIpAddr OBJECT-TYPE
			SYNTAX IpAddress
			MAX-ACCESS read-write
			STATUS current
			DESCRIPTION
				"The source IP address of SAA probes sent by this entry.
				The value 0.0.0.0 means that this address shall be 
				taken from the probe's egress interface's address."
			DEFVAL { '00000000'h }
			::= { avstrRtrEntry 10 }
		
		-- 1.3.6.1.4.1.6889.2.6.2.1.2.4.1.11
		avstrRtrProbeNextHopIf OBJECT-TYPE
			SYNTAX InterfaceIndex
			MAX-ACCESS read-write
			STATUS current
			DESCRIPTION
				"This node is valid only if avstrRtrProbeNextHopIp
				is set to '0.0.0.0'.
				
				The interface on which SAA probes generated by this
				entry shall exit, bypassing normal routing.
				A value of '0' means the probes will undergo 
				routing normally.
				
				NOTES:
				1. In order to set this object, you must first move 
				avstrRtrRowStatus to notInService. When finished 
				setting this object and avstrRtrProbeNextHopMac - 
				move it back to active.
				2. When setting this object to an Ethernet type
				interface which does not employ DHCP client, you must 
				also specify the next-hop MAC address by setting 
				avstrRtrProbeNextHopMac.
				When a DHCP client is used, if the MAC address is not 
				specified, the default Gateway received from the DHCP 
				server shall be used as the next hop."
			DEFVAL { 0 }
			::= { avstrRtrEntry 11 }
		
		-- 1.3.6.1.4.1.6889.2.6.2.1.2.4.1.12
		avstrRtrProbeNextHopMac OBJECT-TYPE
			SYNTAX MacAddress
			MAX-ACCESS read-write
			STATUS current
			DESCRIPTION
				"Use this object in conjunction with 
				avstrRtrProbeNextHopIf to manually set the next-hop
				of SAA probes generated by this entry.
				This object is meaningfull only when the value of 
				avstrRtrProbeNextHopIf is valid and set to an 
				Ethernet type interface.
				
				NOTE:
				In order to set this object, you must first move 
				avstrRtrRowStatus to notInService. When finished 
				setting this object and avstrRtrProbeNextHopIf - 
				move it back to active."
			DEFVAL { '000000000000'h }
			::= { avstrRtrEntry 12 }
		
		-- 1.3.6.1.4.1.6889.2.6.2.1.2.4.1.13
		avstrRtrSchedule OBJECT-TYPE
			SYNTAX INTEGER
				{
				inactive(1),
				active(2)
				}
			MAX-ACCESS read-write
			STATUS current
			DESCRIPTION
				"This object specifies the scheduling status of this row.
				inactive(1) - This entry is currently not scheduled to run.
				active(2)   - This entry is currently running."
			DEFVAL { inactive }
			::= { avstrRtrEntry 13 }
		
		-- 1.3.6.1.4.1.6889.2.6.2.1.2.4.1.14
		avstrRtrOperState OBJECT-TYPE
			SYNTAX INTEGER
				{
				inactive(1),
				up(2),
				down(3)
				}
			MAX-ACCESS read-only
			STATUS current
			DESCRIPTION
				"The conceptual operational state of this entry:
				inactive(1) - the entry is not operating yet.
				up(2)   - the entry is up. This is also the initial state of the 
				          entry when it starts operating (i.e. moves out of
				          the 'inactive' state).
				down(3) - the entry is down.
				
				NOTE: Refer to avstrRtrFailRetries and avstrRtrSuccessRetries 
				to understand how the entry transitions between 'up' and 
				'down' states."
			::= { avstrRtrEntry 14 }
		
		-- 1.3.6.1.4.1.6889.2.6.2.1.2.4.1.15
		avstrRtrOperStateLastChange OBJECT-TYPE
			SYNTAX TimeTicks
			MAX-ACCESS read-only
			STATUS current
			DESCRIPTION
				"sysUpTime when the last change in avstrRtrOperState
				occured, in hundredths of a second."
			::= { avstrRtrEntry 15 }
		
		-- 1.3.6.1.4.1.6889.2.6.2.1.2.4.1.16
		avstrRtrRowStatus OBJECT-TYPE
			SYNTAX RowStatus
			MAX-ACCESS read-write
			STATUS current
			DESCRIPTION
				"This object indicates the conceptual status of this row.
				
				The value of this object has no effect on whether other
				objects in this conceptual row can be modified.
				
				If active, this object must remain active if it is referenced
				by a row in another table.
				
				Use createAndWait (not createAndGo) to create this row.
				In order for this row to be active(1) avstrRtrType and 
				(avstrRtrDestIp or avstrRtrDestHostName) must be set to a 
				valid value."
			::= { avstrRtrEntry 16 }
		
		-- 1.3.6.1.4.1.6889.2.6.2.1.2.4.1.17
		avstrRtrProbeNextHopIp OBJECT-TYPE
			SYNTAX IpAddress
			MAX-ACCESS read-write
			STATUS current
			DESCRIPTION
				"The IP address of the next-hop to which SAA probes 
				generated by this entry shall be routed, bypassing 
				normal routing.
				A value of '0.0.0.0' means that the value in 
				avstrRtrProbeNextHopIf is valid instead.
				
				Note:
				Setting this node to '0.0.0.0' and 
				avstrRtrProbeNextHopIf to '0' will result in the 
				probes undergoing routing normally.
				"
			DEFVAL { '00000000'h }
			::= { avstrRtrEntry 17 }
		
		-- 1.3.6.1.4.1.6889.2.6.2.1.2.4.1.18
		avstrRtrIfKpaliveBypass OBJECT-TYPE
			SYNTAX TruthValue
			MAX-ACCESS read-write
			STATUS current
			DESCRIPTION
				"This node controls whether or not SAA probes 
				generated by this rtr will undergo normal path 
				internally (False), in the Gateway's network stack,
				or will undergo a special bypass path (True) that is 
				required when this rtr is used in conjunction with 
				the interface keepalive feature.
				
				NOTE:
				This node is valid only if avstrRtrProbeNextHopIf
				is valid and set to a value != '0'."
			DEFVAL { false }
			::= { avstrRtrEntry 18 }
			

		avstrRtrDestHostName OBJECT-TYPE
			SYNTAX DisplayString (SIZE (1..255))
			MAX-ACCESS read-write
			STATUS current
			DESCRIPTION
				"The hostname shall follow RFC 1035 Host name convention.
				
				Note that while upper and lower case letters are allowed in domain
				names, no significance is attached to the case.  That is, two names with
				the same spelling but different case are to be treated as if identical.

				The labels must start with a letter or digit, end with a letter or digit, and have as interior
				characters only letters, digits, and hyphen.  There are also some
				restrictions on the length.  Labels must be 63 characters or less. 
				There are up to 4 labels per hostname.
				"
			::= { avstrRtrEntry 19 }
			
		avstrRtrResolvedIp OBJECT-TYPE
			SYNTAX IpAddress
			MAX-ACCESS read-only
			STATUS current
			DESCRIPTION
				"The Resolved destination IP address of SAA probes generated by this 
				entry. 
				The value 0.0.0.0 will be presented if avstrRtrDestHostName is not
				configured or if avstrRtrDestHostName is not resolved."
			::= { avstrRtrEntry 20 }
							
		-- 1.3.6.1.4.1.6889.2.6.2.1.2
		avstrTrackerMIBObjects OBJECT IDENTIFIER ::= { avstrMIBObjects 2 }
		
		-- 1.3.6.1.4.1.6889.2.6.2.1.2.1
		avstrTrackerTable OBJECT-TYPE
			SYNTAX SEQUENCE OF AvstrTrackerEntry
			MAX-ACCESS not-accessible
			STATUS current
			DESCRIPTION
				"This table contains all the object-trackers configured on 
				the device."
			::= { avstrTrackerMIBObjects 1 }
		
		-- 1.3.6.1.4.1.6889.2.6.2.1.3.4.1
		avstrTrackerEntry OBJECT-TYPE
			SYNTAX AvstrTrackerEntry
			MAX-ACCESS not-accessible
			STATUS current
			DESCRIPTION
				"A specific entry."
			INDEX { avstrTrackerId }
			::= { avstrTrackerTable 1 }
		
		AvstrTrackerEntry ::=
			SEQUENCE { 
				avstrTrackerId
					Unsigned32,
				avstrTrackerDescription
					DisplayString,
				avstrTrackerType
					INTEGER,
				avstrTrackerRtrId
					Unsigned32,
				avstrTrackerListType
					INTEGER,
				avstrTrackerListThresholdUp
					Unsigned32,
				avstrTrackerListThresholdDown
					Unsigned32,
				avstrTrackerOperState
					INTEGER,
				avstrTrackerOperStateLastChange
					TimeTicks,
				avstrTrackerRowStatus
					RowStatus,
				avstrTrackerPermanentTrackState
					TruthValue
			 }
                         
                         
		-- 1.3.6.1.4.1.6889.2.6.2.1.3.4.1.1
		avstrTrackerId OBJECT-TYPE
			SYNTAX Unsigned32
			MAX-ACCESS not-accessible
			STATUS current
			DESCRIPTION
				"The ID of the object-tracker object.
				
				This is also the index component of this table."
			::= { avstrTrackerEntry 1 }
		
		-- 1.3.6.1.4.1.6889.2.6.2.1.3.4.1.2
		avstrTrackerDescription OBJECT-TYPE
			SYNTAX DisplayString
			MAX-ACCESS read-write
			STATUS current
			DESCRIPTION
				"Free text describing this row."
			DEFVAL { ''b }
			::= { avstrTrackerEntry 2 }
		
		-- 1.3.6.1.4.1.6889.2.6.2.1.3.4.1.3
		avstrTrackerType OBJECT-TYPE
			SYNTAX INTEGER
				{
				list(1),
				rtr(2)
				}
			MAX-ACCESS read-write
			STATUS current
			DESCRIPTION
				"The type of object to be tracked by this object-tracker.
				The value list(1) is reserved for specifying an entry
				that tracks a list of object-trackers."
			::= { avstrTrackerEntry 3 }
		
		-- 1.3.6.1.4.1.6889.2.6.2.1.3.4.1.4
		avstrTrackerRtrId OBJECT-TYPE
			SYNTAX Unsigned32
			MAX-ACCESS read-write
			STATUS current
			DESCRIPTION
				"This object has a meaning only when avstrTrackerType is set to
				rtr(2).
				The avstrRtrId of the tracked rtr."
			::= { avstrTrackerEntry 4 }
		
		-- 1.3.6.1.4.1.6889.2.6.2.1.3.4.1.5
		avstrTrackerListType OBJECT-TYPE
			SYNTAX INTEGER
				{
				boolAnd(1),
				boolOr(2),
				threshCount(3)
				}
			MAX-ACCESS read-write
			STATUS current
			DESCRIPTION
				"This object has a meaning only when avstrTrackerType is set to
				list(1).
				The value of this object determines how the states of the 
				object-trackers in the tracked list are analyzed in order 
				to determine the state of this object-tracker entry.
				Possible values are:
				boolAnd(1) - The entry is 'up' if all object-trackers are 'up', 
				             or 'down' if one or more object-trackers are 
				             'down'.
				boolOr(2)  - The entry is 'up' if at least one object-tracker 
				             in the list is 'up'.
				threshCount(3) - When the entry is in the 'down' state it 
				                 switches to the 'up' state if the number of 
				                 'up' object-trackers is greater or equal then
				                 the number specified in 
				                 avstrTrackerThresholdUp.
				                 When the entry is in the 'up' state it 
				                 switches to the 'down' state if the number of
				                 'up' objects is less then or equal to the 
				                 number specified in avstrTrackerThresholdDown."
			DEFVAL { boolAnd }
			::= { avstrTrackerEntry 5 }
		
		-- 1.3.6.1.4.1.6889.2.6.2.1.3.4.1.6
		avstrTrackerListThresholdUp OBJECT-TYPE
			SYNTAX Unsigned32
			MAX-ACCESS read-write
			STATUS current
			DESCRIPTION
				"This object has a meaning only when avstrTrackerType is set to
				list(1), and avstrTrackerListType is set to threshXxx.
				When the current state of this entry is 'down', the value
				of this object determines the number of 'up' object-trackers
				in the list that will cause a transition of this entry to 
				the 'up' state."
			::= { avstrTrackerEntry 6 }
		
		-- 1.3.6.1.4.1.6889.2.6.2.1.3.4.1.7
		avstrTrackerListThresholdDown OBJECT-TYPE
			SYNTAX Unsigned32
			MAX-ACCESS read-write
			STATUS current
			DESCRIPTION
				"This object has a meaning only when avstrTrackType is set to
				list(1), and avstrTrackListType is set to threshXxx.
				When the current state of this entry is 'up', the value
				of this object determines the number of 'down' object-trackers
				in the list that will cause a transition of this entry to the 
				'down' state."
			::= { avstrTrackerEntry 7 }
		
		-- 1.3.6.1.4.1.6889.2.6.2.1.3.4.1.8
		avstrTrackerOperState OBJECT-TYPE
			SYNTAX INTEGER
				{
				reserved(1),
				up(2),
				down(3)
				}
			MAX-ACCESS read-only
			STATUS current
			DESCRIPTION
				"The conceptual operational state of this entry:
				reserved(1) - this value is currently reserved.
				up(2)   - the monitored object is 'up'.
				down(3) - the monitored object is 'down' or 'inactive'.
				
				NOTE: Refer to avstrTrackerListType, avstrTrackerThresholdUp 
				and avstrTrackerThresholdDown to understand how the entry 
				transitions between 'up' and 'down' states."
			::= { avstrTrackerEntry 8 }
		
		-- 1.3.6.1.4.1.6889.2.6.2.1.3.4.1.9
		avstrTrackerOperStateLastChange OBJECT-TYPE
			SYNTAX TimeTicks
			MAX-ACCESS read-only
			STATUS current
			DESCRIPTION
				"sysUpTime when the last change in avstrTrackerOperState
				occured, in hundredths of a second."
			::= { avstrTrackerEntry 9 }
		
		-- 1.3.6.1.4.1.6889.2.6.2.1.3.4.1.10
		avstrTrackerRowStatus OBJECT-TYPE
			SYNTAX RowStatus
			MAX-ACCESS read-write
			STATUS current
			DESCRIPTION
				"This object indicates the conceptual status of this row.
				
				The value of this object has no effect on whether other
				objects in this conceptual row can be modified.
				
				If active, this object must remain active if it is referenced
				by a row in another table.
				
				Use createAndWait (not createAndGo) to create this row.
				In order for this row to be active(1) either the following 
				must hold:
				o Set avstrTrackerType to list(1).
				o Set avstrTrackerType to rtr(2), and set avstrTrackerRtrId
				  to an avstrRtrId of an active(1) rtr entry."
			::= { avstrTrackerEntry 10 }
			
			
		avstrTrackerPermanentTrackState OBJECT-TYPE
			SYNTAX TruthValue
			MAX-ACCESS read-write
			STATUS current
			DESCRIPTION
				"Enable/Disable for storing the track state or not in permanent 
				memory to be available after reboot. 
				The default mode is of not keeping the track state after reboot
				and therefore starting as track is down."
			DEFVAL { false }
			::= { avstrTrackerEntry 11 }
		
		
		-- 1.3.6.1.4.1.6889.2.6.2.1.2.2
		avstrTrackerListObjsTable OBJECT-TYPE
			SYNTAX SEQUENCE OF AvstrTrackerListObjsEntry
			MAX-ACCESS not-accessible
			STATUS current
			DESCRIPTION
				"This table contains the associations between object-tracker
				lists and the object-tracker objects they contain."
			::= { avstrTrackerMIBObjects 2 }
		
		-- 1.3.6.1.4.1.6889.2.6.2.1.3.5.1
		avstrTrackerListObjsEntry OBJECT-TYPE
			SYNTAX AvstrTrackerListObjsEntry
			MAX-ACCESS not-accessible
			STATUS current
			DESCRIPTION
				"A specific entry."
			INDEX { avstrTrackerListObjsParentTrackId, avstrTrackerListObjsChildTrackId }
			::= { avstrTrackerListObjsTable 1 }
		
		AvstrTrackerListObjsEntry ::=
			SEQUENCE { 
				avstrTrackerListObjsParentTrackId
					Unsigned32,
				avstrTrackerListObjsChildTrackId
					Unsigned32,
				avstrTrackerListObjsRowStatus
					RowStatus,
				avstrTrackerListObjsReverseState
					TruthValue
			 }

		-- 1.3.6.1.4.1.6889.2.6.2.1.3.5.1.1
		avstrTrackerListObjsParentTrackId OBJECT-TYPE
			SYNTAX Unsigned32
			MAX-ACCESS not-accessible
			STATUS current
			DESCRIPTION
				"The avstrTrackerId of the object-tracker list object."
			::= { avstrTrackerListObjsEntry 1 }
		
		-- 1.3.6.1.4.1.6889.2.6.2.1.3.5.1.2
		avstrTrackerListObjsChildTrackId OBJECT-TYPE
			SYNTAX Unsigned32
			MAX-ACCESS not-accessible
			STATUS current
			DESCRIPTION
				"The avstrTrackerId of the object-tracker that is part of the 
				tracked list."
			::= { avstrTrackerListObjsEntry 2 }
		
		-- 1.3.6.1.4.1.6889.2.6.2.1.3.5.1.3
		avstrTrackerListObjsRowStatus OBJECT-TYPE
			SYNTAX RowStatus
			MAX-ACCESS read-write
			STATUS current
			DESCRIPTION
				"This object indicates the conceptual status of this row.
				
				The value of this object has no effect on whether other
				objects in this conceptual row can be modified.
				
				If active, this object must remain active if it is referenced
				by a row in another table.
				
				Use createAndGo (not createAndWait) to create this row."
			::= { avstrTrackerListObjsEntry 3 }
		
		-- 1.3.6.1.4.1.6889.2.6.2.1.3.5.1.4
		avstrTrackerListObjsReverseState OBJECT-TYPE
			SYNTAX TruthValue
			MAX-ACCESS read-write
			STATUS current
			DESCRIPTION
				"This object determines whether the state of object being 
				tracked is reversed or not. When a state is reversed 'up' is
				considered as 'down', and vice-versa.
				The default value is 'false', which means the state is not 
				reversed."
			DEFVAL { false }
			::= { avstrTrackerListObjsEntry 4 }
		
		-- 1.3.6.1.4.1.6889.2.6.2.1.2.3
		avstrTrackerPtrsTable OBJECT-TYPE
			SYNTAX SEQUENCE OF AvstrTrackerPtrsEntry
			MAX-ACCESS not-accessible
			STATUS current
			DESCRIPTION
				"This table is an informational read-only table that contains
				a list of all the objects that are currently pointing to each
				object-tracker in the system.
				This table is provided for convenience only. An alternative
				equivalent method is to walk over all the variuos ojects in 
				the system that may point to object-trackers."
			::= { avstrTrackerMIBObjects 3 }
		
		-- 1.3.6.1.4.1.6889.2.6.2.1.2.6.1
		avstrTrackerPtrsEntry OBJECT-TYPE
			SYNTAX AvstrTrackerPtrsEntry
			MAX-ACCESS not-accessible
			STATUS current
			DESCRIPTION
				"A specific entry."
			INDEX { avstrTrackerPtrsTrackId, avstrTrackerPtrsIndex }
			::= { avstrTrackerPtrsTable 1 }
		
		AvstrTrackerPtrsEntry ::=
			SEQUENCE { 
				avstrTrackerPtrsTrackId
					Unsigned32,
				avstrTrackerPtrsIndex
					Unsigned32,
				avstrTrackerPtrsDescription
					DisplayString,
				avstrTrackerPtrsType
					INTEGER,
				avstrTrackerPtrsValue
					OCTET STRING
			 }

		-- 1.3.6.1.4.1.6889.2.6.2.1.2.6.1.1
		avstrTrackerPtrsTrackId OBJECT-TYPE
			SYNTAX Unsigned32
			MAX-ACCESS not-accessible
			STATUS current
			DESCRIPTION
				"An ID of the object-tracker, taken from avstrTrackerId."
			::= { avstrTrackerPtrsEntry 1 }
		
		-- 1.3.6.1.4.1.6889.2.6.2.1.2.6.1.2
		avstrTrackerPtrsIndex OBJECT-TYPE
			SYNTAX Unsigned32
			MAX-ACCESS not-accessible
			STATUS current
			DESCRIPTION
				"A running-index to distinguish between multiple objects
				pointing to the same object-tracker."
			::= { avstrTrackerPtrsEntry 2 }
		
		-- 1.3.6.1.4.1.6889.2.6.2.1.2.6.1.3
		avstrTrackerPtrsDescription OBJECT-TYPE
			SYNTAX DisplayString (SIZE (0..80))
			MAX-ACCESS read-only
			STATUS current
			DESCRIPTION
				"A user-friendly string that identifies the object that points
				to this object-tracker. E.g. 'Interface FastEthernet 10/2'.
				The string is equivalent to the one displayed when issuing
				the 'show track detail' CLI command."
			::= { avstrTrackerPtrsEntry 3 }
		
		-- 1.3.6.1.4.1.6889.2.6.2.1.2.6.1.4
		avstrTrackerPtrsType OBJECT-TYPE
			SYNTAX INTEGER
				{
				none(1),
				trackerList(2),
				ifIndex(3),
				isakmpPeer(4),
				ipStaticRoute(5),
				ipPbrNhListEntry(6)
				}
			MAX-ACCESS read-only
			STATUS current
			DESCRIPTION
				"This column together with the next column - 
				avstrTrackerPtrsValue uniquely identify the object pointing
				to this object-tracker, in a machine-friendly manner.
				This column provides the semantics for interpreting
				the contents of the next column - avstrTrackerPtrsValue:
				none(1)    - next column is N/A
				trackerList(2) - next column is taken from avstrTrackerId
				                 of the object-tracker list that points to 
				                 this object-tracker.
				ifIndex(3) - next column is InterfaceIndex TC (IF-MIB)
				isakmpPeer(4) - next column is avipsIsakmpPeerIdType followed
				                by avipsIsakmpPeerId (AVAYA-IPSEC-MIB).
				ipStaticRoute(5) - next column is the following OIDs in the
				                   following order: {ipCidrRouteStaticDest, 
				                   ipCidrRouteStaticMask, 
				                   ipCidrRouteStaticIfIndex, 
				                   ipCidrRouteStaticNextHop,
				                   ipCidrRouteStaticPreference} (CROUTE-MIB).
				ipPbrNhListEntry(6) - next column is the following OIDs in 
				                      the following order:
				                      {nextHopListIndex, nextHopIndex} 
				                      (CROUTE-MIB).
				"
			::= { avstrTrackerPtrsEntry 4 }
		
		-- 1.3.6.1.4.1.6889.2.6.2.1.2.6.1.5
		avstrTrackerPtrsValue OBJECT-TYPE
			SYNTAX OCTET STRING
			MAX-ACCESS read-only
			STATUS current
			DESCRIPTION
				"This column together with the previous column - 
				avstrTrackerPtrsType uniquely identify the object pointing
				to this object-tracker, in a machine-friendly manner.
				See description of avstrTrackerPtrsType for more details."
			::= { avstrTrackerPtrsEntry 5 }
		
		-- 1.3.6.1.4.1.6889.2.6.2.2
		avstrMIBNotificationPrefix OBJECT IDENTIFIER ::= { avayaSaaTrackMib 2 }
		
		-- 1.3.6.1.4.1.6889.2.6.2.2.0
		avstrMIBNotifications OBJECT IDENTIFIER ::= { avstrMIBNotificationPrefix 0 }
		
		-- 1.3.6.1.4.1.6889.2.6.2.2.0.1
		avstrTrackerOperStateChangeNotification NOTIFICATION-TYPE
			OBJECTS { avstrTrackerOperState, avstrTrackerDescription }
			STATUS current
			DESCRIPTION 
				"This notification is sent whenever a state transition for 
				an object-tracker occurs, i.e. whenever avstrTrackerOperState
				changes."
			::= { avstrMIBNotifications 1 }
		
		-- 1.3.6.1.4.1.6889.2.6.2.3
		avstrMIBConformance OBJECT IDENTIFIER ::= { avayaSaaTrackMib 3 }
		
		-- 1.3.6.1.4.1.6889.2.6.2.3.1
		avstrMIBGroups OBJECT IDENTIFIER ::= { avstrMIBConformance 1 }
		
		-- 1.3.6.1.4.1.6889.2.6.2.3.1.1
		avstrRtrConfigGroup OBJECT-GROUP
			OBJECTS { avstrRtrType, avstrRtrFrequencyMs, avstrRtrWaitIntervalMs, avstrRtrFailRetries, avstrRtrSuccessRetries, 
				avstrRtrProbeDscp, avstrRtrProbeSrcIpAddr, avstrRtrProbeNextHopIf, avstrRtrProbeNextHopMac, avstrRtrSchedule, 
				avstrRtrDestPort, avstrRtrIfKpaliveBypass, avstrRtrProbeNextHopIp, avstrRtrRowStatus, avstrRtrDestIp
				 }
			STATUS current
			DESCRIPTION 
				"This group consists of all the SAA configuration items."
			::= { avstrMIBGroups 1 }
		
		-- 1.3.6.1.4.1.6889.2.6.2.3.1.2
		avstrRtrMonitoringGroup OBJECT-GROUP
			OBJECTS { avstrRtrOperState, avstrRtrOperStateLastChange }
			STATUS current
			DESCRIPTION 
				"This group consists of all the SAA monitoring items."
			::= { avstrMIBGroups 2 }
		
		-- 1.3.6.1.4.1.6889.2.6.2.3.1.3
		avstrTrackerConfigGroup OBJECT-GROUP
			OBJECTS { avstrTrackerType, avstrTrackerRtrId, avstrTrackerListType, avstrTrackerRowStatus, avstrTrackerListObjsRowStatus, 
				avstrTrackerListObjsReverseState, avstrTrackerListThresholdUp, avstrTrackerDescription, avstrTrackerListThresholdDown }
			STATUS current
			DESCRIPTION 
				"This group consists of all the Object Tracking configuration 
				items."
			::= { avstrMIBGroups 3 }
		
		-- 1.3.6.1.4.1.6889.2.6.2.3.1.4
		avstrTrackerMonitoringGroup OBJECT-GROUP
			OBJECTS { avstrTrackerOperState, avstrTrackerOperStateLastChange, avstrTrackerPtrsDescription, avstrTrackerPtrsType, avstrTrackerPtrsValue
				 }
			STATUS current
			DESCRIPTION 
				"This group consists of all the Object Tracking monitoring
				items."
			::= { avstrMIBGroups 4 }
		
		-- 1.3.6.1.4.1.6889.2.6.2.3.2
		avstrMIBCompliances OBJECT IDENTIFIER ::= { avstrMIBConformance 2 }
		
		-- 1.3.6.1.4.1.6889.2.6.2.3.2.1
		avstrMIBCompliance MODULE-COMPLIANCE
			STATUS current
			DESCRIPTION 
				"The compliance statement for SNMP entities of
				the SAA and Object Tracking MIB."
			MODULE -- this module
				MANDATORY-GROUPS { avstrRtrConfigGroup, avstrTrackerConfigGroup, avstrRtrMonitoringGroup, avstrTrackerMonitoringGroup }
			::= { avstrMIBCompliances 1 }
		
	
	END

--
-- AVAYA-SAA-TRACK-MIB.my
--
