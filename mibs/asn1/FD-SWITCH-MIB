--
-- FD-SWITCH-MIB.my
-- MIB generated by MG-SOFT Visual MIB Builder Version 3.0 Build 253
-- Wednesday, June 15, 2011 at 18:06:26
--

	FD-SWITCH-MIB DEFINITIONS ::= BEGIN
 
		IMPORTS
			epon			
				FROM EPON-EOC-MIB			
			OBJECT-GROUP, MODULE-COMPLIANCE			
				FROM SNMPv2-CONF			
			IpAddress, Integer32, Unsigned32, OBJECT-TYPE, MODULE-IDENTITY			
				FROM SNMPv2-SMI			
			DisplayString, RowStatus, MacAddress, TEXTUAL-CONVENTION			
				FROM SNMPv2-TC;
	
	
--  May 27, 2010 at 10:56 GMT
		coreSwitch MODULE-IDENTITY 
			LAST-UPDATED "201005271056Z"		-- May 27, 2010 at 10:56 GMT
			ORGANIZATION 
				"epon eoc factory."
			CONTACT-INFO 
				""
			DESCRIPTION 
				"core switch mib module"
			::= { epon 2 }
		
	
--
-- Textual conventions
--
	
--  Textual conventions
-- 
		SniPortList ::= TEXTUAL-CONVENTION
			STATUS current
			DESCRIPTION 
				"Description."
			SYNTAX INTEGER
				{
				ge1(1),
				ge2(2),
				ge3(3),
				ge4(4),
				ge5(5),
				ge6(6),
				ge7(7),
				ge8(8)
				}
			
		SwPortList ::= TEXTUAL-CONVENTION
			STATUS current
			DESCRIPTION 
				"Description."
			SYNTAX INTEGER
				{
				ge1(1),
				ge2(2),
				ge3(3),
				ge4(4),
				ge5(5),
				ge6(6),
				ge7(7),
				ge8(8),
				ge9(9),
				ge10(10),
				ge11(11),
				ge12(12),
				ge13(13),
				ge14(14),
				ge15(15),
				ge16(16)
				}
			
		OperSwitch ::= TEXTUAL-CONVENTION
			STATUS current
			DESCRIPTION 
				"Device function operation switch type"
			SYNTAX INTEGER
				{
				enable(1),
				disable(2)
				}
			
		PortList ::= TEXTUAL-CONVENTION
			STATUS current
			DESCRIPTION 
				"Each octet within this value specifies a set of eight
				ports, with the first octet specifying ports 1 through
				8, the second octet specifying ports 9 through 16, etc.
				Within each octet, the most significant bit represents
				the lowest numbered port, and the least significant bit
				represents the highest numbered port.  Thus, each port
				of the bridge is represented by a single bit within the
				value of this object.  If that bit has a value of '1'
				then that port is included in the set of ports; the port
				is not included if its bit has a value of '0'."
			SYNTAX OCTET STRING
			
		DeviceStatus ::= TEXTUAL-CONVENTION
			STATUS current
			DESCRIPTION 
				"Device work status type. One device or dummy device may
				have following five work status:
				notPresent(1): the device is not present (not installed)
				offline(2):the device is present,but can not be communicated (or failed to get its info)
				online(3):the device is present and can be communicated
				normal(4):the device is online and work well
				abnormal(5): the device is online but work abnormal for some reason"
			SYNTAX INTEGER
				{
				notPresent(1),
				offline(2),
				online(3),
				normal(4),
				abnormal(5)
				}
			
	
--
-- Node definitions
--
	
--  Node definitions
-- 
		-- 1.3.6.1.4.1.34592.1.3.2.1
		switchConfig OBJECT IDENTIFIER ::= { coreSwitch 1 }
		
		-- 1.3.6.1.4.1.34592.1.3.2.1.1
		switchMode OBJECT-TYPE
			SYNTAX INTEGER
				{
				sniDestinated(1),
				transparent(2),
				normal(3)
				}
			MAX-ACCESS read-write
			STATUS current
			DESCRIPTION
				"The work mode of the core switch, now it can work in following
				three modes:
				sniDestinated: SNI port is specified,all internal port (connected with OLT LNP port)
				               exchange traffic with the only one specified SNI port, all other SNI
				               port is not in use in this mode.
				               When set to this mode, the ONUs registered on different PON port(OLT)
				               can not communicate each other
				transparent:   Each SNI port corresponding to one PON port, and the port pairs are
				               isolate each other
				normal:        lay2 switch mode "
			::= { switchConfig 1 }
		
		-- 1.3.6.1.4.1.34592.1.3.2.1.2
		destinedSNIPort OBJECT-TYPE
			SYNTAX SniPortList
			MAX-ACCESS read-write
			STATUS current
			DESCRIPTION
				" "
			::= { switchConfig 2 }
		
		-- 1.3.6.1.4.1.34592.1.3.2.2
		inBandInterface OBJECT IDENTIFIER ::= { coreSwitch 2 }
		
		-- 1.3.6.1.4.1.34592.1.3.2.2.1
		netInterfaceTable OBJECT-TYPE
			SYNTAX SEQUENCE OF NetInterfaceEntry
			MAX-ACCESS not-accessible
			STATUS current
			DESCRIPTION
				" "
			::= { inBandInterface 1 }
		
		-- 1.3.6.1.4.1.34592.1.3.2.2.1.1
		netInterfaceEntry OBJECT-TYPE
			SYNTAX NetInterfaceEntry
			MAX-ACCESS not-accessible
			STATUS current
			DESCRIPTION
				" "
			INDEX { ifIndex }
			::= { netInterfaceTable 1 }
		
		NetInterfaceEntry ::=
			SEQUENCE { 
				ifIndex
					Integer32,
				ifName
					DisplayString,
				ifIpAddr
					IpAddress,
				ifNetMask
					IpAddress,
				ifDefautGateway
					IpAddress,
				ifVlan
					Integer32,
				ifShutDown
					INTEGER,
				ifStatus
					INTEGER
			 }

		-- 1.3.6.1.4.1.34592.1.3.2.2.1.1.1
		ifIndex OBJECT-TYPE
			SYNTAX Integer32 (1..8)
			MAX-ACCESS not-accessible
			STATUS current
			DESCRIPTION
				" "
			::= { netInterfaceEntry 1 }
		
		-- 1.3.6.1.4.1.34592.1.3.2.2.1.1.2
		ifName OBJECT-TYPE
			SYNTAX DisplayString
			MAX-ACCESS read-only
			STATUS current
			DESCRIPTION
				" "
			::= { netInterfaceEntry 2 }
		
		-- 1.3.6.1.4.1.34592.1.3.2.2.1.1.3
		ifIpAddr OBJECT-TYPE
			SYNTAX IpAddress
			MAX-ACCESS read-write
			STATUS current
			DESCRIPTION
				" "
			::= { netInterfaceEntry 3 }
		
		-- 1.3.6.1.4.1.34592.1.3.2.2.1.1.4
		ifNetMask OBJECT-TYPE
			SYNTAX IpAddress
			MAX-ACCESS read-write
			STATUS current
			DESCRIPTION
				" "
			::= { netInterfaceEntry 4 }
		
		-- 1.3.6.1.4.1.34592.1.3.2.2.1.1.5
		ifDefautGateway OBJECT-TYPE
			SYNTAX IpAddress
			MAX-ACCESS read-write
			STATUS current
			DESCRIPTION
				" "
			::= { netInterfaceEntry 5 }
		
		-- 1.3.6.1.4.1.34592.1.3.2.2.1.1.6
		ifVlan OBJECT-TYPE
			SYNTAX Integer32 (1..4094)
			MAX-ACCESS read-write
			STATUS current
			DESCRIPTION
				" "
			::= { netInterfaceEntry 6 }
		
		-- 1.3.6.1.4.1.34592.1.3.2.2.1.1.7
		ifShutDown OBJECT-TYPE
			SYNTAX INTEGER
				{
				operational(1),
				shutdown(2)
				}
			MAX-ACCESS read-write
			STATUS current
			DESCRIPTION
				" "
			::= { netInterfaceEntry 7 }
		
		-- 1.3.6.1.4.1.34592.1.3.2.2.1.1.8
		ifStatus OBJECT-TYPE
			SYNTAX INTEGER
				{
				down(1),
				up(2)
				}
			MAX-ACCESS read-only
			STATUS current
			DESCRIPTION
				" "
			::= { netInterfaceEntry 8 }
		
		-- 1.3.6.1.4.1.34592.1.3.2.3
		switchPort OBJECT IDENTIFIER ::= { coreSwitch 3 }
		
		-- 1.3.6.1.4.1.34592.1.3.2.3.1
		swPortStatusTable OBJECT-TYPE
			SYNTAX SEQUENCE OF SwPortStatusEntry
			MAX-ACCESS not-accessible
			STATUS current
			DESCRIPTION
				" "
			::= { switchPort 1 }
		
		-- 1.3.6.1.4.1.34592.1.3.2.3.1.1
		swPortStatusEntry OBJECT-TYPE
			SYNTAX SwPortStatusEntry
			MAX-ACCESS not-accessible
			STATUS current
			DESCRIPTION
				" "
			INDEX { swSniPortId }
			::= { swPortStatusTable 1 }
		
		SwPortStatusEntry ::=
			SEQUENCE { 
				swSniPortId
					SniPortList,
				sfpPlugStauts
					INTEGER,
				trsPower
					Integer32,
				resPower
					Integer32,
				swPortLinkState
					INTEGER,
				swPortProtStatus
					INTEGER,
				swPortWorkSpd
					INTEGER,
				swPortWorkDup
					INTEGER,
				swPortWorkFlowCtr
					INTEGER
			 }

		-- 1.3.6.1.4.1.34592.1.3.2.3.1.1.1
		swSniPortId OBJECT-TYPE
			SYNTAX SniPortList
			MAX-ACCESS not-accessible
			STATUS current
			DESCRIPTION
				"Description."
			::= { swPortStatusEntry 1 }
		
		-- 1.3.6.1.4.1.34592.1.3.2.3.1.1.2
		sfpPlugStauts OBJECT-TYPE
			SYNTAX INTEGER
				{
				plugIn(1),
				plugOut(2)
				}
			MAX-ACCESS read-only
			STATUS current
			DESCRIPTION
				" "
			::= { swPortStatusEntry 2 }
		
		-- 1.3.6.1.4.1.34592.1.3.2.3.1.1.3
		trsPower OBJECT-TYPE
			SYNTAX Integer32
			MAX-ACCESS read-only
			STATUS current
			DESCRIPTION
				" "
			::= { swPortStatusEntry 3 }
		
		-- 1.3.6.1.4.1.34592.1.3.2.3.1.1.4
		resPower OBJECT-TYPE
			SYNTAX Integer32
			MAX-ACCESS read-only
			STATUS current
			DESCRIPTION
				" "
			::= { swPortStatusEntry 4 }
		
		-- 1.3.6.1.4.1.34592.1.3.2.3.1.1.5
		swPortLinkState OBJECT-TYPE
			SYNTAX INTEGER
				{
				linkUp(1),
				linkDown(2)
				}
			MAX-ACCESS read-only
			STATUS current
			DESCRIPTION
				" "
			::= { swPortStatusEntry 5 }
		
		-- 1.3.6.1.4.1.34592.1.3.2.3.1.1.6
		swPortProtStatus OBJECT-TYPE
			SYNTAX INTEGER
				{
				linkUp(1),
				linkDown(2)
				}
			MAX-ACCESS read-only
			STATUS current
			DESCRIPTION
				" "
			::= { swPortStatusEntry 6 }
		
		-- 1.3.6.1.4.1.34592.1.3.2.3.1.1.7
		swPortWorkSpd OBJECT-TYPE
			SYNTAX INTEGER
				{
				mbps10(1),
				mbps100(2),
				mbps1G(3)
				}
			MAX-ACCESS read-only
			STATUS current
			DESCRIPTION
				" "
			::= { swPortStatusEntry 7 }
		
		-- 1.3.6.1.4.1.34592.1.3.2.3.1.1.8
		swPortWorkDup OBJECT-TYPE
			SYNTAX INTEGER
				{
				fullDup(1),
				halfDup(2)
				}
			MAX-ACCESS read-only
			STATUS current
			DESCRIPTION
				" "
			::= { swPortStatusEntry 8 }
		
		-- 1.3.6.1.4.1.34592.1.3.2.3.1.1.9
		swPortWorkFlowCtr OBJECT-TYPE
			SYNTAX INTEGER
				{
				on(1),
				off(2)
				}
			MAX-ACCESS read-only
			STATUS current
			DESCRIPTION
				" "
			::= { swPortStatusEntry 9 }
		
		-- 1.3.6.1.4.1.34592.1.3.2.3.2
		swPortCfgTable OBJECT-TYPE
			SYNTAX SEQUENCE OF SwPortCfgEntry
			MAX-ACCESS not-accessible
			STATUS current
			DESCRIPTION
				" "
			::= { switchPort 2 }
		
		-- 1.3.6.1.4.1.34592.1.3.2.3.2.1
		swPortCfgEntry OBJECT-TYPE
			SYNTAX SwPortCfgEntry
			MAX-ACCESS not-accessible
			STATUS current
			DESCRIPTION
				" "
			INDEX { swPortId }
			::= { swPortCfgTable 1 }
		
		SwPortCfgEntry ::=
			SEQUENCE { 
				swPortId
					SwPortList,
				sfpModeCfg
					INTEGER,
				swPortCfgSpd
					INTEGER,
				swPortCfgDup
					INTEGER,
				swPortRstAuto
					INTEGER,
				swPortFlowCtl
					INTEGER,
				swPortDftPri
					Integer32,
				swPortDftVid
					Integer32,
				swPortForceLinkDown
					INTEGER,
				swPortEnable
					OperSwitch,
				swPortIngressFilter
					OperSwitch,
				swPortPermitFrameType
					INTEGER,
				swPortNestVlanEnable
					OperSwitch,
				swPortProtVlan
					OperSwitch,
				swPortBroadCastRateCtl
					OperSwitch,
				swPortMultiCastRateCtl
					OperSwitch,
				swPortUnkUcCastRateCtl
					OperSwitch,
				swPortBroadCastRate
					Integer32
			 }

		-- 1.3.6.1.4.1.34592.1.3.2.3.2.1.2
		swPortId OBJECT-TYPE
			SYNTAX SwPortList
			MAX-ACCESS not-accessible
			STATUS current
			DESCRIPTION
				" "
			::= { swPortCfgEntry 2 }
		
		-- 1.3.6.1.4.1.34592.1.3.2.3.2.1.3
		sfpModeCfg OBJECT-TYPE
			SYNTAX INTEGER
				{
				copper(1),
				fiber(2)
				}
			MAX-ACCESS read-write
			STATUS current
			DESCRIPTION
				"this object is only effective when the port is SNI(ge1~ge8)"
			::= { swPortCfgEntry 3 }
		
		-- 1.3.6.1.4.1.34592.1.3.2.3.2.1.4
		swPortCfgSpd OBJECT-TYPE
			SYNTAX INTEGER
				{
				mbps10(1),
				mbps100(2),
				mbps1G(3),
				mbps10G(4),
				auto(5)
				}
			MAX-ACCESS read-write
			STATUS current
			DESCRIPTION
				" "
			::= { swPortCfgEntry 4 }
		
		-- 1.3.6.1.4.1.34592.1.3.2.3.2.1.5
		swPortCfgDup OBJECT-TYPE
			SYNTAX INTEGER
				{
				full(1),
				half(2),
				auto(3)
				}
			MAX-ACCESS read-write
			STATUS current
			DESCRIPTION
				" "
			::= { swPortCfgEntry 5 }
		
		-- 1.3.6.1.4.1.34592.1.3.2.3.2.1.6
		swPortRstAuto OBJECT-TYPE
			SYNTAX INTEGER { restart(1) }
			MAX-ACCESS read-write
			STATUS current
			DESCRIPTION
				" "
			::= { swPortCfgEntry 6 }
		
		-- 1.3.6.1.4.1.34592.1.3.2.3.2.1.7
		swPortFlowCtl OBJECT-TYPE
			SYNTAX INTEGER
				{
				enable(1),
				disable(2),
				auto(3)
				}
			MAX-ACCESS read-write
			STATUS current
			DESCRIPTION
				" "
			::= { swPortCfgEntry 7 }
		
		-- 1.3.6.1.4.1.34592.1.3.2.3.2.1.8
		swPortDftPri OBJECT-TYPE
			SYNTAX Integer32 (0..7)
			MAX-ACCESS read-write
			STATUS current
			DESCRIPTION
				" "
			::= { swPortCfgEntry 8 }
		
		-- 1.3.6.1.4.1.34592.1.3.2.3.2.1.9
		swPortDftVid OBJECT-TYPE
			SYNTAX Integer32 (1..4094)
			MAX-ACCESS read-write
			STATUS current
			DESCRIPTION
				" "
			::= { swPortCfgEntry 9 }
		
		-- 1.3.6.1.4.1.34592.1.3.2.3.2.1.10
		swPortForceLinkDown OBJECT-TYPE
			SYNTAX INTEGER { forceDown(1) }
			MAX-ACCESS read-write
			STATUS current
			DESCRIPTION
				" "
			::= { swPortCfgEntry 10 }
		
		-- 1.3.6.1.4.1.34592.1.3.2.3.2.1.11
		swPortEnable OBJECT-TYPE
			SYNTAX OperSwitch
			MAX-ACCESS read-write
			STATUS current
			DESCRIPTION
				" "
			::= { swPortCfgEntry 11 }
		
		-- 1.3.6.1.4.1.34592.1.3.2.3.2.1.12
		swPortIngressFilter OBJECT-TYPE
			SYNTAX OperSwitch
			MAX-ACCESS read-write
			STATUS current
			DESCRIPTION
				" "
			::= { swPortCfgEntry 12 }
		
		-- 1.3.6.1.4.1.34592.1.3.2.3.2.1.13
		swPortPermitFrameType OBJECT-TYPE
			SYNTAX INTEGER
				{
				tagged(1),
				allType(2),
				unTagged(3)
				}
			MAX-ACCESS read-write
			STATUS current
			DESCRIPTION
				" "
			::= { swPortCfgEntry 13 }
		
		-- 1.3.6.1.4.1.34592.1.3.2.3.2.1.14
		swPortNestVlanEnable OBJECT-TYPE
			SYNTAX OperSwitch
			MAX-ACCESS read-write
			STATUS current
			DESCRIPTION
				" "
			::= { swPortCfgEntry 14 }
		
		-- 1.3.6.1.4.1.34592.1.3.2.3.2.1.15
		swPortProtVlan OBJECT-TYPE
			SYNTAX OperSwitch
			MAX-ACCESS read-write
			STATUS current
			DESCRIPTION
				" "
			::= { swPortCfgEntry 15 }
		
		-- 1.3.6.1.4.1.34592.1.3.2.3.2.1.16
		swPortBroadCastRateCtl OBJECT-TYPE
			SYNTAX OperSwitch
			MAX-ACCESS read-write
			STATUS current
			DESCRIPTION
				" "
			::= { swPortCfgEntry 16 }
		
		-- 1.3.6.1.4.1.34592.1.3.2.3.2.1.17
		swPortMultiCastRateCtl OBJECT-TYPE
			SYNTAX OperSwitch
			MAX-ACCESS read-write
			STATUS current
			DESCRIPTION
				"Description."
			::= { swPortCfgEntry 17 }
		
		-- 1.3.6.1.4.1.34592.1.3.2.3.2.1.18
		swPortUnkUcCastRateCtl OBJECT-TYPE
			SYNTAX OperSwitch
			MAX-ACCESS read-write
			STATUS current
			DESCRIPTION
				"Description."
			::= { swPortCfgEntry 18 }
		
		-- 1.3.6.1.4.1.34592.1.3.2.3.2.1.19
		swPortBroadCastRate OBJECT-TYPE
			SYNTAX Integer32 (0..1000000)
			MAX-ACCESS read-write
			STATUS current
			DESCRIPTION
				" "
			::= { swPortCfgEntry 19 }
		
		-- 1.3.6.1.4.1.34592.1.3.2.3.3
		swPortRateCtlMode OBJECT-TYPE
			SYNTAX INTEGER
				{
				kBps(1),
				kpps(2)
				}
			MAX-ACCESS read-write
			STATUS current
			DESCRIPTION
				"Description."
			::= { switchPort 3 }
		
		-- 1.3.6.1.4.1.34592.1.3.2.4
		vlan OBJECT IDENTIFIER ::= { coreSwitch 4 }
		
		-- 1.3.6.1.4.1.34592.1.3.2.4.1
		proSupportedTable OBJECT-TYPE
			SYNTAX SEQUENCE OF ProSupportedEntry
			MAX-ACCESS not-accessible
			STATUS current
			DESCRIPTION
				" "
			::= { vlan 1 }
		
		-- 1.3.6.1.4.1.34592.1.3.2.4.1.1
		proSupportedEntry OBJECT-TYPE
			SYNTAX ProSupportedEntry
			MAX-ACCESS not-accessible
			STATUS current
			DESCRIPTION
				" "
			INDEX { proSupportedId }
			::= { proSupportedTable 1 }
		
		ProSupportedEntry ::=
			SEQUENCE { 
				proSupportedId
					INTEGER,
				proSupported
					Integer32,
				proSupportedRowStatus
					RowStatus
			 }

		-- 1.3.6.1.4.1.34592.1.3.2.4.1.1.1
		proSupportedId OBJECT-TYPE
			SYNTAX INTEGER (1..8)
			MAX-ACCESS not-accessible
			STATUS current
			DESCRIPTION
				"Description."
			::= { proSupportedEntry 1 }
		
		-- 1.3.6.1.4.1.34592.1.3.2.4.1.1.2
		proSupported OBJECT-TYPE
			SYNTAX Integer32 (1500..65535)
			MAX-ACCESS read-write
			STATUS current
			DESCRIPTION
				" "
			::= { proSupportedEntry 2 }
		
		-- 1.3.6.1.4.1.34592.1.3.2.4.1.1.3
		proSupportedRowStatus OBJECT-TYPE
			SYNTAX RowStatus
			MAX-ACCESS read-create
			STATUS current
			DESCRIPTION
				" "
			::= { proSupportedEntry 3 }
		
		-- 1.3.6.1.4.1.34592.1.3.2.4.2
		proVlanTable OBJECT-TYPE
			SYNTAX SEQUENCE OF ProVlanEntry
			MAX-ACCESS not-accessible
			STATUS current
			DESCRIPTION
				" "
			::= { vlan 2 }
		
		-- 1.3.6.1.4.1.34592.1.3.2.4.2.1
		proVlanEntry OBJECT-TYPE
			SYNTAX ProVlanEntry
			MAX-ACCESS not-accessible
			STATUS current
			DESCRIPTION
				" "
			INDEX { swPortId, proVlanIdx }
			::= { proVlanTable 1 }
		
		ProVlanEntry ::=
			SEQUENCE { 
				proVlanIdx
					INTEGER,
				proVlanProtocol
					Integer32,
				proVlanId
					Integer32,
				proVlanRowStatus
					RowStatus
			 }

		-- 1.3.6.1.4.1.34592.1.3.2.4.2.1.1
		proVlanIdx OBJECT-TYPE
			SYNTAX INTEGER (1..8)
			MAX-ACCESS not-accessible
			STATUS current
			DESCRIPTION
				"Description."
			::= { proVlanEntry 1 }
		
		-- 1.3.6.1.4.1.34592.1.3.2.4.2.1.2
		proVlanProtocol OBJECT-TYPE
			SYNTAX Integer32 (1500..65535)
			MAX-ACCESS read-write
			STATUS current
			DESCRIPTION
				"Description."
			::= { proVlanEntry 2 }
		
		-- 1.3.6.1.4.1.34592.1.3.2.4.2.1.3
		proVlanId OBJECT-TYPE
			SYNTAX Integer32 (1..4094)
			MAX-ACCESS read-write
			STATUS current
			DESCRIPTION
				" "
			::= { proVlanEntry 3 }
		
		-- 1.3.6.1.4.1.34592.1.3.2.4.2.1.4
		proVlanRowStatus OBJECT-TYPE
			SYNTAX RowStatus
			MAX-ACCESS read-create
			STATUS current
			DESCRIPTION
				" "
			::= { proVlanEntry 4 }
		
		-- 1.3.6.1.4.1.34592.1.3.2.4.3
		qVlanTable OBJECT-TYPE
			SYNTAX SEQUENCE OF QVlanEntry
			MAX-ACCESS not-accessible
			STATUS current
			DESCRIPTION
				"Description."
			::= { vlan 3 }
		
		-- 1.3.6.1.4.1.34592.1.3.2.4.3.1
		qVlanEntry OBJECT-TYPE
			SYNTAX QVlanEntry
			MAX-ACCESS not-accessible
			STATUS current
			DESCRIPTION
				"Description."
			INDEX { qVlanId }
			::= { qVlanTable 1 }
		
		QVlanEntry ::=
			SEQUENCE { 
				qVlanId
					Unsigned32,
				qVlanStaticEgressPorts
					PortList,
				qVlanStaticUntaggedPorts
					PortList,
				qVlanRowStatus
					RowStatus
			 }

		-- 1.3.6.1.4.1.34592.1.3.2.4.3.1.1
		qVlanId OBJECT-TYPE
			SYNTAX Unsigned32
			MAX-ACCESS not-accessible
			STATUS current
			DESCRIPTION
				"Description."
			::= { qVlanEntry 1 }
		
		-- 1.3.6.1.4.1.34592.1.3.2.4.3.1.2
		qVlanStaticEgressPorts OBJECT-TYPE
			SYNTAX PortList
			MAX-ACCESS read-write
			STATUS current
			DESCRIPTION
				"first octet specifying ports 1 through 8, the second octet specifying ports 9 through 16."
			::= { qVlanEntry 2 }
		
		-- 1.3.6.1.4.1.34592.1.3.2.4.3.1.3
		qVlanStaticUntaggedPorts OBJECT-TYPE
			SYNTAX PortList
			MAX-ACCESS read-write
			STATUS current
			DESCRIPTION
				"first octet specifying ports 1 through 8, the second octet specifying ports 9 through 16."
			::= { qVlanEntry 3 }
		
		-- 1.3.6.1.4.1.34592.1.3.2.4.3.1.4
		qVlanRowStatus OBJECT-TYPE
			SYNTAX RowStatus
			MAX-ACCESS read-write
			STATUS current
			DESCRIPTION
				"Description."
			::= { qVlanEntry 4 }
		
		-- 1.3.6.1.4.1.34592.1.3.2.4.4
		qVlanCfg OBJECT IDENTIFIER ::= { vlan 4 }
		
		-- 1.3.6.1.4.1.34592.1.3.2.4.4.1
		vlanMode OBJECT-TYPE
			SYNTAX OperSwitch
			MAX-ACCESS read-write
			STATUS current
			DESCRIPTION
				"vlan mode :enable (vlan aware) or disable (vlan unaware)."
			::= { qVlanCfg 1 }
		
		-- 1.3.6.1.4.1.34592.1.3.2.5
		trunk OBJECT IDENTIFIER ::= { coreSwitch 5 }
		
		-- 1.3.6.1.4.1.34592.1.3.2.5.1
		trunkConfig OBJECT IDENTIFIER ::= { trunk 1 }
		
		-- 1.3.6.1.4.1.34592.1.3.2.5.1.1
		trunkBlance OBJECT-TYPE
			SYNTAX INTEGER
				{
				balanceMac(1),
				balanceIp(2),
				balanceL4Port(3),
				balanceIpMac(4),
				balanceL4PortMac(5),
				balanceInL2If(6)
				}
			MAX-ACCESS read-write
			STATUS current
			DESCRIPTION
				" "
			::= { trunkConfig 1 }
		
		-- 1.3.6.1.4.1.34592.1.3.2.5.2
		trunkGroupTable OBJECT-TYPE
			SYNTAX SEQUENCE OF TrunkGroupEntry
			MAX-ACCESS not-accessible
			STATUS current
			DESCRIPTION
				" "
			::= { trunk 2 }
		
		-- 1.3.6.1.4.1.34592.1.3.2.5.2.1
		trunkGroupEntry OBJECT-TYPE
			SYNTAX TrunkGroupEntry
			MAX-ACCESS not-accessible
			STATUS current
			DESCRIPTION
				" "
			INDEX { trunkGroupId }
			::= { trunkGroupTable 1 }
		
		TrunkGroupEntry ::=
			SEQUENCE { 
				trunkGroupId
					Integer32,
				trunkGroupMembers
					PortList,
				trunkGroupRowStatus
					RowStatus
			 }

		-- 1.3.6.1.4.1.34592.1.3.2.5.2.1.1
		trunkGroupId OBJECT-TYPE
			SYNTAX Integer32 (1..8)
			MAX-ACCESS not-accessible
			STATUS current
			DESCRIPTION
				" "
			::= { trunkGroupEntry 1 }
		
		-- 1.3.6.1.4.1.34592.1.3.2.5.2.1.2
		trunkGroupMembers OBJECT-TYPE
			SYNTAX PortList
			MAX-ACCESS read-create
			STATUS current
			DESCRIPTION
				" "
			::= { trunkGroupEntry 2 }
		
		-- 1.3.6.1.4.1.34592.1.3.2.5.2.1.3
		trunkGroupRowStatus OBJECT-TYPE
			SYNTAX RowStatus
			MAX-ACCESS read-create
			STATUS current
			DESCRIPTION
				" "
			::= { trunkGroupEntry 3 }
		
		-- 1.3.6.1.4.1.34592.1.3.2.6
		rstp OBJECT IDENTIFIER ::= { coreSwitch 6 }
		
		-- 1.3.6.1.4.1.34592.1.3.2.6.1
		rstpConfig OBJECT IDENTIFIER ::= { rstp 1 }
		
		-- 1.3.6.1.4.1.34592.1.3.2.6.1.1
		rstpEnable OBJECT-TYPE
			SYNTAX OperSwitch
			MAX-ACCESS read-write
			STATUS current
			DESCRIPTION
				" "
			::= { rstpConfig 1 }
		
		-- 1.3.6.1.4.1.34592.1.3.2.6.1.2
		bridgePri OBJECT-TYPE
			SYNTAX INTEGER
				{
				p0(1),
				p4096(4096),
				p8192(8192),
				p12288(12288),
				p16384(16384),
				p20480(20480),
				p24576(24576),
				p28672(28672),
				p32768(32768),
				p36864(36864),
				p40960(40960),
				p45056(45056),
				p49152(49152),
				p53248(53248),
				p57344(57344),
				p61440(61440)
				}
			MAX-ACCESS read-write
			STATUS current
			DESCRIPTION
				" "
			::= { rstpConfig 2 }
		
		-- 1.3.6.1.4.1.34592.1.3.2.6.1.3
		bridgeMaxAge OBJECT-TYPE
			SYNTAX Integer32 (6..40)
			MAX-ACCESS read-write
			STATUS current
			DESCRIPTION
				" "
			::= { rstpConfig 3 }
		
		-- 1.3.6.1.4.1.34592.1.3.2.6.1.4
		bridgeForwardDelay OBJECT-TYPE
			SYNTAX Integer32 (4..30)
			MAX-ACCESS read-write
			STATUS current
			DESCRIPTION
				" "
			::= { rstpConfig 4 }
		
		-- 1.3.6.1.4.1.34592.1.3.2.6.1.5
		transmitHoldCount OBJECT-TYPE
			SYNTAX Integer32 (1..10)
			MAX-ACCESS read-write
			STATUS current
			DESCRIPTION
				" "
			::= { rstpConfig 5 }
		
		-- 1.3.6.1.4.1.34592.1.3.2.6.1.6
		bridgeIdAddr OBJECT-TYPE
			SYNTAX MacAddress
			MAX-ACCESS read-only
			STATUS current
			DESCRIPTION
				" "
			::= { rstpConfig 6 }
		
		-- 1.3.6.1.4.1.34592.1.3.2.6.1.7
		bridgeHelloTime OBJECT-TYPE
			SYNTAX Integer32
			MAX-ACCESS read-only
			STATUS current
			DESCRIPTION
				" "
			::= { rstpConfig 7 }
		
		-- 1.3.6.1.4.1.34592.1.3.2.6.1.8
		rootPri OBJECT-TYPE
			SYNTAX Integer32
			MAX-ACCESS read-only
			STATUS current
			DESCRIPTION
				" "
			::= { rstpConfig 8 }
		
		-- 1.3.6.1.4.1.34592.1.3.2.6.1.9
		rootAddr OBJECT-TYPE
			SYNTAX MacAddress
			MAX-ACCESS read-only
			STATUS current
			DESCRIPTION
				" "
			::= { rstpConfig 9 }
		
		-- 1.3.6.1.4.1.34592.1.3.2.6.1.10
		rootPathCost OBJECT-TYPE
			SYNTAX Integer32 (1..200000000)
			MAX-ACCESS read-only
			STATUS current
			DESCRIPTION
				" "
			::= { rstpConfig 10 }
		
		-- 1.3.6.1.4.1.34592.1.3.2.6.2
		rstpPortTable OBJECT-TYPE
			SYNTAX SEQUENCE OF RstpPortEntry
			MAX-ACCESS not-accessible
			STATUS current
			DESCRIPTION
				" "
			::= { rstp 2 }
		
		-- 1.3.6.1.4.1.34592.1.3.2.6.2.1
		rstpPortEntry OBJECT-TYPE
			SYNTAX RstpPortEntry
			MAX-ACCESS not-accessible
			STATUS current
			DESCRIPTION
				" "
			INDEX { swSniPortId }
			::= { rstpPortTable 1 }
		
		RstpPortEntry ::=
			SEQUENCE { 
				rstpMode
					INTEGER,
				rstpPri
					INTEGER,
				rstpPathCost
					Integer32,
				rstpMCheck
					OperSwitch,
				rstpEdgeConfig
					INTEGER,
				rstpOperEdge
					INTEGER,
				rstpP2PCfg
					INTEGER,
				rstpOperP2P
					INTEGER,
				rstpPortState
					INTEGER
			 }

		-- 1.3.6.1.4.1.34592.1.3.2.6.2.1.1
		rstpMode OBJECT-TYPE
			SYNTAX INTEGER
				{
				stp(1),
				rstp(2)
				}
			MAX-ACCESS read-only
			STATUS current
			DESCRIPTION
				" "
			::= { rstpPortEntry 1 }
		
		-- 1.3.6.1.4.1.34592.1.3.2.6.2.1.2
		rstpPri OBJECT-TYPE
			SYNTAX INTEGER
				{
				p0(1),
				p16(16),
				p32(32),
				p48(48),
				p64(64),
				p80(80),
				p96(96),
				p112(112),
				p128(128),
				p144(144),
				p160(160),
				p176(176),
				p192(192),
				p208(208),
				p224(224),
				p240(240)
				}
			MAX-ACCESS read-write
			STATUS current
			DESCRIPTION
				" "
			::= { rstpPortEntry 2 }
		
		-- 1.3.6.1.4.1.34592.1.3.2.6.2.1.3
		rstpPathCost OBJECT-TYPE
			SYNTAX Integer32 (1..200000000)
			MAX-ACCESS read-write
			STATUS current
			DESCRIPTION
				" "
			::= { rstpPortEntry 3 }
		
		-- 1.3.6.1.4.1.34592.1.3.2.6.2.1.4
		rstpMCheck OBJECT-TYPE
			SYNTAX OperSwitch
			MAX-ACCESS read-write
			STATUS current
			DESCRIPTION
				" "
			::= { rstpPortEntry 4 }
		
		-- 1.3.6.1.4.1.34592.1.3.2.6.2.1.5
		rstpEdgeConfig OBJECT-TYPE
			SYNTAX INTEGER
				{
				nonEdge(1),
				edge(2),
				auto(3)
				}
			MAX-ACCESS read-write
			STATUS current
			DESCRIPTION
				" "
			::= { rstpPortEntry 5 }
		
		-- 1.3.6.1.4.1.34592.1.3.2.6.2.1.6
		rstpOperEdge OBJECT-TYPE
			SYNTAX INTEGER
				{
				edge(1),
				nonEdge(2)
				}
			MAX-ACCESS read-only
			STATUS current
			DESCRIPTION
				" "
			::= { rstpPortEntry 6 }
		
		-- 1.3.6.1.4.1.34592.1.3.2.6.2.1.7
		rstpP2PCfg OBJECT-TYPE
			SYNTAX INTEGER
				{
				share(1),
				p2p(2),
				auto(3)
				}
			MAX-ACCESS read-write
			STATUS current
			DESCRIPTION
				" "
			::= { rstpPortEntry 7 }
		
		-- 1.3.6.1.4.1.34592.1.3.2.6.2.1.8
		rstpOperP2P OBJECT-TYPE
			SYNTAX INTEGER
				{
				share(1),
				p2p(2)
				}
			MAX-ACCESS read-only
			STATUS current
			DESCRIPTION
				" "
			::= { rstpPortEntry 8 }
		
		-- 1.3.6.1.4.1.34592.1.3.2.6.2.1.9
		rstpPortState OBJECT-TYPE
			SYNTAX INTEGER
				{
				linkdown(1),
				discarding(2),
				learning(3),
				forwarding(4)
				}
			MAX-ACCESS read-only
			STATUS current
			DESCRIPTION
				" "
			::= { rstpPortEntry 9 }
		
		-- 1.3.6.1.4.1.34592.1.3.2.7
		mirror OBJECT IDENTIFIER ::= { coreSwitch 7 }
		
		-- 1.3.6.1.4.1.34592.1.3.2.7.1
		destinationPort OBJECT-TYPE
			SYNTAX INTEGER
				{
				none(0),
				ge1(1),
				ge2(2),
				ge3(3),
				ge4(4),
				ge5(5),
				ge6(6),
				ge7(7),
				ge8(8)
				}
			MAX-ACCESS read-write
			STATUS current
			DESCRIPTION
				"a mirroring destination port, one of none & ge1~ge16, 0 means 'NONE'"
			::= { mirror 1 }
		
		-- 1.3.6.1.4.1.34592.1.3.2.7.2
		sourceIngressPorts OBJECT-TYPE
			SYNTAX PortList
			MAX-ACCESS read-write
			STATUS current
			DESCRIPTION
				"port bitmap: first octet specifying ports 1 through 8, the second octet specifying ports 9 through 16."
			::= { mirror 2 }
		
		-- 1.3.6.1.4.1.34592.1.3.2.7.3
		sourceEgressPorts OBJECT-TYPE
			SYNTAX PortList
			MAX-ACCESS read-write
			STATUS current
			DESCRIPTION
				"port bitmap: first octet specifying ports 1 through 8, the second octet specifying ports 9 through 16."
			::= { mirror 3 }
		
		-- 1.3.6.1.4.1.34592.1.3.2.7.4
		sourceVlan OBJECT-TYPE
			SYNTAX OCTET STRING (SIZE (2..18))
			MAX-ACCESS read-write
			STATUS current
			DESCRIPTION
				"first 2byte is the number of vlans, maxmun number is 8,format:
				    2byte         2byte   2byte         2byte
				-----------------------------------------------
				| vlanNum(N<=8) | vlan1 | vlan2 | ... | vlanN |
				-----------------------------------------------"
			::= { mirror 4 }
		
		-- 1.3.6.1.4.1.34592.1.3.2.7.5
		operation OBJECT-TYPE
			SYNTAX INTEGER
				{
				none(0),
				delete(1)
				}
			MAX-ACCESS read-write
			STATUS current
			DESCRIPTION
				"operation:
				delete:clear all the mirror data,disable mirroring function."
			::= { mirror 5 }
			
		-- 1.3.6.1.4.1.34592.1.3.2.8
		igmpsnooping OBJECT IDENTIFIER ::= { coreSwitch 8 }
		
		-- 1.3.6.1.4.1.34592.1.3.2.8.1
		igmpsnoopingAdmin OBJECT-TYPE
			SYNTAX INTEGER
				{
				enable(1),
				disable(2)
				}
			MAX-ACCESS read-write
			STATUS current
			DESCRIPTION
				"enable or disable igmp-snooping."
			::= { igmpsnooping 1 }	
					
		-- 1.3.6.1.4.1.34592.1.3.2.8.2
		igmpsnoopingRouterAgingTime OBJECT-TYPE
			SYNTAX INTEGER(1..1000)
			MAX-ACCESS read-write
			STATUS current
			DESCRIPTION
				"setting igmp-snooping router-port aging-time."
			::= { igmpsnooping 2 }	
			
		-- 1.3.6.1.4.1.34592.1.3.2.8.3
		igmpsnoopingHostAgingTime OBJECT-TYPE
			SYNTAX INTEGER(200..1000)
			MAX-ACCESS read-write
			STATUS current
			DESCRIPTION
				"setting igmp-snooping member port aging-time."
			::= { igmpsnooping 3 }
			
		-- 1.3.6.1.4.1.34592.1.3.2.8.4
		igmpsnoopingVlanData OBJECT-TYPE
			SYNTAX OCTET STRING
			MAX-ACCESS read-write
			STATUS current
			DESCRIPTION
				"igmpsnooping vlan data."
			::= { igmpsnooping 4 }
			
		-- 1.3.6.1.4.1.34592.1.3.2.8.5
		igmpsnoopingQueryProxy OBJECT-TYPE
			SYNTAX INTEGER
				{
				disable(0),
				enable(1)
				}
			MAX-ACCESS read-write
			STATUS current
			DESCRIPTION
				"setting igmp-snooping query proxy."
			::= { igmpsnooping 5 }
					
		-- 1.3.6.1.4.1.34592.1.3.2.10
		coreSwitchConformance OBJECT IDENTIFIER ::= { coreSwitch 10 }
		
		-- 1.3.6.1.4.1.34592.1.3.2.10.1
		coreSwitchGroups OBJECT IDENTIFIER ::= { coreSwitchConformance 1 }
		
		-- 1.3.6.1.4.1.34592.1.3.2.10.1.1
		inbandNetIfGroup OBJECT-GROUP
			OBJECTS { ifName, ifIpAddr, ifNetMask, ifDefautGateway, ifVlan, 
				ifShutDown, ifStatus }
			STATUS current
			DESCRIPTION 
				"A collection of objects providing inband network interface
				configuration"
			::= { coreSwitchGroups 1 }
		
		-- 1.3.6.1.4.1.34592.1.3.2.10.1.2
		switchCfgGroup OBJECT-GROUP
			OBJECTS { switchMode, destinedSNIPort }
			STATUS current
			DESCRIPTION 
				"A connection of objects providing basic switch configuration"
			::= { coreSwitchGroups 2 }
		
		-- 1.3.6.1.4.1.34592.1.3.2.10.1.3
		swPortManageGroup OBJECT-GROUP
			OBJECTS { sfpPlugStauts, trsPower, resPower, swPortLinkState, swPortProtStatus, 
				swPortWorkSpd, swPortWorkDup, swPortWorkFlowCtr, sfpModeCfg, swPortCfgSpd, 
				swPortCfgDup, swPortRstAuto, swPortFlowCtl, swPortDftPri, swPortDftVid, 
				swPortForceLinkDown, swPortEnable, swPortIngressFilter, swPortPermitFrameType, swPortNestVlanEnable, 
				swPortProtVlan, swPortBroadCastRateCtl, swPortBroadCastRate, swPortMultiCastRateCtl, swPortUnkUcCastRateCtl, 
				swPortRateCtlMode }
			STATUS current
			DESCRIPTION 
				"A collection of objects providing switch port configuration
				management"
			::= { coreSwitchGroups 3 }
		
		-- 1.3.6.1.4.1.34592.1.3.2.10.1.4
		swVlanGroups OBJECT-GROUP
			OBJECTS { proSupportedRowStatus, proVlanRowStatus, proSupported, proVlanProtocol, proVlanId, 
				qVlanStaticEgressPorts, qVlanStaticUntaggedPorts, qVlanRowStatus, vlanMode }
			STATUS current
			DESCRIPTION 
				"A collection of objects providing switch vlan configuration management"
			::= { coreSwitchGroups 4 }
		
		-- 1.3.6.1.4.1.34592.1.3.2.10.1.5
		swTrunkGroup OBJECT-GROUP
			OBJECTS { trunkBlance, trunkGroupMembers, trunkGroupRowStatus }
			STATUS current
			DESCRIPTION 
				"A collection of objects providing switch trunk management"
			::= { coreSwitchGroups 5 }
		
		-- 1.3.6.1.4.1.34592.1.3.2.10.1.6
		swRstpGroup OBJECT-GROUP
			OBJECTS { rstpEnable, bridgePri, bridgeMaxAge, bridgeForwardDelay, transmitHoldCount, 
				bridgeIdAddr, bridgeHelloTime, rootPri, rootAddr, rootPathCost, 
				rstpMode, rstpPri, rstpPathCost, rstpMCheck, rstpEdgeConfig, 
				rstpOperEdge, rstpP2PCfg, rstpOperP2P, rstpPortState }
			STATUS current
			DESCRIPTION 
				"A collection of objects providing switch rstp configuration managment"
			::= { coreSwitchGroups 6 }
		
		-- 1.3.6.1.4.1.34592.1.3.2.10.1.7
		mirrorGroup OBJECT-GROUP
			OBJECTS { destinationPort, sourceIngressPorts, sourceEgressPorts, sourceVlan, operation
				 }
			STATUS current
			DESCRIPTION 
				"Description."
			::= { coreSwitchGroups 7 }
		
		-- 1.3.6.1.4.1.34592.1.3.2.10.2
		coreSwitchCompliances OBJECT IDENTIFIER ::= { coreSwitchConformance 2 }
		
--   this module
-- this module
		-- 1.3.6.1.4.1.34592.1.3.2.10.2.1
		coreSwitchCompliance MODULE-COMPLIANCE
			STATUS current
			DESCRIPTION 
				"The compliance statement"
			MODULE -- this module
				MANDATORY-GROUPS { inbandNetIfGroup, switchCfgGroup, swPortManageGroup, swVlanGroups, swTrunkGroup, 
					swRstpGroup }
			::= { coreSwitchCompliances 1 }
		
	
	END

--
-- FD-SWITCH-MIB.my
--
