DLINK-3100-DELETEIMG-MIB DEFINITIONS ::= BEGIN

        IMPORTS
              rnd                                       FROM DLINK-3100-MIB
              OBJECT-TYPE, MODULE-IDENTITY              FROM SNMPv2-SMI
        ;

-- Declerations

        DELETEIMGName ::= TEXTUAL-CONVENTION
            STATUS  current
            DESCRIPTION
                "Specifies name of image to be deleted:
                 1- image_1.
                 2- image_2."
            SYNTAX  INTEGER {
                none(0),
                image1(1),
                image2(2)
                }

-- module

        rlDeleteImg MODULE-IDENTITY
            LAST-UPDATED "2007111800Z"
            ORGANIZATION "Dlink, Inc."
            CONTACT-INFO
                "www.dlink.com"
            DESCRIPTION
                " Dlink delete image MIB"
            REVISION "200711180000Z"
            DESCRIPTION
                    "Initial revision."
            ::={ rnd 142 }

        rlDeleteImgTable  OBJECT-TYPE
            SYNTAX     SEQUENCE OF RlDeleteImgEntry
            MAX-ACCESS not-accessible
            STATUS     current
            DESCRIPTION
                " Dlink's table for delete image "
            ::= {rlDeleteImg 1 }

        rlDeleteImgEntry  OBJECT-TYPE
            SYNTAX      RlDeleteImgEntry
            MAX-ACCESS  not-accessible
            STATUS      current
            DESCRIPTION
                " Entry in rlDeleteImgTable."
            INDEX    { rlDeleteImgKey }
            ::= {rlDeleteImgTable  1 }

        RlDeleteImgEntry ::= SEQUENCE {
            rlDeleteImgKey              INTEGER(1..1),
            rlDeleteImgUnit             INTEGER,
            rlDeleteImgName             DELETEIMGName
        }

        rlDeleteImgKey OBJECT-TYPE
            SYNTAX      INTEGER (1..1)
            MAX-ACCESS  not-accessible
            STATUS      current
            DESCRIPTION
                "Variable that specifies the key of the MIB's single entry"
            ::=  { rlDeleteImgEntry 1 }

        rlDeleteImgUnit OBJECT-TYPE
            SYNTAX      INTEGER
            MAX-ACCESS  read-write
            STATUS      current
            DESCRIPTION
                " Unit number for Dlink's delete image action MIB"
            ::=  { rlDeleteImgEntry 2 }

        rlDeleteImgName OBJECT-TYPE
            SYNTAX      DELETEIMGName
            MAX-ACCESS  read-write
            STATUS      current
            DESCRIPTION
                " Image name for Dlink's delete image action MIB"
            ::=  { rlDeleteImgEntry 3 }

END
