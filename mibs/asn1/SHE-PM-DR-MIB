--
-- she-pm-dr-mib.mib
-- MIB generated by MG-SOFT Visual MIB Builder Version 6.0  Build 88
-- Wednesday, September 17, 2008 at 13:51:05
--

-- Start of ClearCase branch-information of current release:
-- she-pmdr-mib.mib   /main/she_r2.8_grf/2
-- End of ClearCase branch-information.

	SHE-PM-DR-MIB DEFINITIONS ::= BEGIN
 
		IMPORTS
			she			
				FROM AN-MIB			
			SheControlStatusType			
				FROM SHE-TC-MIB			
			SnmpAdminString			
				FROM SNMP-FRAMEWORK-MIB			
			OBJECT-GROUP, MODULE-COMPLIANCE, NOTIFICATION-GROUP			
				FROM SNMPv2-CONF			
			TimeTicks, IpAddress, Unsigned32, OBJECT-TYPE, MODULE-IDENTITY, 
			NOTIFICATION-TYPE			
				FROM SNMPv2-SMI			
			TruthValue			
				FROM SNMPv2-TC;
	
	
-- ------------------------------------------------------------------
-- |||||||||||||||||| MIB for PM Data Retrieval||||||||||||||||||||||
-- ------------------------------------------------------------------
-- 
		shePmDrMib MODULE-IDENTITY 
			LAST-UPDATED "200809171100Z"		-- September 17, 2008 at 11:00 GMT
			ORGANIZATION 
				"Nokia Siemens Networks"
			CONTACT-INFO 
				"COO BBA
				Siemens Building in Beijing
				
				jie.shen@nsn.com
				##########################
				gerd.barchmann@nsn.com"
			DESCRIPTION 
				"The MIB module describes managed objects
				that support PM Data Retrieval (PM-DR) through FTP."
			REVISION "200507270930Z"		-- July 27, 2005 at 09:30 GMT
			DESCRIPTION 
				"Change the command to set shePmDrControlUploadEnabled to be
				long running command. Trap shePmDrControlResult was added.
				Three more values (wrongIpAddress, wrongUserPassword, and
				permissionDenied) were added to RequestResultType."
			REVISION "200803190948Z"		-- March 19, 2008 at 09:48 GMT
			DESCRIPTION 
				"Bring them to common SHE MIB package with R2.8."
			REVISION "200809171350Z"		-- September 17, 2008 at 13:50 GMT
			DESCRIPTION 
				"Correct some ranges."
			::= { she 30 }

		
	
--
-- Type definitions
--
	
		ShePmDrControlRequestType ::= INTEGER
			{
			noRequest(1),
			setUploadParameters(2)
			}

--  This type specifies the result of user commands (control requests)
-- from the TMN-OS or LCT.
		ShePmDrControlRequestResultType ::= INTEGER
			{
			noRequest(1),
			wrongIpAddress(2),
			wrongUserPassword(3),
			permissionDenied(4),
			comExecStarted(30),
			paramFaulty(31),
			requestBusy(32),
			setDataFailed(34),
			aswTimeout(35),
			commandFailed(36),
			commandSucceeded(37)
			}

--  user command results are defined between 2 - 29
-- The following are the error codes of enabling upload command.
-- All happened at the phase to check and create the RootDir and
-- subdirs.
-- IP address of FTP servre is incorrect
-- The user name or password is wrong
-- The user name has no permission to create dir/file
-- end of user command results
		ShePmDrUploadStatusType ::= INTEGER
			{
			uploadSuccess(1),
			uploadFail(2)
			}

	
	
--
-- Node definitions
--
	
--  -----------------------------------------------------------------
-- shePmDrInfo group, defines the parameters and its control group
-- -----------------------------------------------------------------
		shePmDrInfo OBJECT IDENTIFIER ::= { shePmDrMib 1 }

		
--  -----------------------------------------------------------------
-- Parameters
-- -----------------------------------------------------------------
		shePmDrParameters OBJECT IDENTIFIER ::= { shePmDrInfo 1 }

		
		shePmDrRootDir OBJECT-TYPE
			SYNTAX SnmpAdminString
			MAX-ACCESS read-only
			STATUS current
			DESCRIPTION
				"The root directory name on FTP server that stores the
				PM data of this DSLAM. It is the relative path to the
				ftproot, eg. 'hix5635/v1.5'
				The directory structure looks like:
				ftproot            <-- the upmost ftp root
				|- %RootDir%       <-- this value, specifies the DSLAM
				|   |- performance <-- all PM data saved under this directory
				|   |  |- cpuram   <-- stores CPU RAM data
				|   |  |  |- <yyyymmddhhmm.csv>   <-- data files
				|   |  |- suport   <-- stores data for SU ports
				|   |  |- uplink   <-- stores data for uplink ports
				|   |  |- periodically <-- stores periodical data
				"
			::= { shePmDrParameters 1 }

		
		shePmDrFtpIp OBJECT-TYPE
			SYNTAX IpAddress
			MAX-ACCESS read-only
			STATUS current
			DESCRIPTION
				"FTP server's IP address."
			::= { shePmDrParameters 2 }

		
		shePmDrFtpUser OBJECT-TYPE
			SYNTAX SnmpAdminString
			MAX-ACCESS read-only
			STATUS current
			DESCRIPTION
				"FTP user name. Write permission is required for this user."
			::= { shePmDrParameters 3 }

		
		shePmDrFtpPassword OBJECT-TYPE
			SYNTAX OCTET STRING (SIZE (0..128))
			MAX-ACCESS read-only
			STATUS current
			DESCRIPTION
				"FTP server access password. To protect the password, the string
				of this object in the GetResponse PDU is encrypted."
			::= { shePmDrParameters 4 }

		
		shePmDrUploadInterval OBJECT-TYPE
			SYNTAX INTEGER (1..96)
			UNITS "15-Minute"
			MAX-ACCESS read-only
			STATUS current
			DESCRIPTION
				"The interval that PM data is uploaded to FTP server. It increases
				with step of 15 minutes. The minimum value 1 means 15 minutes,
				while the maximum value 96 means the max interval is 24 hours."
			DEFVAL { 1 }
			::= { shePmDrParameters 5 }

		
		shePmDrUploadEnabled OBJECT-TYPE
			SYNTAX TruthValue
			MAX-ACCESS read-only
			STATUS current
			DESCRIPTION
				"Whether the FTP upload process is enabled."
			DEFVAL { false }
			::= { shePmDrParameters 6 }

		
--  -----------------------------------------------------------------
-- Control group
-- -----------------------------------------------------------------
		shePmDrControl OBJECT IDENTIFIER ::= { shePmDrInfo 2 }

		
		shePmDrControlRequest OBJECT-TYPE
			SYNTAX ShePmDrControlRequestType
			MAX-ACCESS read-write
			STATUS current
			DESCRIPTION
				"Command (setUploadParameters) to configure the PM Data Retrieval
				upload parameters. It must be the last member in the varBindList of
				the SNMP set request. The parameters of this command are:
				    shePmDrControlRootDir
				    shePmDrControlFtpIp
				    shePmDrControlFtpUser
				    shePmDrControlFtpPassword
				    shePmDrControlUploadInterval
				    shePmDrControlUploadEnabled
				  They are optional in the varBindList of set PDU, but at least one
				of them should be there.
				Notifications:
				  shePmDrControlResult at the command ending in case of long running command.
				  The long running command refers to the case that shePmDrUploadEnabled
				is changed from disable to enable. NE will verify the FTP connection at the
				enabling moment. Besides, the RootDir and four subdirs are created if they
				do not exist yet.
				  EM should GET shePmDrControlReqResult when the Response of the SET PDU
				is received, and the error status is noError. If the value of
				shePmDrControlReqResult is comExecStarted(30), which means the SET operation
				is a long running command, EM must issue another GET operation on
				shePmDrControlTimer. A timer should start on EM with the expire time equals
				to the value of shePmDrControlTimer. The shePmDrControlResult trap is expected
				to reach EM within the specified time.
				  When the trap is received by EM, EM can optionally GET
				shePmDrControlReqResult, shePmDrControlStatus, and shePmDrControlTimeStamp.
				"
			::= { shePmDrControl 1 }

		
		shePmDrControlStatus OBJECT-TYPE
			SYNTAX SheControlStatusType
			MAX-ACCESS read-only
			STATUS current
			DESCRIPTION
				"The status of a control request."
			::= { shePmDrControl 2 }

		
		shePmDrControlTimer OBJECT-TYPE
			SYNTAX Unsigned32
			MAX-ACCESS read-only
			STATUS current
			DESCRIPTION
				"The maximum wait time for the manager for command ending.
				For long running commands.
				The manager reads this value from the SHE."
			::= { shePmDrControl 3 }

		
		shePmDrControlReqResult OBJECT-TYPE
			SYNTAX ShePmDrControlRequestResultType
			MAX-ACCESS read-only
			STATUS current
			DESCRIPTION
				"The result of the last user command."
			::= { shePmDrControl 4 }

		
		shePmDrControlTimeStamp OBJECT-TYPE
			SYNTAX Unsigned32
			UNITS "sec"
			MAX-ACCESS read-only
			STATUS current
			DESCRIPTION
				"The time stamp of the last command (end of command)."
			::= { shePmDrControl 5 }

		
		shePmDrControlRootDir OBJECT-TYPE
			SYNTAX SnmpAdminString
			MAX-ACCESS read-write
			STATUS current
			DESCRIPTION
				"The root directory name on FTP server that stores the
				PM data of this DSLAM. Change the value of shePmDrRootDir."
			::= { shePmDrControl 6 }

		
		shePmDrControlFtpIp OBJECT-TYPE
			SYNTAX IpAddress
			MAX-ACCESS read-write
			STATUS current
			DESCRIPTION
				"FTP server's IP address. Change the value of shePmDrFtpIp."
			::= { shePmDrControl 7 }

		
		shePmDrControlFtpUser OBJECT-TYPE
			SYNTAX SnmpAdminString
			MAX-ACCESS read-write
			STATUS current
			DESCRIPTION
				"FTP user name.  Change the value of shePmDrFtpUser."
			::= { shePmDrControl 8 }

		
		shePmDrControlFtpPassword OBJECT-TYPE
			SYNTAX OCTET STRING (SIZE (0..128))
			MAX-ACCESS read-write
			STATUS current
			DESCRIPTION
				"FTP server access password. To protect the password, the string
				of this object in the GetResponse PDU is encrypted."
			::= { shePmDrControl 9 }

		
		shePmDrControlUploadInterval OBJECT-TYPE
			SYNTAX INTEGER (1..96)
			UNITS "15-Minute"
			MAX-ACCESS read-write
			STATUS current
			DESCRIPTION
				"The interval that PM data is uploaded to FTP server.
				Change the value of shePmDrUploadInterval."
			::= { shePmDrControl 10 }

		
		shePmDrControlUploadEnabled OBJECT-TYPE
			SYNTAX TruthValue
			MAX-ACCESS read-write
			STATUS current
			DESCRIPTION
				"Whether the FTP upload process is enabled.
				Change the value of shePmDrUploadEnabled.
				If the shePmDrUploadEnabled is changed from disable to enable,
				FTP connection will be verified at the enabling moment. Besides,
				the RootDir and four subdirs are created if they do not exist
				yet. The command in this case is a long running command.
				shePmDrControlResult trap will be sent to EM to notify the command result.
				"
			::= { shePmDrControl 11 }

		
--  -----------------------------------------------------------------
-- Status
-- -----------------------------------------------------------------
		shePmDrUploadInfo OBJECT IDENTIFIER ::= { shePmDrInfo 3 }

		
		shePmDrLastUploadStatus OBJECT-TYPE
			SYNTAX ShePmDrUploadStatusType
			MAX-ACCESS read-only
			STATUS current
			DESCRIPTION
				"The status of last FTP upload operation.
				It could be uploadSuccess(1) or uploadFail(2)."
			::= { shePmDrUploadInfo 1 }

		
		shePmDrLastUploadTimeStamp OBJECT-TYPE
			SYNTAX TimeTicks
			MAX-ACCESS read-only
			STATUS current
			DESCRIPTION
				"The time stamp of the last FTP upload operation
				(end of operation)."
			::= { shePmDrUploadInfo 2 }

		
		shePmDrLastUploadFileName OBJECT-TYPE
			SYNTAX SnmpAdminString
			MAX-ACCESS read-only
			STATUS current
			DESCRIPTION
				"The file name of last FTP upload operation."
			::= { shePmDrUploadInfo 3 }

		
		shePmDrLastUploadErrorString OBJECT-TYPE
			SYNTAX SnmpAdminString
			MAX-ACCESS read-only
			STATUS current
			DESCRIPTION
				"The text that describes the FTP upload failure. If
				upload succeeded, this string is empty."
			::= { shePmDrUploadInfo 4 }

		
--  -----------------------------------------------------------------
-- Trap definitions
-- -----------------------------------------------------------------
		shePmDrNotifications OBJECT IDENTIFIER ::= { shePmDrMib 2 }

		
		shePmDrEvents OBJECT IDENTIFIER ::= { shePmDrNotifications 1 }

		
		shePmDrControlResult NOTIFICATION-TYPE
			OBJECTS { shePmDrControlTimeStamp, shePmDrControlRequest, shePmDrControlReqResult }
			STATUS current
			DESCRIPTION 
				"Notification sent at the end of long running command.
				The possible values of shePmDrControlReqResult are:
				    wrongIpAddress(2),      -- IP address of FTP servre is incorrect
				    wrongUserPassword(3),   -- The user name or password is wrong
				    permissionDenied(4),    -- The user name has no permission to create dir/file
				    commandSucceeded(37)
				"
			::= { shePmDrEvents 1 }

		
		shePmDrUploadFailed NOTIFICATION-TYPE
			OBJECTS { shePmDrLastUploadStatus, shePmDrLastUploadTimeStamp, shePmDrLastUploadFileName, shePmDrLastUploadErrorString }
			STATUS current
			DESCRIPTION 
				"Indicates that an FTP upload failure occurred."
			::= { shePmDrEvents 2 }

		
		shePmDrMibConformance OBJECT IDENTIFIER ::= { shePmDrMib 100 }

		
		shePmDrMibCompliances OBJECT IDENTIFIER ::= { shePmDrMibConformance 1 }

		
		shePmDrMibCompliance MODULE-COMPLIANCE
			STATUS current
			DESCRIPTION 
				"Description."
			MODULE -- this module
				MANDATORY-GROUPS { shePmDrMibGroup, shePmDrMibControlGroup, shePmDrMibNotificationGroup }
			::= { shePmDrMibCompliances 1 }

		
		shePmDrMibGroups OBJECT IDENTIFIER ::= { shePmDrMibConformance 2 }

		
		shePmDrMibGroup OBJECT-GROUP
			OBJECTS { shePmDrRootDir, shePmDrFtpIp, shePmDrFtpUser, shePmDrFtpPassword, shePmDrUploadInterval, 
				shePmDrUploadEnabled, shePmDrLastUploadStatus, shePmDrLastUploadTimeStamp, shePmDrLastUploadFileName, shePmDrLastUploadErrorString
				 }
			STATUS current
			DESCRIPTION 
				"Description."
			::= { shePmDrMibGroups 1 }

		
		shePmDrMibControlGroup OBJECT-GROUP
			OBJECTS { shePmDrControlRequest, shePmDrControlStatus, shePmDrControlTimer, shePmDrControlReqResult, shePmDrControlTimeStamp, 
				shePmDrControlRootDir, shePmDrControlFtpIp, shePmDrControlFtpUser, shePmDrControlFtpPassword, shePmDrControlUploadInterval, 
				shePmDrControlUploadEnabled }
			STATUS current
			DESCRIPTION 
				"Description."
			::= { shePmDrMibGroups 2 }

		
		shePmDrMibNotificationGroup NOTIFICATION-GROUP
			NOTIFICATIONS { shePmDrControlResult, shePmDrUploadFailed }
			STATUS current
			DESCRIPTION 
				"Description."
			::= { shePmDrMibGroups 3 }

		
	
	END

--
-- she-pm-dr-mib.mib
--
