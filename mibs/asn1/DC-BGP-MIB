DC-BGP-MIB DEFINITIONS ::= BEGIN

-- PRODUCT-SHORT-NAME BGP

  IMPORTS
    MODULE-IDENTITY,
    OBJECT-TYPE,
    NOTIFICATION-TYPE,
    Integer32,
    Counter32,
    Gauge32,
    Unsigned32
      FROM SNMPv2-SMI

    TEXTUAL-CONVENTION,
    DisplayString,
    TruthValue,
    RowStatus,
    TimeStamp,
    TimeInterval
      FROM SNMPv2-TC

    MODULE-COMPLIANCE,
    OBJECT-GROUP,
    NOTIFICATION-GROUP
      FROM SNMPv2-CONF

    BfdSessionStatus
      FROM DC-MASTER-TC

    InetAddressType,
    InetAddress,
    InetPortNumber,
    InetAddressPrefixLength
      FROM INET-ADDRESS-MIB;

  bgpMib MODULE-IDENTITY
    LAST-UPDATED "201308290000Z" -- Thu Aug 2013 GMT 2013
    ORGANIZATION "Data Connection Ltd."
    CONTACT-INFO
                 "Postal: Data Connection Ltd.
                          100 Church Street
                          Enfield
                          Middlesex EN2 6BQ
                          United Kingdom
                  Tel:    +44 20 83661177
                  E-mail: dcbgp@datconnection.com"
    DESCRIPTION  "The MIB module for management of the DC-BGP
                  product."
    REVISION "201308290000Z" 
    DESCRIPTION "Changed the default values for Graceful Restart Timers and bgpPeerAfiSafiDisable"
    
    REVISION "201304020000Z" 
    DESCRIPTION "Started with new MIB file from Jun12 DCL code and merged in Arris changes"

  ::= { iso member-body(2) gb(826) national (0) eng-ltd (1)
        dataConnectionLtd (1578918) adg (5) qb (65) 1 }

-------------------------------------------------------------------------------
-- Textual Conventions.

  BgpIdentifier ::= TEXTUAL-CONVENTION
    DISPLAY-HINT "4x"
    STATUS     current
    DESCRIPTION
        "The representation of a BGP Identifier."
    SYNTAX OCTET STRING (SIZE (4))

  BgpAfi ::= TEXTUAL-CONVENTION
    STATUS current
    DESCRIPTION
        "The representation of a BGP AFI (Address Family Identifier)"
    SYNTAX      INTEGER {
                  other(0),
                  ipv4(1),
                  ipv6(2),
                  l2vpn(25)
                }

  BgpSafi ::= TEXTUAL-CONVENTION
    STATUS current
    DESCRIPTION
        "The representation of a BGP SAFI (Sub-Address Family Identifier)"
    SYNTAX      INTEGER {
                  none(0),
                  unicast(1),
                  multicast(2),
                  both(3),
                  labeled(4),
                  vpls(65),
                  mplsBgpVpn(128)
                }

  BgpAutonomousSystemNumber ::= TEXTUAL-CONVENTION
    STATUS current
    DESCRIPTION
        "An autonomous System Number.  If bgpAsSize is
        two-octet, the range is 0..65535.  If it is
        four-octet, it is the full range of Unsigned32."
    SYNTAX Unsigned32

  BgpAsSize ::= TEXTUAL-CONVENTION
    STATUS      current
    DESCRIPTION "The size of the AS number."
    SYNTAX      INTEGER {
                  twoOctet(1),
                  fourOctet(2)
                }

  BgpAdminStatus ::= TEXTUAL-CONVENTION
    STATUS      current
    DESCRIPTION "The desired administrative state of an entry."
    SYNTAX      INTEGER {
                  adminStatusUp(1),
                  adminStatusDown(2)
                }

  BgpOperStatus ::= TEXTUAL-CONVENTION
    STATUS      current
    DESCRIPTION "The current operational state of an entity."
    SYNTAX      INTEGER {
                  operStatusUp(1),        -- active
                  operStatusDown(2),      -- inactive
                  operStatusGoingUp(3),   -- activating
                  operStatusGoingDown(4), -- deactivating
                  operStatusActFailed(5)  -- activation failed
                }

  BgpOriginCode ::= TEXTUAL-CONVENTION
    STATUS      current
    DESCRIPTION "A BGP origin code."
    SYNTAX      INTEGER {
                  originIgp(0),        -- path interior to originating AS
                  originEgp(1),        -- path learned via EGP protocol
                  originIncomplete(2)  -- path was learned by other means
                }

  BgpMedDeltaType ::= TEXTUAL-CONVENTION
    STATUS      current
    DESCRIPTION "Whether to increment or decrement an MED value."
    SYNTAX      INTEGER {
                  increment(1),     -- increment the MED by the value specified
                  decrement(2)      -- decrement the MED by the value specified
                }

  BgpIpMatchType ::= TEXTUAL-CONVENTION
    STATUS      current
    DESCRIPTION "The type of match carried out by the route map for this IP
                 prefix list."
    SYNTAX      INTEGER {
                  nlriAddr(1),
                  sourceAddr(2),
                  nextHopAddr(3)
                }

  BgpPermitOrDeny ::= TEXTUAL-CONVENTION
    STATUS      current
    DESCRIPTION "Whether the behavior is to permit or deny."
    SYNTAX      INTEGER {
                  permit(1),        -- Unmatched routes are permitted
                  deny(2)           -- Unmatched routes are denied
                }

  BgpDropOrWarn ::= TEXTUAL-CONVENTION
    STATUS      current
    DESCRIPTION "Whether to drop a session or just warn a parameter has been
                 exceeded."
    SYNTAX      INTEGER {
                  drop(1),          -- The session is dropped
                  warn(2)           -- A warning is produced
                }

  BgpIbgpOrEbgp ::= TEXTUAL-CONVENTION
    STATUS      current
    DESCRIPTION "Whether this is an iBGP, confederation eBGP, or eBGP
                 peer group."
    SYNTAX      INTEGER {
                  ibgp(1),
                  ebgp(2),
                  ebgpconfed(3)
                }

  BgpPeerOrAfm ::= TEXTUAL-CONVENTION
    STATUS      current
    DESCRIPTION "Whether an index refers to a BGP Peer Index or an AFM index."
    SYNTAX      INTEGER {
                  peerIndex(1),
                  afmIndex(2)
                }

  BgpAsPathAction ::= TEXTUAL-CONVENTION
    STATUS      current
    DESCRIPTION "How to handle setting an AS-Path attribute."
    SYNTAX      INTEGER {
                  none(0),          -- No action is carried out
                  set(1),           -- The local AS number is prepended to the
                                    --  AS path
                  remMatch(2),      -- AS values matching the bgpRouteMapMaAS
                                    --  regular expression are removed
                  remMatchAndSet(3) -- AS values matching the bgpRouteMapMaAS
                                    --  regular expression are remove, and the
                                    --  local AS number is prepended to the AS
                                    --  path
                }

  BgpAggregateOptions ::= TEXTUAL-CONVENTION
    STATUS      current
    DESCRIPTION "The option used when aggregating."
    SYNTAX      INTEGER {
                  none(1),           -- No options.  An aggregate entry is
                                     --  generated if more specific entries are
                                     --  present
                  summary(2),        -- Only the summary option.  More specific
                                     --  routes that make the aggregate are not
                                     --  advertised
                  asSet(3),          -- Aggregates the AS-PATH using the
                                     --  algorithm described in RFC 1771.  This
                                     --  maintains the longest AS-Sequence common
                                     --  common to the aggregated routes and
                                     --  adds AS numbers from the other routes
                                     --  to an AS-Set
                  summaryAsSet(4),   -- Both summary and AS-Set options
                  asAppend(5),       -- No common AS sequence is maintained.
                                     --  All AS numbers from the aggregated
                                     --  routes are added to an AS-Set.
                  summaryAsAppend(6) -- Both summary and As-Append options
                }

  BgpMjStatus ::= TEXTUAL-CONVENTION
    STATUS      current
    DESCRIPTION "The status of a master join."
    SYNTAX      INTEGER {
                  mjNotJoined(1),        -- initial state of join
                  mjSentAddJoin(2),      -- sent ATG_FT_ADD_JOIN to slave
                  mjSentRegister(3),     -- sent registration signal to slave
                  mjJoinActive(4),       -- join is active
                  mjSentDelJoin(5),      -- sent ATG_FT_DELETE_JOIN to slave
                  mjSentUnregister(6),   -- sent unregistration to slave
                  mjJoinGone(7),         -- join has been deleted
                  mjFailedToRegister(8), -- slave rejected reg message
                  mjFailingOver(9),      -- slave is failing over
                  mjFailed(10),          -- join has permanently failed
                  mjNoPartner(11)        -- no partner to join to
                }

  BgpSjStatus ::= TEXTUAL-CONVENTION
    STATUS      current
    DESCRIPTION "The status of a slave join."
    SYNTAX      INTEGER {
                  sjNotJoined(1),      -- initial state of join
                  sjJoined(2),         -- master has sent an ATG_FT_ADD_JOIN
                  sjJoinActive(3),     -- master has registered the join
                  sjJoinUnreg(4),      -- master has unregistered the join
                  sjJoinGone(5),       -- master has deleted the join
                  sjFailingOver(6),    -- master is failing over
                  sjFailed(7)          -- join has permanently failed
                }

  BgpPeerStates ::= TEXTUAL-CONVENTION
    STATUS      current
    DESCRIPTION "The current state of a connection to a BGP peer."
    SYNTAX      INTEGER {
                  idle(1),
                  connect(2),
                  active(3),
                  opensent(4),
                  openconfirm(5),
                  established(6)
                }

  BgpPeerEvents ::= TEXTUAL-CONVENTION
    STATUS      current
    DESCRIPTION "An event that has occurred to a connection to a BGP peer."
    SYNTAX      INTEGER {
                  noEvent(0),             -- no event has yet occured
                  start(1),               -- the connection has been activated
                                          --  (either outgoing or incoming)
                  stop(2),                -- the connection has been
                                          --  deactivated
                  transportOpen(3),       -- the transport connection has been
                                          --  opened
                  transportClosed(4),     -- the transport connection has been
                                          --  closed
                  transportOpenFailed(5), -- an attempt to open the transport
                                          --  connection has failed
                  transportFatalError(6), -- a fatal error has occurred on the
                                          --  transport connection
                  connectRetryTimer(7),   -- the ConnectRetry timer has popped
                  holdTimer(8),           -- the Hold timer has popped
                  keepaliverTimer(9),     -- the Keepalive timer has popped
                  recvOpen(10),           -- a BGP Open message has been
                                          --  received
                  recvKeepAlive(11),      -- a BGP KeepAlive message has been
                                          --  received
                  recvUpdate(12),         -- a BGP Update message has been
                                          --  received
                  recvNotification(13)    -- a BGP Notification message has
                                          --  been received
                }

  BgpCapabilities ::= TEXTUAL-CONVENTION
    STATUS      current
    DESCRIPTION "The capabilities advertised by a BGP instance."
    SYNTAX      BITS {
                  mpIpv4Unicast(0),             -- multiprotocol BGP support
                                                --  for IPv4 unicast routes
                  mpIpv4Multicast(1),           -- multiprotocol BGP support
                                                --  for IPv4 multicast routes
                  mpIpv4Vpn(2),                 -- multiprotocol BGP support
                                                --  for IPv4 VPN routes
                  mpIpv4Label(3),               -- multiprotocol BGP support
                                                --  for labeled IPv4 VPN
                                                --  routes
                  mpIpv6Unicast(4),             -- multiprotocol BGP support
                                                --  for IPv6 unicast routes
                  mpIpv6Multicast(5),           -- multiprotocol BGP support
                                                --  for IPv6 multicast routes
                  mpIpv6Vpn(6),                 -- multiprotocol BGP support
                                                --  for IPv6 VPN routes
                  mpIpv6Label(7),               -- multiprotocol BGP support
                                                --  for labeled IPv6 VPN
                                                --  routes
                  routeRefresh(8),              -- support for Route Refresh
                                                --  messages
                  gracefulRestart(9),           -- support for graceful restart
                                                --  processing
                  routeRefreshCisco(10),        -- support for pre-standard
                                                --  (Cisco) Route Refresh
                                                --  messages
                  outboundRouteFilter(11),      -- support for Outbound Route
                                                --  Filtering, for one or more
                                                --  AFI/SAFI types
                  outboundRouteFilterCisco(12), -- support for pre-standard
                                                --  (Cisco) Outbound Route
                                                --  Filtering, for one or more
                                                --  AFI/SAFI types
                  fourOctetAs(13),              -- support for four-octet AS
                                                --  numbers
                  mpL2vpnVpls(14)               -- multiprotocol BGP support
                                                --  for AFI/SAFI = L2VPN/VPLS
                }

  BgpPeerRestartSupport ::= TEXTUAL-CONVENTION
    STATUS      current
    DESCRIPTION "The level of restart support advertised by a peer."
    SYNTAX      INTEGER {
                  none(1),        -- the peer does not support restart.
                  awareOnly(2),   -- the peer has advertised a restart
                                  --  capability, but has not advertised any
                                  --  address families as being restart
                                  --  capable.
                  enabled(3)      -- the peer supports restart capability for
                                  --  one or more address families.
                }

  BgpPeerRestartStatus ::= TEXTUAL-CONVENTION
    STATUS      current
    DESCRIPTION "The current status of a restarting BGP peer."
    SYNTAX      INTEGER {
                  notRestarting(1),        -- the peer is not restarting
                  restartTimerRunning(2),  -- the restart timer is running in
                                           --  one or more Adj-RIB-Ins for this
                                           --  peer.  The session to this peer
                                           --  has failed and has not yet been
                                           --  re-established.
                  stalePathTimerRunning(3) -- the stale path timer is running
                                           --  in one or more Adj-RIB-Ins for
                                           --  this peer, and the restart timer
                                           --  is not running for any
                                           --  Adj-RIB-Ins for this peer.  The
                                           --  session to this peer has failed
                                           --  and has been re-established, but
                                           --  the peer has not yet refreshed
                                           --  its routes to DC-BGP.
                }

  BgpPeerLastFailure ::= TEXTUAL-CONVENTION
    STATUS current
    DESCRIPTION
        "The cause of the last failure to occur to a session to a BGP peer."
    SYNTAX      INTEGER {
                  other(1),      -- the trap was not triggered by a
                                 --  Notification message
                  notifySent(2), -- the trap was triggered by a sent
                                 --  Notificatino message
                  notifyRecv(3)  -- the trap was triggered by a received
                                 --  Notification message
                }

  BgpCeaseErrorSubcode ::= TEXTUAL-CONVENTION
    STATUS current
    DESCRIPTION
        "The error subcode to be sent in the Cease Notification message."
    SYNTAX      INTEGER {
                  none(0),          -- no subcode is specified.
                  adminShutdown(2), -- administrative Shutdown.
                  peerUnconfig(3),  -- peer De-configured.
                  adminReset(4),    -- administrative Reset.
                  configChange(6),  -- other Configuration Change.
                  noResource(8)     -- out of Resources.
                }

  BgpPeerReflectorClientType ::= TEXTUAL-CONVENTION
    STATUS      current
    DESCRIPTION "What type of client this BGP Peer is.  A client of a route
                 reflector is a meshed client if and only if it is fully meshed
                 with all meshed clients of that route reflector."
    SYNTAX      INTEGER {
                  nonClient(0),
                  client(1),
                  meshedClient(2)
                }

  BgpComponentId ::= TEXTUAL-CONVENTION
    STATUS      current
    DESCRIPTION "The type of process to which a given entity is joined."
    SYNTAX      INTEGER {
                  componentRm(1),        -- RIB Manager
                  componentNm(2),        -- Neighbor Manager
                  componentIpSockets(3), -- IP Sockets Stub
                  componentRtm(4),       -- Routing Table Manager
                  componentVmIpv4(5),    -- VPN Manager (IPv4 VPNs)
                  componentBfd(6)        -- BFD Stub
                }

  BgpCommunity ::= TEXTUAL-CONVENTION
    DISPLAY-HINT "4x"
    STATUS       current
    DESCRIPTION "The representation of a BGP Community."
    SYNTAX OCTET STRING (SIZE(4))

  BgpExtendedCommunity ::= TEXTUAL-CONVENTION
    DISPLAY-HINT "8x"
    STATUS       current
    DESCRIPTION "The representation of a BGP Extended Community."
    SYNTAX OCTET STRING (SIZE(8))

  BgpCommunityAction ::= TEXTUAL-CONVENTION
    STATUS      current
    DESCRIPTION "How to handle adding a community attribute."
    SYNTAX      INTEGER {
                  none(0),      -- No action is carried out
                  removeAll(1),  -- Current community list is cleared
                  removeSpecific(2),  -- The community is removed from the list
                  setSpecific(3),    -- The community is added to the list
                  removeAllAndSet(4) -- The community replaces the current list
                }

  BgpPathAttrAtomicAggPresence ::= TEXTUAL-CONVENTION
    STATUS      current
    DESCRIPTION "Whether the route has the ATOMIC_AGGREGATE Path Attribute
                 present."
    SYNTAX      INTEGER {
                  atomicAggregatePresent(1),
                  atomicAggregateMissing(2)
                }

  BgpOrfType ::= TEXTUAL-CONVENTION
    STATUS      current
    DESCRIPTION "Type of Outbound Route Filter."
    SYNTAX      INTEGER {
                  community(1),          -- Community ORF-Type
                  extCommunity(2),       -- Extended Community ORF-Type
                  prefix(64)             -- Address Prefix ORF-Type
                }

  BgpOrfSendReceive ::= TEXTUAL-CONVENTION
    STATUS      current
    DESCRIPTION "ORF send/receive indicator."
    SYNTAX      INTEGER {
                  receive(1),       -- Willing to receive ORF entries from peer
                  send(2),          -- Would like to send ORF entries to peer
                  both(3)           -- Both send and receive
                }

  BgpOrfAssociation ::= TEXTUAL-CONVENTION
    STATUS      current
    DESCRIPTION "Indicates the type of association (if any) to the Outbound
                 Route Filtering protocol."
    SYNTAX      INTEGER {
                  noAssociation(0),  -- No association.  Route map is not
                                     -- eligible for advertisement to peers via
                                     -- the ORF protocol
                  local(1),          -- Configured locally and eligible for
                                     -- advertisement to peers via the ORF
                                     -- protocol
                  remote(2)          -- Learned from peer via the ORF protocol
                }

 BgpPeeringType ::= TEXTUAL-CONVENTION
    STATUS      current
    DESCRIPTION "Indicates the type of peering relationship with the peer."
    SYNTAX      INTEGER {
                  unspecified(0),   -- Relationship is unspecified
                  provider(1),      -- Peer is a provider
                  customer(2),      -- Peer is a customer
                  biLateral(3)      -- Peer is neither a customer or a provider
                }

 BgpAfiSafiBits ::= TEXTUAL-CONVENTION
    STATUS      current
    DESCRIPTION "Bit flags used to indicate one or more AFI/SAFI combinations."
    SYNTAX      BITS {
                  ipv4Unicast(0),
                  ipv4Multicast(1),
                  ipv4MplsBgpVpn(2),
                  ipv6Unicast(3),
                  ipv6Multicast(4),
                  ipv6MplsBgpVpn(5),
                  ipv4Labeled(6),
                  ipv6Labeled(7),
                  l2vpnVpls(8)
                }

  BgpNlriIsActiveFlag ::= TEXTUAL-CONVENTION
    STATUS      current
    DESCRIPTION "Indicates whether an NLRI is active in the routing table."
    SYNTAX      INTEGER {
                  notTracked(1),    -- BGP is not tracking active routes
                  inactive(2),      -- The BGP route is inactive
                  active(3)         -- The BGP route is active
                }

-------------------------------------------------------------------------------
  bgpNotifications     OBJECT IDENTIFIER ::= { bgpMib 1 }
  bgpRm                OBJECT IDENTIFIER ::= { bgpMib 2 }

--
-- RIB Manager Entity Table.
--
-- This is the top-level MIB for the DC-BGP RIB Manager.  It controls
-- creation and global configuration of the RIB Manager.
--
-- It also contains the system wide parameters of Route Flap Damping as
-- defined in RFC 2439.  Route Flap Damping applies a penalty to a route if it
-- changes, and this penalty value is decayed over time.  If the penalty value
-- exceeds a cut off threshold the route is suppressed until the penalty falls
-- below the reuse threshold.  These values are set via a route map in the
-- bgpFlapConfigTable.  The values in this table are used system wide and
-- define how often calculations take place and sizes of reuse lists.  Reuse
-- lists are utilised to make the calculations of when a flapping route is
-- available for re-use more efficient.
--

  bgpRmEntTable OBJECT-TYPE
  -- FAMILY-SHORT-NAME BGP_RM
    SYNTAX      SEQUENCE OF BgpRmEntEntry
    MAX-ACCESS  not-accessible
    STATUS      current
    DESCRIPTION "Each entry in this table represents a RIB Manager
                 entity.  Only some fields in an entry can be changed while the
                 admin status is up."
    ::= { bgpRm 1 }

  bgpRmEntEntry OBJECT-TYPE
    SYNTAX      BgpRmEntEntry
    MAX-ACCESS  not-accessible
    STATUS      current
    DESCRIPTION "Each entry represents a RIB Manager entity."
    INDEX { bgpRmEntIndex }
    ::= { bgpRmEntTable 1 }

  BgpRmEntEntry ::= SEQUENCE {
      bgpRmEntIndex                   Unsigned32,
      bgpRmEntRowStatus               RowStatus,
      bgpRmEntAdminStatus             BgpAdminStatus,
      bgpRmEntOperStatus              BgpOperStatus,
      bgpRmEntAsSize                  BgpAsSize,
      bgpRmEntLocalAs                 BgpAutonomousSystemNumber,
      bgpRmEntLocalMbrAs              BgpAutonomousSystemNumber,
      bgpRmEntLocalIdentifier         BgpIdentifier,
      bgpRmEntClusterId               BgpIdentifier,
      bgpRmEntIpv4MultiSupport        TruthValue,
      bgpRmEntVpnIpv4Support          TruthValue,
      bgpRmEntFlapDeltat              Unsigned32,
      bgpRmEntFlapReusemax            Unsigned32,
      bgpRmEntFlapReusesize           Unsigned32,
      bgpRmEntFlapReusearray          Unsigned32,
      bgpRmEntFlapFreemax             Unsigned32,
      bgpRmEntNoRefresh               TruthValue,
      bgpRmEntDefLocalPref            Unsigned32,
      bgpRmEntAlwaysCompMed           TruthValue,
      bgpRmEntAggregateMed            TruthValue,
      bgpRmEntDeterministicMed        TruthValue,
      bgpRmEntNhrJoinStatus           BgpMjStatus,
      bgpRmEntNhrEntIndex             Unsigned32,
      bgpRmEntI3JoinStatus            BgpMjStatus,
      bgpRmEntI3EntIndex              Unsigned32,
      bgpRmEntPauseThreshold          Unsigned32,
      bgpRmEntMaxIBgpEcmpRoutes       Unsigned32,
      bgpRmEntMaxEBgpEcmpRoutes       Unsigned32,
      bgpRmEntRestartSupported        TruthValue,
      bgpRmEntMaxRestartTime          Unsigned32,
      bgpRmEntRecoveryTime            Unsigned32,
      bgpRmEntRestarting              TruthValue,
      bgpRmEntIpv4UniFwdPrsrvd        TruthValue,
      bgpRmEntIpv4MultiFwdPrsrvd      TruthValue,
      bgpRmEntVpnIpv4FwdPrsrvd        TruthValue,
      bgpRmEntIpv4ArinhJoinStatus     BgpSjStatus,
      bgpRmEntIpv4ArinhEntIndex       Unsigned32,
      bgpRmEntIpv6ArinhJoinStatus     BgpSjStatus,
      bgpRmEntIpv6ArinhEntIndex       Unsigned32,
      bgpRmEntSupportIpv6             TruthValue,
      bgpRmEntStrictConfed            TruthValue,
      bgpRmEntOrfSupported            TruthValue,
      bgpRmEntCiscoPrefixSupported    TruthValue,
      bgpRmEntSelectDeferTime         Unsigned32,
      bgpRmEntStalePathTime           Unsigned32,
      bgpRmEntNonPersistentAros       TruthValue,
      bgpRmEntAroRouteThreshold       Unsigned32,
      bgpRmEntMaxActiveAroGroups      Unsigned32,
      bgpRmEntNumArosInGroup          Unsigned32,
      bgpRmEntNumAroRoutes            Counter32,
      bgpRmEntPeakNumAroRoutes        Counter32,
      bgpRmEntClearStats              TruthValue,
      bgpRmEntFastExtFallover         TruthValue,
      bgpRmEntRemainDelayTime         TimeInterval,
      bgpRmEntPathAttrs               Gauge32,
      bgpRmEntAggSplitHorizon         TruthValue,
      bgpRmEntAggAdvSuppr             TruthValue,
      bgpRmEntUpdateGroups            TruthValue,
      bgpRmEntPhase3DelayTime         Unsigned32,
      bgpRmEntTrapOperState           TruthValue
      }

  bgpRmEntIndex OBJECT-TYPE
    SYNTAX      Unsigned32
    MAX-ACCESS  not-accessible
    STATUS      current
    DESCRIPTION "Identifies a RIB Manager entity."
    ::= { bgpRmEntEntry 1 }

  bgpRmEntRowStatus OBJECT-TYPE
    SYNTAX      RowStatus
    MAX-ACCESS  read-create
    STATUS      current
    DESCRIPTION "The row status for this RIB Manager Entity Table entry,
                 used to create and destroy table entries."
    ::= { bgpRmEntEntry 2 }

  bgpRmEntAdminStatus OBJECT-TYPE
    SYNTAX      BgpAdminStatus
    MAX-ACCESS  read-create
    STATUS      current
    DESCRIPTION "The administrative status of this RIB Manager entity,
                 used to activate and deactivate RM."
    DEFVAL      { adminStatusDown }
    ::= { bgpRmEntEntry 3 }

  bgpRmEntOperStatus OBJECT-TYPE
    SYNTAX      BgpOperStatus
    MAX-ACCESS  read-only
    STATUS      current
    DESCRIPTION "The current operational status of this RIB Manager
                 entity."
    ::= { bgpRmEntEntry 4 }

  bgpRmEntAsSize OBJECT-TYPE
    SYNTAX      BgpAsSize
    MAX-ACCESS  read-create
    STATUS      current
    DESCRIPTION "The size of AS numbers.

                 The semantics of this are determined as per RFC 4893.  It is
                 equivalent to the Base Scalar bgpM2AsSize.  This field can
                 only be changed when the Admin Status is down."
    DEFVAL      { twoOctet }
    ::= { bgpRmEntEntry 5 }

  bgpRmEntLocalAs OBJECT-TYPE
    SYNTAX      BgpAutonomousSystemNumber
    MAX-ACCESS  read-create
    STATUS      current
    DESCRIPTION "The local autonomous system number.

                 If the bgpAsSize is twoOctet, then the range is
                 constrained to be 0-65535.  A non-mappable 4-octet AS number
                 should only be used when all BGP speakers within the AS
                 support 4-octet AS numbers.  This field can only be
                 changed when the Admin Status is down.
                 For a router not in a confederation, it is equivalent to
                 the Base Scalar bgpM2LocalAs.  For a router in a
                 confederation, it is equivalent to the Base Scalar
                 bgpM2ConfederationId.  If bgpRmEntLocalMbrAs is not 0,
                 then this router is in a confederation and this field
                 contains the confederation ID for this confederation."
    ::= { bgpRmEntEntry 6 }

  bgpRmEntLocalMbrAs OBJECT-TYPE
    SYNTAX      BgpAutonomousSystemNumber
    MAX-ACCESS  read-create
    STATUS      current
    DESCRIPTION "The local member autonomous system number.

                 This field is only valid if the router is in a confederation.
                 This field must be 0 if and only if the router is not in a
                 confederation.  If the bgpAsSize is twoOctet, then the range
                 is constrained to be 0-65535.  A non-mappable 4-octet AS
                 number should only be used when all BGP speakers within the
                 confederation support 4-octet AS numbers.  This field can only
                 be changed when the Admin Status is down.  If this field is
                 not 0, it is equivalent to the Base Scalar bgpM2LocalAS."
   DEFVAL { 0 }
    ::= { bgpRmEntEntry 7 }

  bgpRmEntLocalIdentifier OBJECT-TYPE
    SYNTAX      BgpIdentifier
    MAX-ACCESS  read-create
    STATUS      current
    DESCRIPTION "The BGP Identifier of the local system. This is a generic
                 identifier and not necessarily an IP address.  This field
                 can only be changed when the Admin Status is down.
                 It is equivalent to the Base Scalar bgpM2LocalIdentifier."
    ::= { bgpRmEntEntry 8 }

  bgpRmEntClusterId OBJECT-TYPE
    SYNTAX      BgpIdentifier
    MAX-ACCESS  read-create
    STATUS      current
    DESCRIPTION "The configured Cluster-ID of the local router.
                 A value of 0.0.0.0 indicates the absence of this
                 value.  This field can only be changed when the Admin
                 Status is down.  The RM entity will act as a route reflector
                 if any peer is configured to be a client.  If no cluster ID is
                 explicitly configured here, the Router ID will be used.
                 It is equivalent to the Base Scalar Route Reflector Extension
                 entry bgpM2ClusterId."
    DEFVAL { '00000000'h }
    ::= { bgpRmEntEntry 9 }

  bgpRmEntIpv4MultiSupport OBJECT-TYPE
    SYNTAX      TruthValue
    MAX-ACCESS  read-create
    STATUS      obsolete
    DESCRIPTION "This value is TRUE if Multicast IPv4 is supported.
                 This field can only be changed when the Admin Status is
                 down."
    DEFVAL { false }
    ::= { bgpRmEntEntry 10 }

  bgpRmEntVpnIpv4Support OBJECT-TYPE
    SYNTAX      TruthValue
    MAX-ACCESS  read-create
    STATUS      obsolete
    DESCRIPTION "This value is TRUE if VPN-IPv4 addresses for MPLS/BGP
                 VPNs are supported.  This field can only be changed when
                 the Admin Status is down."
    DEFVAL { false }
    ::= { bgpRmEntEntry 11 }

  bgpRmEntFlapDeltat OBJECT-TYPE
    SYNTAX      Unsigned32 (1..4294967295)
    UNITS       "seconds"
    MAX-ACCESS  read-create
    STATUS      current
    DESCRIPTION "This is the time granularity used to perform all decay
                 computations.  This field can only be changed when the
                 Admin Status is down."
    DEFVAL { 1 }
    ::= { bgpRmEntEntry 12 }

  bgpRmEntFlapReusemax OBJECT-TYPE
    SYNTAX      Unsigned32 (1..65535)
    UNITS       "seconds"
    MAX-ACCESS  read-create
    STATUS      current
    DESCRIPTION "This is the time corresponding to the last reuse list. This
                 is the maximum value of T-hold that may be configured in the
                 bgpFlapConfigTable table.  This field can only be changed
                 when the Admin Status is down."
    DEFVAL { 3600 }
    ::= { bgpRmEntEntry 13 }

  bgpRmEntFlapReusesize OBJECT-TYPE
    SYNTAX      Unsigned32 (1..65535)
    MAX-ACCESS  read-create
    STATUS      current
    DESCRIPTION "This is the number of reuse lists.  This field, together with
                 bgpRmEntFlapReusemax, fixes the time interval that each reuse
                 list covers.  This field can only be changed when the Admin
                 Status is down."
    DEFVAL { 256 }
    ::= { bgpRmEntEntry 14 }

  bgpRmEntFlapReusearray OBJECT-TYPE
    SYNTAX      Unsigned32
    MAX-ACCESS  read-create
    STATUS      current
    DESCRIPTION "This is the size of the reuse index arrays.  This size
                 determines the accuracy with which suppressed routes can be
                 placed within the set of reuse lists when suppressed for a
                 long time.  This field can only be changed when the Admin
                 Status is down."
    DEFVAL { 1024 }
    ::= { bgpRmEntEntry 15 }

  bgpRmEntFlapFreemax OBJECT-TYPE
    SYNTAX      Unsigned32
    UNITS       "seconds"
    MAX-ACCESS  read-create
    STATUS      current
    DESCRIPTION "This is the maximum length of time for which a penalty against
                 a route this is not available shall be remebered, across all
                 configurations in the bgpFlapConfigTable.  This field can only
                 be changed when the Admin Status is down."
    DEFVAL { 3600 }
    ::= { bgpRmEntEntry 16 }

  bgpRmEntNoRefresh OBJECT-TYPE
    SYNTAX      TruthValue
    MAX-ACCESS  read-create
    STATUS      current
    DESCRIPTION "This is set to TRUE to prevent automatic route refresh
                 when a policy update has occured.  This is to allow several
                 route maps to be updated and then have one route refresh
                 once completed.

                 Once the route maps are updated, set this field to FALSE to
                 send out the route refreshes."
    DEFVAL { false }
    ::= { bgpRmEntEntry 17 }

  bgpRmEntDefLocalPref OBJECT-TYPE
    SYNTAX      Unsigned32
    MAX-ACCESS  read-create
    STATUS      current
    DESCRIPTION "The default value used for the local preference if one is not
                 set up through the filtering process.  This field can only be
                 changed when the Admin Status is down."
    DEFVAL { 100 }
    ::= { bgpRmEntEntry 18 }

  bgpRmEntAlwaysCompMed OBJECT-TYPE
    SYNTAX      TruthValue
    MAX-ACCESS  read-create
    STATUS      current
    DESCRIPTION "This is set to TRUE to always compare the MULTI-EXIT-DESC
                 route attribute in the BGP decision process, even if the
                 routes in consideration were learned from different autonomous
                 systems.  This field can only be changed when the Admin Status
                 is down."
    DEFVAL { false }
    ::= { bgpRmEntEntry 19 }

  bgpRmEntAggregateMed OBJECT-TYPE
    SYNTAX      TruthValue
    MAX-ACCESS  read-create
    STATUS      current
    DESCRIPTION "If FALSE, then routes will only be aggregated if they
                 have matching MULTI-EXIT-DISC route attributes.  This
                 means that operation is in strict compliance with the
                 specification. If TRUE, routes will be aggregated independent
                 of their MULTI-EXIT-DISC attributes.  This field can only be
                 changed when the Admin Status is down."
    DEFVAL { true }
    ::= { bgpRmEntEntry 20 }

  bgpRmEntDeterministicMed OBJECT-TYPE
    SYNTAX      TruthValue
    MAX-ACCESS  read-create
    STATUS      current
    DESCRIPTION "This is set to TRUE to enable deterministic MULTI-EXIT-DESC
                 processing.  If set to FALSE, the selection of routes by the
                 BGP decision process is non-deterministic, because of the
                 rules for comparing MULTI-EXIT-DESC values, and this can lead
                 to flapping of routes.  Setting this value to TRUE modifies
                 the route selection procedure so that the BGP decision process
                 is deterministic.  This field can only be changed when the
                 Admin Status is down."
    DEFVAL { true }
    ::= { bgpRmEntEntry 21 }

  bgpRmEntNhrJoinStatus OBJECT-TYPE
    SYNTAX      BgpMjStatus
    MAX-ACCESS  read-only
    STATUS      obsolete
    DESCRIPTION "The status of the NHR Interface join."
    ::= { bgpRmEntEntry 22 }

  bgpRmEntNhrEntIndex OBJECT-TYPE
    SYNTAX      Unsigned32
    MAX-ACCESS  read-create
    STATUS      obsolete
    DESCRIPTION "Identifies the NHR Interface routing stub entity.  This field
                 can only be changed when the Admin Status is down."
    ::= { bgpRmEntEntry 23 }

  bgpRmEntI3JoinStatus OBJECT-TYPE
    SYNTAX      BgpMjStatus
    MAX-ACCESS  read-only
    STATUS      current
    DESCRIPTION "The status of the I3 join."
    ::= { bgpRmEntEntry 24 }

  bgpRmEntI3EntIndex OBJECT-TYPE
    SYNTAX      Unsigned32
    MAX-ACCESS  read-create
    STATUS      current
    DESCRIPTION "Identifies the I3 Interface routing stub entity.  This field
                 can only be changed when the Admin Status is down."
    ::= { bgpRmEntEntry 25 }

  bgpRmEntPauseThreshold OBJECT-TYPE
    SYNTAX      Unsigned32
    MAX-ACCESS  read-create
    STATUS      current
    DESCRIPTION "The RM component can be configured to limit the amount of
                 work that it carries out in a single cycle of the N-BASE
                 scheduler.  The component maintains a work penalty that is set
                 to zero each time RM is scheduled, and that is incremented
                 during lengthy calculations.  If the penalty reaches the
                 threshold, then RM pauses processing.  The default value for
                 the threshold has been chosen so that the most common UPDATE
                 messages will be processed without pausing."
    DEFVAL { 2000 }
    ::= { bgpRmEntEntry 26 }

  bgpRmEntMaxIBgpEcmpRoutes OBJECT-TYPE
    SYNTAX      Unsigned32
    MAX-ACCESS  read-create
    STATUS      current
    DESCRIPTION "The maximum number of Equal Cost BGP next-hops stored by
                 DC-BGP for a route learnt via internal BGP.  This is also
                 the maximum number of network next-hops sent to the
                 routing table manager by DC-BGP for such a route.

                 This field can only be changed when the Admin Status is
                 down."
    DEFVAL { 4 }
    ::= { bgpRmEntEntry 27 }

  bgpRmEntMaxEBgpEcmpRoutes OBJECT-TYPE
    SYNTAX      Unsigned32
    MAX-ACCESS  read-create
    STATUS      current
    DESCRIPTION "The maximum number of Equal Cost BGP next-hops stored by
                 DC-BGP for a route learnt via external BGP.  This is also
                 the maximum number of network next-hops sent to the
                 routing table manager by DC-BGP for such a route.

                 This field can only be changed when the Admin Status is
                 down."
    DEFVAL { 4 }
    ::= { bgpRmEntEntry 28 }

  bgpRmEntRestartSupported OBJECT-TYPE
    SYNTAX      TruthValue
    MAX-ACCESS  read-create
    STATUS      current
    DESCRIPTION "Whether DC-BGP RIB Manager should execute graceful restart
                 procedures in the event of either a peer failure or its own
                 failure.  This field can only be changed when the Admin Status
                 is down."
    DEFVAL { true }
    ::= { bgpRmEntEntry 29 }

  bgpRmEntMaxRestartTime OBJECT-TYPE
    SYNTAX 	     Unsigned32 (1..3600)
    UNITS       "seconds"
    MAX-ACCESS  read-create
    STATUS      current
    DESCRIPTION "This is the maximum time (in seconds) to wait for a graceful
                 restart capable peer to come back after a restart.  This value
                 is used when the value advertised by the peer in its own OPEN
                 message exceeds this threshold.  This field is only used if
                 bgpRmEntRestartSupported is set to TRUE."
    DEFVAL { 120 }
    ::= { bgpRmEntEntry 30 }

  bgpRmEntRecoveryTime OBJECT-TYPE
    SYNTAX      Unsigned32 (1..3600)
    UNITS       "seconds"
    MAX-ACCESS  read-create
    STATUS      current
    DESCRIPTION "The interval which DC-BGP should advertize to its peers as
                 the estimated time (in seconds) it will take for the BGP
                 session to be re-established after a restart.  This can be
                 used to speed up routing convergence by its peer in case
                 the BGP speaker does not come back after a restart.

                 Following a local restart, DC-BGP will impose an upper bound
                 on the length of time permitted for required AFMs to restart
                 which is equal to the value of this field.  If any AFMs fail
                 to restart within this time the decision process will commence
                 immediately thereby overriding the timer specified by
                 bgpRmEntSelectDeferTime.

                 This field is also the time DC-BGP will wait for a failed
                 stub to re-join.  If the stub does not come back within
                 this time, DC-BGP will deactivate."
    DEFVAL { 120 }
    ::= { bgpRmEntEntry 31 }

  bgpRmEntRestarting OBJECT-TYPE
    SYNTAX      TruthValue
    MAX-ACCESS  read-create
    STATUS      current
    DESCRIPTION "Boolean flag used to inform DC-BGP RIB Manager whether or
                 not it is currently restarting.  The value of this field is
                 only checked when the entity is activated.

                 If bgpRmEntRestartSupported is set to FALSE, then
                 bgpRmEntRestarting must also be set to FALSE.

                 If bgpRmEntRestartSupported and bgpRmEntRestarting are both
                 set to TRUE on activation, then BGP RIB Mananger is
                 undergoing a graceful restart.  Once the graceful restart
                 has completed, bgpRmEntRestarting will be internal set to
                 FALSE.

                 If bgpRmEntRestartSupported is set to TRUE and
                 bgpRmEntRestarting is set to FALSE at the point of
                 activation, the activation will not attempt to recover state
                 from local AFMs and peers.  However, once started, BGP RIB
                 Manager will participate in peer restart processing as
                 needed."
    DEFVAL { false }
    ::= { bgpRmEntEntry 32 }

  bgpRmEntIpv4UniFwdPrsrvd OBJECT-TYPE
    SYNTAX      TruthValue
    MAX-ACCESS  read-create
    STATUS      obsolete
    DESCRIPTION "This value should be set to TRUE if Unicast IPv4
                 forwarding state has been preserved over a restart, and the
                 value of the bgpRmEntRestartSupported field is set to TRUE."
    DEFVAL { false }
    ::= { bgpRmEntEntry 33 }

  bgpRmEntIpv4MultiFwdPrsrvd OBJECT-TYPE
    SYNTAX      TruthValue
    MAX-ACCESS  read-create
    STATUS      obsolete
    DESCRIPTION "This value should be set to TRUE if Multicast IPv4
                 forwarding state has been preserved over a restart, and the
                 value of the bgpRmEntRestartSupported field is set to TRUE."
    DEFVAL { false }
    ::= { bgpRmEntEntry 34 }

  bgpRmEntVpnIpv4FwdPrsrvd OBJECT-TYPE
    SYNTAX      TruthValue
    MAX-ACCESS  read-create
    STATUS      obsolete
    DESCRIPTION "This value should be set to TRUE if VPN-IPv4 forwarding
                 state has been preserved over a restart, and the
                 value of the bgpRmEntRestartSupported field is set to TRUE."
    DEFVAL { false }
    ::= { bgpRmEntEntry 35 }

  bgpRmEntIpv4ArinhJoinStatus OBJECT-TYPE
    SYNTAX      BgpSjStatus
    MAX-ACCESS  read-only
    STATUS      current
    DESCRIPTION "The status of the ARI Interface slave join for querying IPv4
                 next hops.  This is equivalent to the bgpRmArinhJoinStatus
                 field within the bgpRmArinhJoinTable for the IPv4 Unicast
                 table entry."
    ::= { bgpRmEntEntry 36 }

  bgpRmEntIpv4ArinhEntIndex OBJECT-TYPE
    SYNTAX      Unsigned32
    MAX-ACCESS  read-only
    STATUS      current
    DESCRIPTION "Identifies the IPv4 ARI provider entity.  This is equivalent
                 to the bgpRmArinhEntIndex field within the
                 bgpRmArinhJoinTable for the IPv4 Unicast table entry."
    ::= { bgpRmEntEntry 37 }

  bgpRmEntIpv6ArinhJoinStatus OBJECT-TYPE
    SYNTAX      BgpSjStatus
    MAX-ACCESS  read-only
    STATUS      current
    DESCRIPTION "The status of the ARI Interface slave join for querying IPv6
                 next hops.  This is equivalent to the bgpRmArinhJoinStatus
                 field within the bgpRmArinhJoinTable for the IPv6 Unicast
                 table entry."
    ::= { bgpRmEntEntry 38 }

  bgpRmEntIpv6ArinhEntIndex OBJECT-TYPE
    SYNTAX      Unsigned32
    MAX-ACCESS  read-only
    STATUS      current
    DESCRIPTION "Identifies the IPv6 ARI provider entity.  This is equivalent
                 to the bgpRmArinhEntIndex field within the
                 bgpRmArinhJoinTable for the IPv6 Unicast table entry."
    ::= { bgpRmEntEntry 39 }

  bgpRmEntSupportIpv6 OBJECT-TYPE
    SYNTAX      TruthValue
    MAX-ACCESS  read-create
    STATUS      current
    DESCRIPTION "Indicates whether this instance supports connections to BGP
                 peers with IPv6 addresses, and understands IPv6 next hop
                 addresses.  This field can only be set when the row is admin
                 down.  This field must not be set to TRUE unless IPv6 support
                 has been licensed."
    DEFVAL { false }
    ::= { bgpRmEntEntry 40 }

  bgpRmEntStrictConfed OBJECT-TYPE
    SYNTAX      TruthValue
    MAX-ACCESS  read-create
    STATUS      current
    DESCRIPTION "When set to TRUE DC-BGP insists upon strict adherence by peers
                 to the protocol specification, rejecting AS-Path attributes
                 with erroneous AS-Confed segments.  When set to FALSE DC-BGP
                 adopts a more pragmatic approach dealing as best it can with
                 non standard AS-Path information.  This latter approach can be
                 useful in allowing interoperability with older, non-standards
                 compliant peers.

                 This field can only be changed when the Admin Status is down."
    DEFVAL { false }
    ::= { bgpRmEntEntry 41 }

  bgpRmEntOrfSupported OBJECT-TYPE
    SYNTAX      TruthValue
    MAX-ACCESS  read-create
    STATUS      current
    DESCRIPTION "Whether DC-BGP RIB Manager should support Cooperative Route
                 Filtering (commonly referred to as Outbound Route Filtering
                 or ORF).

                 This field can only be changed when the Admin Status is
                 down."
     DEFVAL { false }
     ::= { bgpRmEntEntry 42 }

  bgpRmEntCiscoPrefixSupported OBJECT-TYPE
    SYNTAX      TruthValue
    MAX-ACCESS  read-create
    STATUS      current
    DESCRIPTION "Whether DC-BGP RIB Manager should advertise support for
                 the proprietary Cisco ORF prefix type.

                 This field can only be changed when the Admin Status is
                 down and is only relevant if ORF support is enabled."
     DEFVAL { false }
     ::= { bgpRmEntEntry 43 }

  bgpRmEntSelectDeferTime OBJECT-TYPE
    SYNTAX      Unsigned32 (1..3600)
    UNITS       "seconds"
    MAX-ACCESS  read-create
    STATUS      current
    DESCRIPTION "When DC-BGP is itself restarting this is the upper bound on
                 the amount of time (in seconds) route selection will be
                 deferred.  The value specified should be large enough so as
                 to provide all peers with enough time to send all their
                 routes.  The value must be greater or equal to
                 bgpRmEntRecoveryTime.

                 This field is only relevant if bgpRmEntRestartSupported is
                 TRUE."
    DEFVAL { 120 }
    ::= { bgpRmEntEntry 44 }

  bgpRmEntStalePathTime OBJECT-TYPE
    SYNTAX      Unsigned32 (1..3600)
    UNITS       "seconds"
    MAX-ACCESS  read-create
    STATUS      current
    DESCRIPTION "The maximum time (in seconds) following a peer restart that
                 DC-BGP waits before removing stale routes associated with
                 that peer.  The value must be greater or equal to
                 bgpRmEntMaxRestartTime.

                 This field is only relevant if bgpRmEntRestartSupported is
                 TRUE."
    DEFVAL      { 120 }
    ::= { bgpRmEntEntry 45 }

  bgpRmEntNonPersistentAros OBJECT-TYPE
     SYNTAX      TruthValue
     MAX-ACCESS  read-create
     STATUS      current
     DESCRIPTION "Whether DC-BGP maintains Adj-RIB-Out details for peers.
                  Setting this to TRUE reduces memory requirements but can
                  lead to an increase in processing requirements.  Setting
                  this to TRUE also disables support for the Adj-RIB-Out
                  table.

                  This field can only be changed when the Admin Status is
                  down."
     DEFVAL      { false }
     ::= { bgpRmEntEntry 46 }

  bgpRmEntAroRouteThreshold OBJECT-TYPE
     SYNTAX      Unsigned32
     MAX-ACCESS  read-create
     STATUS      current
     DESCRIPTION "When bgpRmEntNonPersistentAros is set to TRUE this specifies
                  the number of Adj-Rib-Out routes that are permitted to exist
                  before commencing procedures to limit further increases in
                  route occupancy.  A value of 0 indicates that no threshold
                  should be applied and Adj-RIB-Out route numbers will not be
                  aggressively limited.  The lower this value the lower the
                  peak occupancy associated with Adj-RIB-Out routes.

                  Once this threshold is exceeded aggressive techniques are
                  employed to free up Adj-RIB-Out routes as quickly as
                  possible.  A side-affect of this is that the
                  bgpPeerMinRouteAdvertisementInterval,
                  bgpPeerMinASOriginationInterval and
                  bgpPeerMinRouteWithdrawIntervals are ignored, which may lead
                  to increased network traffic.

                  This field can only be changed when the Admin Status is down
                  and is only applicable if bgpRmEntNonPersistentAros is set to
                  TRUE."
     DEFVAL       { 1000000 }
     ::= { bgpRmEntEntry 47 }

  bgpRmEntMaxActiveAroGroups OBJECT-TYPE
     SYNTAX      Unsigned32 (1..4294967295)
     MAX-ACCESS  read-create
     STATUS      current
     DESCRIPTION "When non-persistent AROs are in use, DC-BGP breaks up the
                  processing and reduces the peak occupancy requirements by
                  splitting the Adj-RIB-Outs into a number of processing
                  groups.  The number of AROs in a group is controlled by
                  bgpRmEntNumArosInGroup.  This field is used to specify the
                  maximum number of such groups permitted to contain fully
                  populated AROs.

                  Each group is processed to completion including the
                  transmission of required UPDATEs to peers.  Processing to
                  completion allows the routes in a group to be freed
                  before moving onto the next group thus limiting peak
                  occupancy.  A group is blocked if one or more of its member
                  Adj-RIB-Outs are subject to flow control.  If
                  bgpRmEntMaxActiveAroGroups are blocked then DC-BGP will
                  itself be blocked until a group is unblocked.  Setting a
                  high value for the number of groups decreases the chance of
                  DC-BGP being blocked but increases peak occupancy.

                  This field can only be changed when the Admin Status is down
                  and is only applicable if bgpRmEntNonPersistentAros is set to
                  TRUE."
     DEFVAL       { 2 }
     ::= { bgpRmEntEntry 48 }

  bgpRmEntNumArosInGroup OBJECT-TYPE
     SYNTAX      Unsigned32 (1..4294967295)
     MAX-ACCESS  read-create
     STATUS      current
     DESCRIPTION "The number of Adj-RIB-Outs within a processing group.  The
                  more permitted the better the peer group caching performance
                  but the greater the occupancy requirements.

                  This field can only be changed when the Admin Status is down
                  and is only applicable if bgpRmEntNonPersistentAros is set to
                  TRUE."
     DEFVAL      { 5 }
     ::= { bgpRmEntEntry 49 }

  bgpRmEntNumAroRoutes OBJECT-TYPE
     SYNTAX       Counter32
     MAX-ACCESS   read-only
     STATUS       current
     DESCRIPTION  "The total number of Adj-RIB-Out routes currently allocated
                   across all Adj-RIBs-Out."
     ::= {bgpRmEntEntry 50 }

  bgpRmEntPeakNumAroRoutes OBJECT-TYPE
     SYNTAX       Counter32
     MAX-ACCESS   read-only
     STATUS       current
     DESCRIPTION  "The peak number of Adj-RIB-Out routes that have been
                   allocated at any one time.  This counter can be reset to
                   the current bgpRmEntNumAroRoutes value by setting the
                   bgpRmEntClearStats field to true."
     ::= {bgpRmEntEntry 51 }

  bgpRmEntClearStats OBJECT-TYPE
    SYNTAX      TruthValue
    MAX-ACCESS  read-create
    STATUS      current
    DESCRIPTION "Set to true to clear the applicable statistics.  Reading the
                 value of this field has no meaning."
	DEFVAL      { false }
    ::= { bgpRmEntEntry 52 }

  bgpRmEntFastExtFallover OBJECT-TYPE
    SYNTAX      TruthValue
    MAX-ACCESS  read-create
    STATUS      current
    DESCRIPTION "Indicates whether DC-BGP is configured to perform fast
                 external fallover.

                 When bgpRmEntFastExtFallover is 'true', BGP sessions to
                 directly connected eBGP peers fail as soon as a loss of
                 reachability is detected, instead of waiting for the TCP
                 session to time out.

                 Note that this is only applied to peers that are known to be
                 directly connected - in other words, peers that have
                 bgpPeerTtl set to 1."
    DEFVAL       { false }
    ::= { bgpRmEntEntry 53 }

  bgpRmEntRemainDelayTime OBJECT-TYPE
    SYNTAX      TimeInterval
    MAX-ACCESS  read-only
    STATUS      current
    DESCRIPTION "The maximum time remaining until route selection takes
                 place following a restart, in hundredths of a second.  This
                 is the time left until the timer with duration
                 bgpRmEntSelectDeferTime pops."
    ::= { bgpRmEntEntry 54 }

  bgpRmEntPathAttrs OBJECT-TYPE
    SYNTAX      Gauge32
    MAX-ACCESS  read-only
    STATUS      current
    DESCRIPTION "The total number of path attributes present."
    ::= { bgpRmEntEntry 55 }

  bgpRmEntAggSplitHorizon OBJECT-TYPE
    SYNTAX      TruthValue
    MAX-ACCESS  read-create
    STATUS      current
    DESCRIPTION "Indicates whether DC-BGP should apply split-horizon
                 processing when advertising locally generated aggregate
                 routes to a peer.

                 If set to TRUE, locally generated aggregate routes will not
                 be advertised to any peer that advertised a route that
                 contributed to the aggregate.

                 If set to FALSE, this check will not be performed."
    DEFVAL       { true }
    ::= { bgpRmEntEntry 56 }

  bgpRmEntAggAdvSuppr OBJECT-TYPE
    SYNTAX      TruthValue
    MAX-ACCESS  read-create
    STATUS      current
    DESCRIPTION "This field governs the behaviour of DC-BGP when a
                 locally-generated, summary aggregate route cannot be
                 advertised to a peer.

                 If set to TRUE, DC-BGP should attempt to advertise the
                 suppressed routes that contributed to the aggregate.

                 If set to FALSE, the suppressed routes will not be
                 advertised."
    DEFVAL       { true }
    ::= { bgpRmEntEntry 57 }

  bgpRmEntUpdateGroups OBJECT-TYPE
    SYNTAX      TruthValue
    MAX-ACCESS  read-create
    STATUS      current
    DESCRIPTION "This field indicates that DC-BGP should treat each
                 configured peer group for IBGP peers as an update group.
                 This means that all the peers in the peer group will share
                 a single Adj-RIB-Out and will receive the same set of
                 updates.

                 Note that setting bgpRmEntUpdateGroups to 'true' requires
                 that all of the peers in each IBGP peer group are
                 configured such that they require the same set of routes.
                 This imposes a number of configuration restrictions.

                 Inconsistent entity MIB settings will be rejected.

                 -  Split-horizon aggregates must be disabled
                    (bgpRmEntAggSplitHorizon must be 'false'.

                 -  Non-persistent AROs (NPA) must be disabled
                    (bgpRmEntNonPersistentAros must be 'false').

                 The value of bgpPeerCheckNextHop is ignored (assumed to be
                 'false') for peers in an IBGP peer group when update
                 groups are enabled.

                 If a peer session starts and one of the following values
                 does not match the value for a peer in the peer group's
                 update group, then the new peer will not be added to the
                 update group.

                 -  The negotiated AS number size for the session.
                 -  The configured value for bgpPeerConfedMember.
                 -  The configured value for bgpPeerReflectorClient.

                 The following timer values will be taken from an arbitrary
                 member of the update group and will be applied to the
                 whole update group.  The timer values will therefore be
                 deterministic only if the same values are used for all
                 peers in a peer group.

                 -  bgpPeerMinASOriginationInterval.
                 -  bgpPeerMinRouteAdvertiseInterval.
                 -  bgpPeerMinRouteWithdrawInterval.

                 The local IP address used for next-hop-self will be taken
                 from an arbitrary member of the update group and will be
                 applied to the whole update group.  The local IP address
                 used will therefore be deterministic only if the same
                 values are used for all peers in a peer group.

                 Note also that setting bgpRmEntUpdateGroups to 'true'
                 limits the use of ORF (Outbound Route Filtering) for the
                 peers in an update group.  In particular, DC-BGP will
                 continue to send outbound route filters to peers, but
                 received filters are ignored.

                 In addition, when bgpRmEntUpdateGroups is 'true', the
                 value of bgpPeerConfigPeergr for a peer can only be
                 changed while the peer MIB row admin status is 'down'.

                 This field can only be changed when the Admin Status is
                 down."
    DEFVAL       { false }
    ::= { bgpRmEntEntry 58 }

  bgpRmEntPhase3DelayTime OBJECT-TYPE
    SYNTAX      Unsigned32 (0..3600)
    MAX-ACCESS  read-create
    STATUS      current
    DESCRIPTION "The time in seconds after the number of Established BGP
                 sessions changes from zero to one in which phase 3 work will
                 be postponed if there is still phase 1 or phase 2 work to
                 do.

                 The allows the Loc-RIB to stabilize before advertising
                 routes to peers, preventing the same route being advertised
                 multiple times."
    DEFVAL       { 120 }
    ::= { bgpRmEntEntry 59 }

  bgpRmEntTrapOperState OBJECT-TYPE
    SYNTAX      TruthValue
    MAX-ACCESS  read-create
    STATUS      current
    DESCRIPTION "This value indicates whether or not the Oper State change
                 trap is used.

                 If in use DC-BGP will send a trap whenever the operational
                 status of the RM Entity changes to 'up', 'down' or
                 'actFailed'."
    DEFVAL       { false }
    ::= { bgpRmEntEntry 60 }

-------------------------------------------------------------------------------

  bgpPeer OBJECT IDENTIFIER ::= { bgpMib 3 }

  bgpPeerData OBJECT IDENTIFIER ::= { bgpPeer 1 }

  --
  -- BGP Peer Data Table
  --
  -- This table contains all the information required for each peer including
  -- protocol parameters, statistics and policy configuration.  A row in this
  -- table is created for each peer the RIB Manager knows about.
  --

  bgpPeerTable OBJECT-TYPE
  -- FAMILY-SHORT-NAME BGP_PER
    SYNTAX      SEQUENCE OF BgpPeerEntry
    MAX-ACCESS  not-accessible
    STATUS      current
    DESCRIPTION "BGP peer table.

                 This table contains, one entry per BGP peer,
                 and information about the connections with BGP
                 peers."
    ::= { bgpPeerData 1 }

  bgpPeerEntry OBJECT-TYPE
    SYNTAX      BgpPeerEntry
    MAX-ACCESS  not-accessible
    STATUS      current
    DESCRIPTION "Entry containing information about the connection with
                 a BGP peer."
    INDEX { bgpRmEntIndex,
            bgpPeerLocalAddrType,
            bgpPeerLocalAddr,
            bgpPeerLocalPort,
            bgpPeerRemoteAddrType,
            bgpPeerRemoteAddr,
            bgpPeerRemotePort,
            bgpPeerLocalAddrScopeId}
    ::= { bgpPeerTable 1 }

  BgpPeerEntry ::= SEQUENCE {
      bgpPeerIdentifier                   BgpIdentifier,
      bgpPeerState                        BgpPeerStates,
      bgpPeerRowStatus                    RowStatus,
      bgpPeerAdminStatus                  BgpAdminStatus,
      bgpPeerOperStatus                   BgpOperStatus,
      bgpPeerLocalAddrType                InetAddressType,
      bgpPeerLocalAddr                    InetAddress,
      bgpPeerLocalPort                    InetPortNumber,
      bgpPeerLocalNm                      Integer32,
      bgpPeerRemoteAddrType               InetAddressType,
      bgpPeerRemoteAddr                   InetAddress,
      bgpPeerRemotePort                   InetPortNumber,
      bgpPeerRemoteAs                     BgpAutonomousSystemNumber,
      bgpPeerIndex                        Unsigned32,
      bgpPeerConfedMember                 TruthValue,
      bgpPeerReflectorClient              BgpPeerReflectorClientType,
      bgpPeerTrapEstab                    TruthValue,
      bgpPeerTrapBackw                    TruthValue,
      bgpPeerCapsSupport                  TruthValue,
      bgpPeerLastError                    OCTET STRING,
      bgpPeerLastErrorDataLen             Unsigned32,
      bgpPeerLastErrorData                OCTET STRING,
      bgpPeerFsmEstablishedTime           Gauge32,
      bgpPeerInUpdatesElapsedTime         Gauge32,
      bgpPeerConnectRetryInterval         Unsigned32,
      bgpPeerHoldTimeConfigd              Unsigned32,
      bgpPeerKeepAliveConfigd             Unsigned32,
      bgpPeerMinASOriginationInterval     Unsigned32,
      bgpPeerMinRouteAdvertiseInterval    Unsigned32,
      bgpPeerHoldTime                     Integer32,
      bgpPeerKeepAlive                    Integer32,
      bgpPeerInUpdates                    Counter32,
      bgpPeerOutUpdates                   Counter32,
      bgpPeerInTotalMessages              Counter32,
      bgpPeerOutTotalMessages             Counter32,
      bgpPeerFsmEstablishedTransitions    Counter32,
      bgpPeerConnectRetryCount            Counter32,
      bgpPeerClearCnts                    TruthValue,
      bgpPeerConfigPeergr                 Unsigned32,
      bgpPeerConfigIndex                  Unsigned32,
      bgpPeerConfigRtRefresh              TruthValue,
      bgpPeerConfigMaxPrfx                Integer32,
      bgpPeerConfigDropWarn               BgpDropOrWarn,
      bgpPeerConfigPassive                TruthValue,
      bgpPeerConfigOpenDelay              Unsigned32,
      bgpPeerConfigIdleHold               Unsigned32,
      bgpPeerPassword                     OCTET STRING,
      bgpPeerTtl                          Integer32,
      bgpPeerCheckFirstAsNum              TruthValue,
      bgpPeerAggrInclConfedAS             TruthValue,
      bgpPeerMinRouteWithdrawInterval     Unsigned32,
      bgpPeerStalePathTime                Unsigned32,
      bgpPeerCheckNextHop                 TruthValue,
      bgpPeerLocalAddrScopeId             Unsigned32,
      bgpPeerMaxOrfEntries                Unsigned32,
      bgpPeerOrfEntryCount                Counter32,
      bgpPeerPeeringType                  BgpPeeringType,
      bgpPeerSoftResetWithStoredInfo      TruthValue,
      bgpPeerAllowLocalAs                 Unsigned32,
      bgpPeerDisableSenderLoopDetect      TruthValue,
      bgpPeerDisableRouteRefresh          TruthValue,
      bgpPeerFlapStatsClearStat           TruthValue,
      bgpPeerFlapStatsClearMap            Unsigned32,
      bgpPeerLastErrorRcvd                OCTET STRING,
      bgpPeerLastErrorRcvdTime            TimeStamp,
      bgpPeerLastErrorSent                OCTET STRING,
      bgpPeerLastErrorSentTime            TimeStamp,
      bgpPeerLastState                    BgpPeerStates,
      bgpPeerLastEvent                    BgpPeerEvents,
      bgpPeerCapsSent                     BgpCapabilities,
      bgpPeerCapsRcvd                     BgpCapabilities,
      bgpPeerCapsNegotiated               BgpCapabilities,
      bgpPeerRstrSupport                  BgpPeerRestartSupport,
      bgpPeerRstrFamily                   BgpAfiSafiBits,
      bgpPeerRstrRestarting               TruthValue,
      bgpPeerRstrStatus                   BgpPeerRestartStatus,
      bgpPeerRstrRemTime                  TimeInterval,
      bgpPeerRcvdMsgElapsedTime           TimeInterval,
      bgpPeerIdleHoldRemTime              TimeInterval,
      bgpPeerRouteRefrSent                Counter32,
      bgpPeerRouteRefrRcvd                Counter32,
      bgpPeerNxtHopSlf                    TruthValue,
      bgpPeerThirdPtyNxtHop               TruthValue,
      bgpPeerNxtHopPeer                   TruthValue,
      bgpPeerTrapPrefix                   TruthValue,
      bgpPeerConfigThreshold              Unsigned32,
      bgpPeerMaxPrfxHold                  Unsigned32,
      bgpPeerSelectedLocalAddrType        InetAddressType,
      bgpPeerSelectedLocalAddr            InetAddress,
      bgpPeerSelectedLocalPort            InetPortNumber,
      bgpPeerSelectedRemotePort           InetPortNumber,
      bgpPeerBfdDesired                   TruthValue,
      bgpPeerBfdStatus                    BfdSessionStatus,
      bgpPeerCeaseErrorSubcode            BgpCeaseErrorSubcode,
      bgpPeerConfAltLocalAs               BgpAutonomousSystemNumber,
      bgpPeerSelectedLocalAs              BgpAutonomousSystemNumber,
      bgpPeerSelectedRemoteAs             BgpAutonomousSystemNumber,
      bgpPeerInPrfxes                     Gauge32,
      bgpPeerOutPrfxes                    Gauge32,
      bgpPeerOutPrfxesAdvertised          Gauge32,
      bgpPeerTrapGrHelperState            TruthValue,
      bgpPeerEnableAttributeDiscard       TruthValue
      }

  bgpPeerIdentifier OBJECT-TYPE
    SYNTAX      BgpIdentifier
    MAX-ACCESS  read-only
    STATUS      current
    DESCRIPTION "The BGP Identifier of this entry's BGP peer.

                 This entry is 0000 unless the bgpPeerState is
                 in the openconfirm or the established state.
                 It is equivalent to the bgpM2PeerTable entry
                 bgpM2PeerIdentifier."
    ::= { bgpPeerEntry 2 }

  bgpPeerState OBJECT-TYPE
    SYNTAX      BgpPeerStates
    MAX-ACCESS  read-only
    STATUS      current
    DESCRIPTION "The BGP peer's FSM state.
                 It is equivalent to the bgpM2PeerTable entry
                 bgpM2PeerState."
    ::= { bgpPeerEntry 3 }

  bgpPeerRowStatus OBJECT-TYPE
    SYNTAX      RowStatus
    MAX-ACCESS  read-create
    STATUS      current
    DESCRIPTION "This object type reflects the status of the row within the
                agent.  Note that this is independent of the bgpPeerAdminStatus
                which reflects the underlying peering session itself.  An
                instance of this row is returned by the agent to reflect the
                validity of the current state of this row.  The valid RowStatus
                enumeration values for this are 'active', 'notInService', and
                'notReady'."
    ::= { bgpPeerEntry 4 }

  bgpPeerAdminStatus OBJECT-TYPE
    SYNTAX      BgpAdminStatus
    MAX-ACCESS  read-create
    STATUS      current
    DESCRIPTION "The desired state of the BGP connection.

                 A transition from 'up' to 'down' will cause the BGP  Stop
                 Event to be generated.

                 A transition from 'down' to 'up' will cause the BGP  Start
                 Event to be generated.

                 This parameter can be used to restart BGP peer
                 connections.  Care should be used in providing write
                 access to this object without adequate authentication."
    DEFVAL      { adminStatusDown }
    ::= { bgpPeerEntry 5 }

  bgpPeerOperStatus OBJECT-TYPE
    SYNTAX      BgpOperStatus
    MAX-ACCESS  read-only
    STATUS      current
    DESCRIPTION "The current operation status of this peer.  This usually
                 reflects the desired AdminStatus, but can contain transitional
                 values and failures."
    ::= { bgpPeerEntry 6 }

  bgpPeerLocalAddrType OBJECT-TYPE
    SYNTAX      InetAddressType
    MAX-ACCESS  read-only
    STATUS      current
    DESCRIPTION "The address family of the local end of the peering
                 session.
                 It is equivalent to the bgpM2PeerTable entry
                 bgpM2PeerLocalAddrType.
                 Valid values are: AMB_INETWK_ADDR_TYPE_IPV4 and
                 AMB_INETWK_ADDR_TYPE_IPV6. AMB_INETWK_ADDR_TYPE_IPV6 is only
                 accepted if bgpRmEntSupportIpv6 is TRUE."
    ::= { bgpPeerEntry 7 }

  bgpPeerLocalAddr OBJECT-TYPE
    SYNTAX      InetAddress (SIZE(0..32))
    MAX-ACCESS  read-only
    STATUS      current
    DESCRIPTION "The address of the local end of the peering session.  This is
                 used as an index to the row.  If a zero length address is
                 used, DC-BGP will not bind a specific address but use whatever
                 is available through the NM instance configured in the
                 bgpPeerLocalNm field.  In this case the
                 bgpPeerSelectedLocalAddr field shows which local address is
                 actually used.  If a specific local address is configured,
                 then outbound socket connections will be bound to this
                 address.  If a non-zero bgpPeerLocalPort is specified, then
                 outbound socket connections will be bound to this port.  Note
                 that you can have 2 peer entries to the same remote <address,
                 port> if they come from a different local <address,
                 port>. To configure this each local <address, port> must
                 be specified explicitly and not be zero length.  You will
                 not be allowed to do this if you are listening on all
                 addresses as it will be impossible to tell which peer an
                 incoming connection is for.  You must explicitly listen
                 on each local address in this case.  It is equivalent to
                 the bgpM2PeerTable entry bgpM2PeerLocalAddr."
    ::= { bgpPeerEntry 8 }

  bgpPeerLocalPort OBJECT-TYPE
    SYNTAX      InetPortNumber
    MAX-ACCESS  not-accessible
    STATUS      current
    DESCRIPTION "The local port for the transport connection between the BGP
                 peers.  If set to zero DC-BGP will not bind to a specific port
                 but use any that is available.  If configured to a
                 specific number DC-BGP will attempt to connect out on
                 that port, but will continue to listen on any ports
                 configured in the bgpNmListenTable.  It is equivalent to
                 the bgpM2PeerTable entry bgpM2PeerLocalPort."
    ::= { bgpPeerEntry 9 }

  bgpPeerLocalNm OBJECT-TYPE
    SYNTAX      Integer32
    MAX-ACCESS  read-create
    STATUS      current
    DESCRIPTION "The entity index of the NM to use to connect to this peer.
                 This field can only be changed when the row is not active."
    ::= { bgpPeerEntry 10 }

  bgpPeerRemoteAddrType OBJECT-TYPE
    SYNTAX      InetAddressType
    MAX-ACCESS  read-only
    STATUS      current
    DESCRIPTION "The address family of the remote end of the peering session.
                 It is equivalent to the bgpM2PeerTable entry
                 bgpM2PeerRemoteAddrType.
                 Valid values are: AMB_INETWK_ADDR_TYPE_IPV4 and
                 AMB_INETWK_ADDR_TYPE_IPV6. AMB_INETWK_ADDR_TYPE_IPV6 is only
                 accepted if bgpRmEntSupportIpv6 is TRUE."
    ::= { bgpPeerEntry 11 }

  bgpPeerRemoteAddr OBJECT-TYPE
    SYNTAX      InetAddress (SIZE(0..32))
    MAX-ACCESS  read-only
    STATUS      current
    DESCRIPTION "The address of the remote end of the peering session.
                 It is equivalent to the bgpM2PeerTable entry
                 bgpM2PeerRemoteAddr."
    ::= { bgpPeerEntry 12 }

  bgpPeerRemotePort OBJECT-TYPE
    SYNTAX      InetPortNumber
    MAX-ACCESS  read-only
    STATUS      current
    DESCRIPTION "The remote port for the transport connection between
                 the BGP peers.  A value of zero allows connections from any
                 remote port, otherwise the connection must be from the
                 specified port.  A value of zero also means DC-BGP attempts to
                 connect to port 179.
                 You cannot configure a port of zero if you have already
                 configured a non-zero port for this remote address.  Similarly
                 you cannot configure a non-zero port if you have already
                 configured a port of zero for this remote address.
                 It is equivalent to the bgpM2PeerTable entry
                 bgpM2PeerRemotePort."
    ::= { bgpPeerEntry 13 }

  bgpPeerRemoteAs OBJECT-TYPE
    SYNTAX      BgpAutonomousSystemNumber
    MAX-ACCESS  read-create
    STATUS      current
    DESCRIPTION "The remote autonomous system number.  This field can only be
                 changed when the Admin Status is down.
                 It is equivalent to the bgpM2PeerTable entry
                 bgpM2PeerRemoteAs."
    ::= { bgpPeerEntry 14 }

  bgpPeerIndex OBJECT-TYPE
    SYNTAX      Unsigned32
    MAX-ACCESS  read-only
    STATUS      current
    DESCRIPTION "This value is a unique index for the peer entry in the
                 bgpPeerTable.  It is assigned by the agent at the point
                 of creation of the bgpPeerTable row entry.  While its
                 value is guaranteed to be unique at any time, it is
                 otherwise opaque to the management application with
                 respect to its value or the contiguity of bgpPeerIndex
                 row instance values across rows of the bgpPeerTable.  It
                 is used to provide an index structure for other tables
                 whose data is logically per-peer.
                 It is equivalent to the bgpM2PeerTable entry
                 bgpM2PeerIndex."
    ::= { bgpPeerEntry 15 }

  bgpPeerConfedMember OBJECT-TYPE
    SYNTAX      TruthValue
    MAX-ACCESS  read-create
    STATUS      current
    DESCRIPTION "This value indicates whether or not the peer is a member of
                 the same confederation that this router is in.  This field
                 can only be changed when the Admin Status is down, and can
                 only be set to true if the field bgpRmEntLocalMbrAs is
                 non-zero.  Note that the value should be set to true even
                 if the peer is in the same member AS that this router is in.
                 Member AS numbers are kept internal to the confederation, so
                 it is possible for a member AS number to be the same as the
                 AS number of a neighbor outside the confederation, and so it
                 is not possible to determine whether a peer is in this
                 confederation just by examining the peer's AS number.  The
                 value of this field resolves any ambiguity."
    DEFVAL      { false }
    ::= { bgpPeerEntry 16 }

  bgpPeerReflectorClient OBJECT-TYPE
    SYNTAX      BgpPeerReflectorClientType
    MAX-ACCESS  read-create
    STATUS      current
    DESCRIPTION "This value indicates whether the given peer is a
                 reflector client of this router, or not.  A value of
                 nonClient(0) indicates that this peer is not a reflector
                 client.  A value of client(1) indicates that this peer is a
                 reflector client that is not fully meshed with other
                 reflector clients.  A value of meshedClient(2) indicates
                 that the peer is a reflector client and is fully meshed
                 with all other reflector clients.  This field can only be
                 changed when the Admin Status is down.
                 It is equivalent to the bgpM2PeerReflectorClientTable entry
                 bgpM2PeerReflectorClient."
    DEFVAL      { nonClient }
    ::= { bgpPeerEntry 17 }

  bgpPeerTrapEstab OBJECT-TYPE
    SYNTAX      TruthValue
    MAX-ACCESS  read-create
    STATUS      current
    DESCRIPTION "This value indicates whether or not the Established trap is
                 used.  This field can only be changed when the Admin Status is
                 down."
    DEFVAL { false }
    ::= { bgpPeerEntry 18 }

  bgpPeerTrapBackw OBJECT-TYPE
    SYNTAX      TruthValue
    MAX-ACCESS  read-create
    STATUS      current
    DESCRIPTION "This value indicates whether or not the Backward Transition
                 trap is used.  This field can only be changed when the Admin
                 Status is down."
    DEFVAL { false }
    ::= { bgpPeerEntry 19 }

  bgpPeerCapsSupport OBJECT-TYPE
    SYNTAX      TruthValue
    MAX-ACCESS  read-only
    STATUS      current
    DESCRIPTION "Whether or not this peer accepted our local capabilities
                 optional parameter sent on the OPEN message.  This field will
                 not be relevant until the peer has reached open_confirm
                 state.  Note that this field indicates support or otherwise of
                 the capabilities optional parameter, not a specific
                 capability."
    ::= { bgpPeerEntry 20 }

  bgpPeerLastError OBJECT-TYPE
    SYNTAX      OCTET STRING (SIZE (2))
    MAX-ACCESS  read-only
    STATUS      current
    DESCRIPTION "The last error code and subcode sent or received on this
                 connection.  If no error has occurred, this field is zero.
                 Otherwise, the first byte of this two byte OCTET STRING
                 contains the error code, and the second byte contains the
                 subcode.

                 It is equivalent to the bgpM2PeerErrorsTable entries
                 bgpM2PeerLastErrorReceived and bgpM2PeerLastErrorSent."
    ::= { bgpPeerEntry 21 }

  bgpPeerLastErrorDataLen OBJECT-TYPE
    SYNTAX      Unsigned32 (0..128)
    MAX-ACCESS  read-only
    STATUS      current
    DESCRIPTION "The length of the last error data.  If this is zero no error
                 data was provided or generated."
    ::= { bgpPeerEntry 22 }

  bgpPeerLastErrorData OBJECT-TYPE
    SYNTAX      OCTET STRING (SIZE (128))
    MAX-ACCESS  read-only
    STATUS      current
    DESCRIPTION "The last error code's data seen by this peer on this
                 connection.

                 It is equivalent to the bgpM2PeerErrorsTable entries
                 bgpM2PeerLastErrorReceivedData and
                 bgpM2PeerLastErrorSentData."
    ::= { bgpPeerEntry 23 }

  bgpPeerFsmEstablishedTime OBJECT-TYPE
    SYNTAX      Gauge32
    UNITS       "seconds"
    MAX-ACCESS  read-only
    STATUS      current
    DESCRIPTION "This timer indicates how long this peer has been in the
                 Established state or how long since this peer was last in the
                 Established state.  It is set to zero when a new peer is
                 configured or the router is booted.
                 It is equivalent to the bgpM2PeerEventTimesTable entry
                 bgpM2PeerFsmEstablishedTime."
    ::= { bgpPeerEntry 24 }

  bgpPeerInUpdatesElapsedTime OBJECT-TYPE
    SYNTAX      Gauge32
    UNITS       "seconds"
    MAX-ACCESS  read-only
    STATUS      current
    DESCRIPTION "Elapsed time since the last BGP message was received from the
                 peer.  Each time bgpPeerInUpdates is incremented, the value
                 of this object is set to zero (0).
                 It is equivalent to the bgpM2PeerEventTimesTable entry
                 bgpM2PeerInUpdatesElapsedTime."
    ::= { bgpPeerEntry 25 }

  bgpPeerConnectRetryInterval OBJECT-TYPE
    SYNTAX      Unsigned32 (1..65535)
    UNITS       "seconds"
    MAX-ACCESS  read-create
    STATUS      current
    DESCRIPTION "Time interval for the ConnectRetry timer.  The suggested
                 value for this timer is 120 seconds.  This field can only be
                 changed when the Admin Status is down.
                 It is equivalent to the bgpM2PeerConfiguredTimersTable entry
                 bgpM2PeerConnectRetryInterval."
    DEFVAL { 120 }
    ::= { bgpPeerEntry 26 }

  bgpPeerHoldTimeConfigd OBJECT-TYPE
    SYNTAX      Unsigned32 ( 0 | 3..65535 )
    UNITS       "seconds"
    MAX-ACCESS  read-create
    STATUS      current
    DESCRIPTION "Time interval in seconds for the Hold Time configured for
                 this BGP speaker with this peer.  This value is placed in an
                 OPEN message sent to this peer by this BGP speaker, and is
                 compared with the Hold Time field in an OPEN message
                 received from the peer when determining the Hold Time
                 (bgpPeerHoldTime) with the peer.  This value must not be
                 less than three seconds if it is not zero (0) in which case
                 the Hold Time is NOT to be established with the peer.  The
                 value of this object is only allowed to be zero (0) if the
                 value of bgpPeerKeepAliveConfigd is also zero (0).  The
                 suggested value for this timer is 90 seconds.  This field
                 can only be changed when the Admin Status is down.  It is
                 equivalent to the bgpM2PeerConfiguredTimersTable entry
                 bgpM2PeerHoldTimeConfigured."
       DEFVAL { 90 }
    ::= { bgpPeerEntry 27 }

  bgpPeerKeepAliveConfigd OBJECT-TYPE
    SYNTAX      Unsigned32 ( 0 | 1..21845 )
    UNITS       "seconds"
    MAX-ACCESS  read-create
    STATUS      current
    DESCRIPTION  "Time interval in seconds for the KeepAlive configured for
                 this BGP speaker with this peer.  The value of this object
                 will only determine the KEEPALIVE messages' frequency
                 relative to the value specified in bgpPeerHoldTimeConfigd;
                 the actual time interval for the KEEPALIVE messages is
                 indicated by bgpPeerKeepAlive.  A reasonable maximum value
                 for this timer would be configured to be one third of that
                 of bgpPeerHoldTimeConfigd.

                 The value of this object is only allowed to be zero (0) if the
                 value of bgpPeerHoldTimeConfigd is also zero (0). If the
                 value of this object is zero (0), no periodical KEEPALIVE
                 messages are sent to the peer after the BGP connection
                 has been established.  The suggested value for this timer is
                 30 seconds.  This field can only be changed when the Admin
                 Status is down.  It is equivalent to the
                 bgpM2PeerConfiguredTimersTable entry
                 bgpM2PeerKeepAliveConfigured."
    DEFVAL { 30 }
    ::= { bgpPeerEntry 28 }

  bgpPeerMinASOriginationInterval OBJECT-TYPE
    SYNTAX      Unsigned32 (1..65535)
    UNITS       "seconds"
    MAX-ACCESS  read-create
    STATUS      current
    DESCRIPTION "Time interval in seconds for the
                 timer.  The suggested value for this timer is 15
                 seconds.
                 It is equivalent to the bgpM2PeerConfiguredTimersTable entry
                 bgpM2PeerMinASOrigInterval."
    DEFVAL { 15 }
    ::= { bgpPeerEntry 29 }

  bgpPeerMinRouteAdvertiseInterval OBJECT-TYPE
    SYNTAX      Unsigned32 (1..65535)
    UNITS       "seconds"
    MAX-ACCESS  read-create
    STATUS      current
    DESCRIPTION "Time interval in seconds for the
                 MinRouteAdvertisementInterval timer.  This determines the
                 minimum time between a BGP UPDATE to a peer advertising or
                 withdrawing a route and a subsequent BGP UPDATE to the
                 peer advertising a route to the same destination.

                 The default value for this timer is 30 seconds.  Its value
                 must not be less than bgpPeerMinRouteWithdrawInterval.
                 It is equivalent to the bgpM2PeerConfiguredTimersTable
                 entry bgpM2PeerMinRouteAdverInterval."
    DEFVAL { 5 }
    ::= { bgpPeerEntry 30 }

  bgpPeerHoldTime OBJECT-TYPE
    SYNTAX      Integer32  ( 0 | 3..65535 )
    UNITS       "seconds"
    MAX-ACCESS  read-only
    STATUS      current
    DESCRIPTION "Time interval in seconds for the Hold Timer
                established with the peer.  The value of this
                is calculated by this BGP speaker by using the
                smaller of the value in bgpPeerHoldTimeConfigd
                and the Hold Time received in the OPEN message.
                This value must be at least three seconds if it is
                not zero (0) in which case the Hold Timer has not
                been established with the peer, or, the value of
                bgpPeerHoldTimeConfigd is zero (0).
                It is equivalent to the bgpM2PeerNegotiatedTimersTable entry
                bgpM2PeerHoldTime."
    ::= { bgpPeerEntry 31 }

  bgpPeerKeepAlive OBJECT-TYPE
    SYNTAX      Integer32 ( 0 | 1..21845 )
    UNITS       "seconds"
    MAX-ACCESS  read-only
    STATUS      current
    DESCRIPTION "Time interval in seconds for the KeepAlive timer
                established with the peer.  The value of this
                is calculated by this BGP speaker such that, when
                compared with bgpPeerHoldTime, it has the same
                proportion as what bgpPeerKeepAliveConfigd has
                when compared with bgpPeerHoldTimeConfigd.  If
                the value of this object is zero (0), it indicates
                that the KeepAlive timer has not been established
                with the peer, or, the value of
                bgpPeerKeepAliveConfigd is zero (0).
                It is equivalent to the bgpM2PeerNegotiatedTimersTable entry
                bgpM2PeerKeepAlive."
    ::= { bgpPeerEntry 32 }

  bgpPeerInUpdates OBJECT-TYPE
    SYNTAX      Counter32
    MAX-ACCESS  read-only
    STATUS      current
    DESCRIPTION "The number of BGP UPDATE messages received on this
                 connection.  This object should be initialized to zero
                 (0) when the connection is established.
                 It is equivalent to the bgpM2PeerCountersTable entry
                 bgpM2PeerInUpdates."
    ::= { bgpPeerEntry 33 }

  bgpPeerOutUpdates OBJECT-TYPE
    SYNTAX      Counter32
    MAX-ACCESS  read-only
    STATUS      current
    DESCRIPTION "The number of BGP UPDATE messages transmitted on this
                 connection.  This object should be initialized to zero
                 (0) when the connection is established.
                 It is equivalent to the bgpM2PeerCountersTable entry
                 bgpM2PeerOutUpdates."
    ::= { bgpPeerEntry 34 }

  bgpPeerInTotalMessages OBJECT-TYPE
    SYNTAX      Counter32
    MAX-ACCESS  read-only
    STATUS      current
    DESCRIPTION "The total number of messages received from the remote
                 peer on this connection.  This object should be
                 initialized to zero when the connection is established.
                 It is equivalent to the bgpM2PeerCountersTable entry
                 bgpM2PeerInTotalMessages."
    ::= { bgpPeerEntry 35 }

  bgpPeerOutTotalMessages OBJECT-TYPE
    SYNTAX      Counter32
    MAX-ACCESS  read-only
    STATUS      current
    DESCRIPTION "The total number of messages transmitted to the remote
                 peer on this connection.  This object should be
                 initialized to zero when the connection is established.
                 It is equivalent to the bgpM2PeerCountersTable entry
                 bgpM2PeerOutTotalMessages."
    ::= { bgpPeerEntry 36 }

  bgpPeerFsmEstablishedTransitions OBJECT-TYPE
    SYNTAX      Counter32
    MAX-ACCESS  read-only
    STATUS      current
    DESCRIPTION "The total number of times the BGP FSM transitioned into the
                 established state for this peer.
                 It is equivalent to the bgpM2PeerCountersTable entry
                 bgpM2PeerFsmEstablishedTrans."
    ::= { bgpPeerEntry 37 }

  bgpPeerConnectRetryCount OBJECT-TYPE
    SYNTAX      Counter32
    MAX-ACCESS  read-only
    STATUS      current
    DESCRIPTION "The current connect retry count of this peer.  This is
                 incremented each time the peer session flaps, and is used to
                 determine the time to wait before retrying the session.  Note
                 this is only incremented when an active session terminates
                 abnormally, and not when it simply fails to come up.  This
                 counter can be cleared by setting the bgpPeerClearCnts field
                 to true."
    ::= { bgpPeerEntry 38 }

  bgpPeerClearCnts OBJECT-TYPE
    SYNTAX      TruthValue
    MAX-ACCESS  read-create
    STATUS      current
    DESCRIPTION "Set to clear the counters associated with this Peer.  Reading
                 the value of this field has no meaning."
	DEFVAL { false }
    ::= { bgpPeerEntry 39 }

  bgpPeerConfigPeergr OBJECT-TYPE
    SYNTAX      Unsigned32
    MAX-ACCESS  read-create
    STATUS      current
    DESCRIPTION "The index of the Peer Group this neighbor belongs to."
    DEFVAL { 0 }
    ::= { bgpPeerEntry 40 }

  bgpPeerConfigIndex OBJECT-TYPE
    SYNTAX      Unsigned32
    MAX-ACCESS  read-create
    STATUS      current
    DESCRIPTION "The index of the Policy Configuration Table this peer
                 uses for its policy setup.  This field may be changed when
                 the admin-status is up.  A value of zero indicates that the
                 peer is not associated with any config row."
    DEFVAL { 0 }
    ::= { bgpPeerEntry 41 }

  bgpPeerConfigRtRefresh OBJECT-TYPE
    SYNTAX      TruthValue
    MAX-ACCESS  read-create
    STATUS      current
    DESCRIPTION "This is set to 'true' to trigger a route refresh for this
                 peer.

                 This object always has the value 'false' when read."
    DEFVAL { false }
    ::= { bgpPeerEntry 42 }

  bgpPeerConfigMaxPrfx OBJECT-TYPE
    SYNTAX      Integer32
    MAX-ACCESS  read-create
    STATUS      current
    DESCRIPTION "This object is used in conjunction with the address-family
                 specific bgpPeerAfiSafiConfigMaxPrfx to limit the number of
                 prefixes that can be accepted from this peer.

                 Setting bgpPeerConfigMaxPrfx to a non-zero value sets the
                 maximum number of prefixes (totalled across all supported
                 address families) that can be accepted from this peer.

                 Alternatively, seperate values for the maximum prefix limit
                 can be specified for each address family.  To configure
                 this, set bgpPeerConfigMaxPrfx to zero, and set
                 bgpPeerAfiSafiConfigMaxPrfx for each address family for
                 which a limit is required."
    DEFVAL { 0 }
    ::= { bgpPeerEntry 43 }

  bgpPeerConfigDropWarn OBJECT-TYPE
    SYNTAX      BgpDropOrWarn
    MAX-ACCESS  read-create
    STATUS      current
    DESCRIPTION "This object is used in conjunction with the address-family
                 specific bgpPeerAfiSafiConfigDropWarn to determine whether
                 the session is dropped or a warning is generated when
                 the maximum number of prefixes set is exceeded.

                 Setting bgpPeerConfigDropWarn to 'drop' will cause the
                 session to be dropped when the prefix limit is reached.

                 To configure this behavior independently for different address
                 families, set bgpPeerConfigDropWarn to 'warn', and set
                 the value of bgpPeerAfiSafiConfigDropWarn for each address
                 family as needed."
    DEFVAL { warn }
    ::= { bgpPeerEntry 44 }

  bgpPeerConfigPassive OBJECT-TYPE
    SYNTAX      TruthValue
    MAX-ACCESS  read-create
    STATUS      current
    DESCRIPTION "If TRUE, then no outbound connections will be initiated,
                 and only incoming connections will be accepted.
                 If FALSE, then outbound connections will be attempted to this
                 peer, and incoming connections will be accepted from this
                 peer.  Note that receipt of incoming connections requires a
                 listening socket to be active in the Neighbor Manager
                 instance responsible for this peer.  This field can only be
                 changed when the Admin Status is down."
    DEFVAL { false }
    ::= {bgpPeerEntry 45 }

  bgpPeerConfigOpenDelay OBJECT-TYPE
    SYNTAX      Unsigned32 (0..240)
    UNITS       "seconds"
    MAX-ACCESS  read-create
    STATUS      current
    DESCRIPTION "The delay to enforce in between a TCP connection with this
                 peer becoming established and a BGP Open message being sent.
                 If this delay is zero, then no delay will be injected, and
                 a BGP Open message will be sent as soon as the TCP connection
                 allows it.  This field can only be changed when the Admin
                 Status is down."
    DEFVAL { 0 }
    ::= { bgpPeerEntry 46 }

  bgpPeerConfigIdleHold OBJECT-TYPE
    SYNTAX      Unsigned32 (1..32767)
    UNITS       "seconds"
    MAX-ACCESS  read-create
    STATUS      current
    DESCRIPTION "The time to hold this peer in Idle state after a BGP
                session has progressed beyond Idle state initially and then
                returned to it.  No new connections will be initiated or
                accepted until the peer comes out of Idle state.  By setting
                this field to a large value, this timer can be used to
                provide some level of peer oscillation damping, if desired.
                This field can only be changed when the Admin Status is down."
    DEFVAL { 15 }
    ::= { bgpPeerEntry 47 }

  bgpPeerPassword OBJECT-TYPE
    SYNTAX      OCTET STRING (SIZE (0..128))
    MAX-ACCESS  read-create
    STATUS      current
    DESCRIPTION "The MD5 password used by this peer.  This value is passed to
                 the sockets stub at creation.  bgpPeerPasswordLen must be
                 set to the length of the string.  This field can only be
                 changed when the row is not active."
    ::= { bgpPeerEntry 48 }

  bgpPeerTtl OBJECT-TYPE
    SYNTAX      Integer32
    MAX-ACCESS  read-create
    STATUS      current
    DESCRIPTION "The Time To Live used by the connection on this peer.
                 Directly connected peers should have this set to one.
                 A value of zero indicates the TTL socket option will not be
                 set for this peer.  The sockets layer will therefore insert
                 its default value of TTL into all packets.  This field
                 can only be changed when the Admin Status is down."
    DEFVAL { 0 }
    ::= { bgpPeerEntry 49 }

  bgpPeerCheckFirstAsNum OBJECT-TYPE
    SYNTAX      TruthValue
    MAX-ACCESS  read-create
    STATUS      current
    DESCRIPTION "Whether or not the first AS number in the AS_PATH
                 attribute in an UPDATE received from this peer should be
                 checked to make sure it is the same as the AS number of
                 the peer.  This flag only applies to EBGP peers.  It
                 should be set to True unless the peer has a specific
                 policy that means it does not prepend its AS number so
                 that it is the first in the path.  This field can only be
                 changed when the Admin Status is down."
    DEFVAL { false }
    ::= { bgpPeerEntry 50 }

  bgpPeerAggrInclConfedAS OBJECT-TYPE
    SYNTAX      TruthValue
    MAX-ACCESS  read-create
    STATUS      current
    DESCRIPTION "This value indicates whether or not the neighbor
                 understands aggregated confederation AS_PATH information.
                 If set to FALSE, no confederation AS_PATH information is
                 included in aggregate AS_PATHs."
    DEFVAL { true }
    ::= { bgpPeerEntry 51 }

  bgpPeerMinRouteWithdrawInterval OBJECT-TYPE
    SYNTAX      Unsigned32 (0..65535)
    UNITS       "seconds"
    MAX-ACCESS  read-create
    STATUS      current
    DESCRIPTION "Time interval in seconds for the MinRouteWithdrawInterval
                 timer.  This is the interval which is enforced between
                 advertisement and subsequent withdrawal of a route.

                 The default value for this timer is 30 seconds.  The value
                 must not exceed that of bgpPeerMinRouteAdvertiseInterval."
    DEFVAL { 5 }
    ::= { bgpPeerEntry 52 }

  bgpPeerStalePathTime OBJECT-TYPE
    SYNTAX      Unsigned32
    UNITS       "seconds"
    MAX-ACCESS  read-only
    STATUS      current
    DESCRIPTION "The maximum length of time that DC-BGP will wait before
                 removing stale routes from the peer, following a restart
                 of the peer.  This is advertised by the peer in its OPEN
                 message if it supports graceful restart.  If the
                 advertised value is greater than the
                 bgpRmEntMaxRestartTime, then that value will be used in
                 preference.

                 Specifically, this is the maximum duration that RM will
                 wait between the session going down and receiving an
                 end-of-RIB (EOR) marker."
    DEFVAL { 30 }
    ::= { bgpPeerEntry 53 }

  bgpPeerCheckNextHop OBJECT-TYPE
    SYNTAX      TruthValue
    MAX-ACCESS  read-create
    STATUS      current
    DESCRIPTION "Whether or not to check the BGP next-hop of routes sent to
                 this peer.  If set to TRUE, which is the default, then
                 routes with a BGP next-hop which is the same as the peer's
                 address will not be sent to this peer.  If set to FALSE,
                 then this filtering will not be performed.  In this case,
                 the receiving peer should discard any such routes itself."
    DEFVAL { true }
    ::= { bgpPeerEntry 54 }

  bgpPeerLocalAddrScopeId OBJECT-TYPE
    SYNTAX      Unsigned32
    MAX-ACCESS  not-accessible
    STATUS      current
    DESCRIPTION "The scope ID of the bgpPeerLocalAddr.  The scope ID is
                 required if the address is an IPv6 link-local address.
                 Otherwise, this field must be set to zero."
    ::= { bgpPeerEntry 55 }

  bgpPeerMaxOrfEntries OBJECT-TYPE
    SYNTAX      Unsigned32
    MAX-ACCESS  read-create
    STATUS      current
    DESCRIPTION "This object is used in conjunction with the address-family
                 specific bgpPeerAfiSafiMaxOrfEntries to limit the number of
                 ORF entries of all types that can be accepted from this peer.

                 Setting bgpPeerMaxOrfEntries to a non-zero value sets the
                 maximum number of ORF entries (totalled across all supported
                 address families) that can be accepted from this peer.

                 If this limit is exceeded then the connection will be closed.

                 Alternatively, separate values for the maximum number of ORF
                 entries can be specified for each address family.  To
                 configure this, set bgpPeerMaxOrfEntries to zero, and set
                 bgpPeerAfiSafiMaxOrfEntries for each address family for which
                 a limit is required.

                 The value of this field can be changed at any time.
                 However, the new value will only take effect the next time
                 the session is restarted or when the peer modifies its ORF
                 entries."
    DEFVAL { 100000 }
    ::= { bgpPeerEntry 56 }

  bgpPeerOrfEntryCount OBJECT-TYPE
    SYNTAX      Counter32
    MAX-ACCESS  read-only
    STATUS      current
    DESCRIPTION "The current number of ORF entries of all types that have been
                 received from the peer."
    ::= { bgpPeerEntry 57 }

  bgpPeerPeeringType OBJECT-TYPE
    SYNTAX      BgpPeeringType
    MAX-ACCESS  read-create
    STATUS      current
    DESCRIPTION "The type of peering relationship associated with this peer.
                 Setting this to 'biLateral' will stop the advertisement of
                 routes with the NOPEER community to this peer, and also
                 filter out routes with the NOPEER community received from the
                 peer.  Setting the field to other values is currently only
                 for information.  This field only applies to EBGP peers.  If
                 this field is set for an IBGP peer, the setting will have no
                 effect and will still return 'unspecified'.  This field can
                 only be changed when the Admin Status is down."
    DEFVAL      { unspecified }
    ::= { bgpPeerEntry 58 }

  bgpPeerSoftResetWithStoredInfo OBJECT-TYPE
    SYNTAX      TruthValue
    MAX-ACCESS  read-create
    STATUS      current
    DESCRIPTION "This object is used in conjunction with
                 bgpPeerAfiSafiSoftResetStore to configure 'soft reset with
                 stored routing information'.  This option
                 causes all routes learned from a peer to be stored so that
                 the ARI can be recalculated (for example, due to a change in
                 import policy) without performing a route refresh or
                 restarting the peer session.

                 When bgpPeerSoftResetWithStoredInfo is 'false', BGP does not
                 perform soft reset for any address family.

                 When bgpPeerSoftResetWithStoredInfo is 'true', BGP performs
                 soft reset for those address families for which
                 bgpPeerAfiSafiSoftResetStore is 'true'.

                 This field can only be changed when the Admin Status is down.

                 There is a significant occupancy impact associated with
                 this option.

                 Note that this option overlaps with route refresh (RR) and
                 Outbound Route Filter (ORF) behavior.  To clarify, when this
                 option is enabled, the following also occur for the session
                 to that peer.
                 - Routes are stored in this way, even if the peer advertizes
                   support for RR or ORF.
                 - Route refresh and ORF capabilities continue to be advertized
                   (if configured).
                 - A route refresh will never be sent to this peer, apart from
                   one (containing no ORFs) at the start of the session if
                   both peers support ORF.
                 - ORFs are never sent to the peer.
                 - DC-BGP still responds to RR requests from the peer (if it
                   advertizes the RR capability).
                 - DC-BGP still accepts ORF requests from the peer (if it
                   advertizes the ORF capability)."
    DEFVAL { false }
    ::= { bgpPeerEntry 59 }

  bgpPeerAllowLocalAs OBJECT-TYPE
    SYNTAX      Unsigned32 (0..255)
    MAX-ACCESS  read-create
    STATUS      current
    DESCRIPTION "The number of instances of the local AS identifier that may
                 be contained in the route's AS-Path without rejecting the
                 route.

                 The AS-Path attribute of a BGP route contains the identifiers
                 of the Autonomous Systems traversed by the route.  When
                 a route is received with an AS-Path containing the local
                 AS identifier, it normally indicates a routing loop, and
                 the default behavior is to reject the route.  This object
                 allows this behavior to be over-ridden.

                 This is useful, for example, for VPN routes, where routes
                 from one CE router are advertised to other CE routers
                 through a provider's BGP network.  Two CE routers in
                 the same AS can enable this feature to prevent routes from
                 the other CE from being discarded.

                 When bgpPeerAllowLocalAs is set to a non-zero value, that
                 value is used for all address families, and the value of
                 bgpPeerAfiSafiAllowLocalAs is ignored.

                 Alternatively, the value may be configured independently for
                 each address family.  To do this, set bgpPeerAllowLocalAs to 0
                 and set the value of bgpPeerAfiSafiAllowLocalAs for each
                 address family.

                 Changing the value of this object while the peer is active
                 triggers BGP to refresh its routes from the peer."
    DEFVAL { 0 }
    ::= { bgpPeerEntry 60 }

  bgpPeerDisableSenderLoopDetect OBJECT-TYPE
    SYNTAX      TruthValue
    MAX-ACCESS  read-create
    STATUS      current
    DESCRIPTION "This field is used in conjunction with
                 bgpPeerAfiSafiDisableSndLpDetect to indicate whether BGP
                 should disable sender-side loop detection when sending
                 routes to the peer.

                 By default, BGP performs sender side loop detection.
                 That is, it will not advertise a route to a peer if
                 the AS-Path of the route already contains the peer's AS
                 number.  A peer would typically discard such routes, so
                 this is normally a useful optimization.

                 However, the peer may be configured to accept such routes
                 (see bgpPeerAllowLocalAs).  In this case it is
                 necessary to disable sender-side loop detection, by setting
                 bgpPeerDisableSndLpDetect to 'true'.

                 Sender-side loop detection may be disabled independently
                 for each address family.  When bgpPeerDisableSndLpDetect
                 is set to 'true', set bgpPeerAfiSafiDisableSndLpDetect to
                 'true' or 'false' to disable or enable sender-side loop
                 detection for each address family.

                 If the value of this object is changed while the peer session
                 is active, BGP will check for any routes that need to be
                 advertised or withdrawn as a result of the change."
    DEFVAL { false }
    ::= { bgpPeerEntry 61 }

  bgpPeerDisableRouteRefresh OBJECT-TYPE
    SYNTAX      TruthValue
    MAX-ACCESS  read-create
    STATUS      current
    DESCRIPTION "Indicates that DC-BGP should not advertise support for
                 Route Refresh messages to this peer.

                 When this flag is set, DC-BGP will not advertise support for
                 Route Refresh messages to this peer.  When this flag is not
                 set, DC-BGP will advertise support for Route Refresh
                 messages to this peer."
    DEFVAL { false }
    ::= { bgpPeerEntry 62 }

  bgpPeerFlapStatsClearStat OBJECT-TYPE
    SYNTAX      TruthValue
    MAX-ACCESS  read-create
    STATUS      current
    DESCRIPTION "This field is set to clear the bgpFlapStatsFlapcnt in all
                 entries in the bgpNlriTable matching routes from this peer.
                 This will not unsuppress a suppressed route.

                 If the field bgpPeerFlapStatsClearMap is also set, this
                 defines the Route Map used to determine the set of routes
                 for which the bgpFlapStatsFlapcnt should be reset.  If
                 bgpPeerFlapStatsClearMap is not set, all routes from this
                 peer will be reset.

                 Reading the value of this field has no meaning.  The field
                 is not returned on a MIB Get."
    DEFVAL { false }
    ::= { bgpPeerEntry 63 }

  bgpPeerFlapStatsClearMap OBJECT-TYPE
    SYNTAX      Unsigned32
    MAX-ACCESS  read-create
    STATUS      current
    DESCRIPTION "This field is set with bgpPeerFlapStatsClearStat to
                 restrict the set of routes for which bgpFlapStatsFlapcnt is
                 reset when bgpPeerFlapStatsClearStat is set.

                 This field is an index to the bgpRouteMapTable.  The
                 bgpFlapStatsFlapcnt in all routes matching the Route Map are
                 cleared.  Entries in the Route Map may be set to permit (to
                 cause a match) or to deny (to prevent a match).

                 Setting this field without bgpPeerFlapStatsClearStat has no
                 meaning.

                 Reading the value of this field has no meaning.  The field
                 is not returned on a MIB Get."
    DEFVAL { 0 }
    ::= { bgpPeerEntry 64 }

  bgpPeerLastErrorRcvd OBJECT-TYPE
    SYNTAX      OCTET STRING (SIZE(2))
    MAX-ACCESS  read-only
    STATUS      current
    DESCRIPTION "The last error code and subcode received from the peer on
                 this connection.

                 If no error has been received from the peer, this field is
                 zero.  Otherwise, the first byte of this two byte OCTET
                 STRING contains the error code, and the second byte contains
                 the subcode.

                 It is equivalent to the bgpM2PeerErrorsTable entry
                 bgpM2PeerLastErrorReceived."
    ::= { bgpPeerEntry 65 }

  bgpPeerLastErrorRcvdTime OBJECT-TYPE
    SYNTAX      TimeStamp
    MAX-ACCESS  read-only
    STATUS      current
    DESCRIPTION "The value of sysUpTime when the last error was received
                 from the peer on this connection.

                 If no error has been received from the peer, this field is
                 zero.

                 It is equivalent to the bgpM2PeerErrorsTable entry
                 bgpM2PeerLastErrorReceivedTime."
    ::= { bgpPeerEntry 66 }

  bgpPeerLastErrorSent OBJECT-TYPE
    SYNTAX      OCTET STRING (SIZE(2))
    MAX-ACCESS  read-only
    STATUS      current
    DESCRIPTION "The last error code and subcode sent to the peer on this
                 connection.

                 If no error has been sent to the peer, this field is zero.
                 Otherwise, the first byte of this two byte OCTET STRING
                 contains the error code, and the second byte contains the
                 subcode.

                 It is equivalent to the bgpM2PeerErrorsTable entry
                 bgpM2PeerLastErrorSent."
    ::= { bgpPeerEntry 67 }

  bgpPeerLastErrorSentTime OBJECT-TYPE
    SYNTAX      TimeStamp
    MAX-ACCESS  read-only
    STATUS      current
    DESCRIPTION "The value of sysUpTime when the last error was sent to the
                 peer on this connection.

                 If no error has been sent to the peer, this field is zero.

                 It is equivalent to the bgpM2PeerErrorsTable entry
                 bgpM2PeerLastErrorSentTime."
    ::= { bgpPeerEntry 68 }

  bgpPeerLastState OBJECT-TYPE
    SYNTAX      BgpPeerStates
    MAX-ACCESS  read-only
    STATUS      current
    DESCRIPTION "The BGP peer's previous FSM state."
    ::= { bgpPeerEntry 69 }

  bgpPeerLastEvent OBJECT-TYPE
    SYNTAX      BgpPeerEvents
    MAX-ACCESS  read-only
    STATUS      current
    DESCRIPTION "The last input to be made to the BGP peer's FSM."
    ::= { bgpPeerEntry 70 }

  bgpPeerCapsSent OBJECT-TYPE
    SYNTAX      BgpCapabilities
    MAX-ACCESS  read-only
    STATUS      current
    DESCRIPTION "The capabilities announced to the peer on the most recent
                 Open message sent to the peer.  This field is set to zero
                 before the first Open message is sent to the peer, and
                 is unchanged if the session comes down."
    ::= { bgpPeerEntry 71 }

  bgpPeerCapsRcvd OBJECT-TYPE
    SYNTAX      BgpCapabilities
    MAX-ACCESS  read-only
    STATUS      current
    DESCRIPTION "The capabilities received on the most recent Open message
                 received from the peer.  This field is set to zero before
                 the first Open message is received from the peer, and is
                 unchanged if the session comes down.

                 In the event that the peer signals a capability that DC-BGP
                 does not recognize, this field will only contain those
                 capabilities that DC-BGP recognizes.  A user should walk the
                 bgpPeerCapsRcvdTable to confirm the full list of
                 capabilities received from the peer."
    ::= { bgpPeerEntry 72 }

  bgpPeerCapsNegotiated OBJECT-TYPE
    SYNTAX      BgpCapabilities
    MAX-ACCESS  read-only
    STATUS      current
    DESCRIPTION "The capabilities negotiated for the session with the peer.
                 This field is set to zero before Open messages have been
                 exchanged with the peer, and is unchanged if the session
                 comes down."
    ::= { bgpPeerEntry 73 }

  bgpPeerRstrSupport OBJECT-TYPE
    SYNTAX      BgpPeerRestartSupport
    MAX-ACCESS  read-only
    STATUS      current
    DESCRIPTION "Whether the peer supports graceful restart.  This field is
                 set to 'none' before an Open message has been received from
                 a peer, and is unchanged if the session comes down."
    ::= { bgpPeerEntry 74 }

  bgpPeerRstrFamily OBJECT-TYPE
    SYNTAX      BgpAfiSafiBits
    MAX-ACCESS  read-only
    STATUS      current
    DESCRIPTION "The address and subaddress families for which the peer
                 supports graceful restart.  This field is set to zero before
                 an Open message has been received from a peer, and is
                 unchanged if the session comes down."
    ::= { bgpPeerEntry 75 }

  bgpPeerRstrRestarting OBJECT-TYPE
    SYNTAX      TruthValue
    MAX-ACCESS  read-only
    STATUS      current
    DESCRIPTION "Whether the peer is currently in the process of
                 restarting."
    ::= { bgpPeerEntry 76 }

  bgpPeerRstrStatus OBJECT-TYPE
    SYNTAX      BgpPeerRestartStatus
    MAX-ACCESS  read-only
    STATUS      current
    DESCRIPTION "The current state of the peer's restart processing.  If
                 bgpPeerRstrRestarting is false, this is set to
                 notRestarting."
    ::= { bgpPeerEntry 77 }

  bgpPeerRstrRemTime OBJECT-TYPE
    SYNTAX      TimeInterval
    MAX-ACCESS  read-only
    STATUS      current
    DESCRIPTION "The time remaining in the current restart state, in
                 hundredths of a second.  If bgpPeerRstrStatus is
                 notRestarting, this is set to zero."
    ::= { bgpPeerEntry 78 }

  bgpPeerRcvdMsgElapsedTime OBJECT-TYPE
    SYNTAX      TimeInterval
    MAX-ACCESS  read-only
    STATUS      current
    DESCRIPTION "The elapsed time in hundredths of a second since anything
                 was received from the socket from this peer.  If nothing has
                 been received from the socket from this peer, this field is
                 set to zero.  If the session comes down this value continues
                 to increase."
    ::= { bgpPeerEntry 79 }

  bgpPeerIdleHoldRemTime OBJECT-TYPE
    SYNTAX      TimeInterval
    MAX-ACCESS  read-only
    STATUS      current
    DESCRIPTION "For a peer in 'idle' state, the time remaining in
                 hundredths of a second until DC-BGP will try to reactivate
                 the connection.  If the peer is not in 'idle' state, this is
                 set to zero."
    ::= { bgpPeerEntry 80 }

  bgpPeerRouteRefrSent OBJECT-TYPE
    SYNTAX      Counter32
    MAX-ACCESS  read-only
    STATUS      current
    DESCRIPTION "The number of Route Refresh messages sent to the peer.  If
                 the session comes down this value is unchanged, and will
                 continue to increment if the session is reestablished."
    ::= { bgpPeerEntry 81 }

  bgpPeerRouteRefrRcvd OBJECT-TYPE
    SYNTAX      Counter32
    MAX-ACCESS  read-only
    STATUS      current
    DESCRIPTION "The number of Route Refresh messages received from the
                 peer.  If the session comes down this value is unchanged,
                 and will continue to increment if the session is
                 reestablished."
    ::= { bgpPeerEntry 82 }

  bgpPeerNxtHopSlf OBJECT-TYPE
    SYNTAX      TruthValue
    MAX-ACCESS  read-create
    STATUS      current
    DESCRIPTION "Whether or not the peer has next hop self configured.

                 Setting this field to 'true' causes the value of
                 bgpPeerThirdPtyNxtHop to be ignored.

                 Address family specific configuration of this option is
                 provided by the field bgpPeerAfiSafiNxtHopSlf.

                 When bgpPeerNxtHopSlf is 'false', BGP does not perform
                 next-hop-self for any address family.

                 When bgpPeerNxtHopSlf is 'true', BGP performs
                 next-hop-self for those address families for which
                 bgpPeerAfiSafiNxtHopSlf is 'true'."
    DEFVAL { false }
    ::= { bgpPeerEntry 83 }

  bgpPeerThirdPtyNxtHop OBJECT-TYPE
    SYNTAX      TruthValue
    MAX-ACCESS  read-create
    STATUS      current
    DESCRIPTION "Whether or not the local BGP speaker should advertise routes
                 received from this peer using third party next hop (this is
                 optional behaviour described in the BGP specification).

                 This field is only used when exporting routes to other EBGP
                 peers, and when bgpPeerNxtHopSlf is 'false'."
    DEFVAL { true }
    ::= { bgpPeerEntry 84 }

  bgpPeerNxtHopPeer OBJECT-TYPE
    SYNTAX      TruthValue
    MAX-ACCESS  read-create
    STATUS      current
    DESCRIPTION "Whether or not the local BGP speaker should override the use
                 of third party next hop by an EBGP peer.  If an EBGP peer
                 speaker uses third party next hop, routes learnt from the peer
                 may specify a next hop belonging to a router that the local
                 BGP speaker does not peer with.

                 If this field is set to 'true', then all data forwarded along
                 a route learnt from an EBGP peer will be sent to the EBGP
                 peer.  The peer's address is put into the BGP next hop field
                 when the route is advertised to IBGP peers.

                 If set to 'false', then data is sent to the next hop
                 specified by the peer.  The field is only used when importing
                 routes from EBGP."
    DEFVAL { false }
    ::= { bgpPeerEntry 85 }

  bgpPeerTrapPrefix OBJECT-TYPE
    SYNTAX      TruthValue
    MAX-ACCESS  read-create
    STATUS      current
    DESCRIPTION "Used in conjunction with bgpPeerAfiSafiTrapPrefix to
                 determine whether BGP issues an SNMP trap when the number of
                 prefixes received from this peer reaches the maximum number
                 of prefixes allowed, set by bgpPeerConfigMaxPrfx and
                 bgpPeerAfiSafiConfigMaxPrfx, or the warning threshold set by
                 bgpPeerConfigThreshold and bgpPeerAfiSafiConfigThreshold.

                 To disable sending of traps for all address families, set
                 bgpPeerTrapPrefix to 'false'.

                 To enable the sending of traps, set bgpPeerTrapPrefix to
                 'true' and set bgpPeerAfiSafiTrapPrefix to 'true' for those
                 address families for which this behavior is required."
    DEFVAL { false }
    ::= { bgpPeerEntry 86 }

  bgpPeerConfigThreshold OBJECT-TYPE
    SYNTAX      Unsigned32 (0..100)
    MAX-ACCESS  read-create
    STATUS      current
    DESCRIPTION "A percentage of the limit set by bgpPeerConfigMaxPrfx.
                 When the number of prefixes received from this peer reaches
                 this threshold, BGP issues a warning.  The action carried
                 out by DC-BGP depends on the value of bgpPeerTrapPrefix and
                 bgpPeerAfiSafiTrapPrefix.

                 This field is not used if bgpPeerConfigMaxPrfx is set to
                 zero.  This field sets a threshold for all address families
                 received from a peer.

                 To configure a threshold for individual families, set
                 bgpPeerConfigThreshold to zero and set
                 bgpPeerAfiSafiConfigThreshold to the required threshold for
                 each address family."
    DEFVAL { 75 }
    ::= { bgpPeerEntry 87 }

  bgpPeerMaxPrfxHold OBJECT-TYPE
    SYNTAX      Unsigned32 (0..86400)
    MAX-ACCESS  read-create
    STATUS      current
    DESCRIPTION "The time interval in seconds between when this BGP session
                 is torn down due to the number of prefixes received from
                 this peer exceeding the maximum in
                 bgpPeerConfigMaxPrfx(AfiSafi) and when BGP attempts to
                 reestablish the session.

                 To configure a time interval for individual families, set
                 bgpPeerMaxPrfxHold to zero and set bgpPeerAfiSafiMaxPrfxHold
                 to the required time interval for each address family.

                 If both bgpPeerMaxPrfxHold and bgpPeerAfiSafiMaxPrfxHold are
                 set to zero for an address family, the session is not
                 reestablished.  An attempt to configure a non-zero value
                 less than 30 seconds is rejected."
    DEFVAL { 90 }
    ::= { bgpPeerEntry 88 }

    bgpPeerSelectedLocalAddrType OBJECT-TYPE
    SYNTAX      InetAddressType
    MAX-ACCESS  read-only
    STATUS      current
    DESCRIPTION "The address family selected for the local end of the peering
                 session.  If a connection exists then this field will be
                 identical to bgpPeerLocalAddrType.  A value of none implies
                 that there is currently no connection to this peer."
    ::= { bgpPeerEntry 89 }

  bgpPeerSelectedLocalAddr OBJECT-TYPE
    SYNTAX      InetAddress (SIZE(0..32))
    MAX-ACCESS  read-only
    STATUS      current
    DESCRIPTION "The address selected for the local end of the peering
                 session.  If a connection exists and bgpPeerLocalAddr is
                 specified then these two fields will be identical."
    ::= { bgpPeerEntry 90 }

   bgpPeerSelectedLocalPort OBJECT-TYPE
    SYNTAX      InetPortNumber
    MAX-ACCESS  read-only
    STATUS      current
    DESCRIPTION "The local port selected for transport connection between the
                 BGP peers.  If bgpPeerLocalPort is non-zero and a connection
                 exists then these two fields will be identical.  A value of
                 zero implies that there is currently no connection to this
                 peer."
    ::= { bgpPeerEntry 91 }

   bgpPeerSelectedRemotePort OBJECT-TYPE
    SYNTAX      InetPortNumber
    MAX-ACCESS  read-only
    STATUS      current
    DESCRIPTION "The remote port selected for the transport connection between
                 the BGP peers.  If bgpPeerRemotePort is non-zero and a
                 connection exists then these two fields will be identical.  A
                 value of zero implies that there is currently no connection to
                 this peer."
   ::= { bgpPeerEntry 92 }

   bgpPeerBfdDesired OBJECT-TYPE
    SYNTAX      TruthValue
    MAX-ACCESS  read-create
    STATUS      current
    DESCRIPTION "Indicates whether Bidirectional Forwarding Detection (BFD) is
                 desired for this peer.

                 If the NM entity managing this peer session (configured using
                 bgpPeerLocalNm) does not have an active join to a BFD provider
                 (configured using bgpNmEntBfdEntityIndex), then BFD will not be
                 used on this interface regardless of the value of this field.

                 This field can only be changed when the row is not active."
    DEFVAL { false }
    ::= { bgpPeerEntry 93 }

   bgpPeerBfdStatus OBJECT-TYPE
    SYNTAX      BfdSessionStatus
    MAX-ACCESS  read-only
    STATUS      current
    DESCRIPTION "BFD session state for this peer."
    ::= { bgpPeerEntry 94 }

   bgpPeerCeaseErrorSubcode OBJECT-TYPE
    SYNTAX      BgpCeaseErrorSubcode
    MAX-ACCESS  read-create
    STATUS      current
    DESCRIPTION "The error subcode to be sent in the Cease Notification
                 messages triggered by MIB requests that set the state of
                 the BGP connection from 'up' to 'down'.  If set to 'none'
                 then DC-BGP chooses the subcode itself.

                 This field does not affect the error subcode for Cease
                 Notification messages triggered for other reasons."
    DEFVAL      { none }
    ::= { bgpPeerEntry 95 }

   bgpPeerConfAltLocalAs OBJECT-TYPE
    SYNTAX      BgpAutonomousSystemNumber
    MAX-ACCESS  read-create
    STATUS      current
    DESCRIPTION "An alternative 'local AS' number that can be used to
                 create a session to this peer.  This is used when merging
                 two ASs into a single AS.

                 A value of zero means 'not configured'.  If a non-zero
                 value is configured, then the AS number included in the
                 OPEN messages sent when trying to create the peer session
                 will alternate between the 'normal' local AS number
                 (defined by bgpRmEntLocalAs) and the 'alternative' local
                 AS number defined here.

                 If this is an iBGP peer, then bgpPeerRemoteAs must have
                 the same value as bgpRmEntLocalAs.  In this case, an OPEN
                 message received from the remote peer will be accepted if
                 it contains an AS number that matches either
                 bgpPeerConfAltLocalAs or bgpPeerRemoteAs.

                 If this is an eBGP peer, then bgpPeerRemoteAs must contain
                 the remote peer's AS number.  An OPEN message received
                 from the remote peer will be accepted only if it contains
                 an AS number that matches bgpPeerRemoteAs.

                 This field can be changed at any time.  However, if the
                 field is changed while the row is admin_status UP, the
                 change will only take effect after the row has been
                 deactivated and reactivated, thus forcing the peer session
                 to be restarted.

                 If this router is a member of a confederation, then this
                 field is meaningless and is ignored."
    DEFVAL      { 0 }
    ::= { bgpPeerEntry 96 }

   bgpPeerSelectedLocalAs OBJECT-TYPE
    SYNTAX      BgpAutonomousSystemNumber
    MAX-ACCESS  read-only
    STATUS      current
    DESCRIPTION "The local AS number used on this session.

                 If bgpPeerConfAltLocalAs is set to a non-zero value, then
                 the session might have been set up advertising one of two
                 'local AS' numbers (bgpRmEntLocalAs or
                 bgpPeerConfAltLocalAs).  This field reports which local AS
                 number was used.

                 If, as normal, bgpPeerConfAltLocalAs is zero, then the AS
                 number advertised for the session (and reported by this
                 field) is bgpRmEntLocalAs, or bgpRmEntLocalMbrAs (if this
                 router is in a confederation along with the peer).

                 If the bgpPeerState is not 'established', then this field is
                 zero."
    ::= { bgpPeerEntry 97 }

   bgpPeerSelectedRemoteAs OBJECT-TYPE
    SYNTAX      BgpAutonomousSystemNumber
    MAX-ACCESS  read-only
    STATUS      current
    DESCRIPTION "The remote AS number used on this session.

                 If bgpPeerConfAltLocalAs is set to a non-zero value, and
                 if this is an iBGP peer, then the remote peer might have
                 advertised one of two AS numbers (bgpPeerRemoteAs or
                 bgpPeerConfAltLocalAs).  This field reports which AS
                 number was advertised by the remote peer.

                 If bgpPeerConfAltLocalAs is zero, then the AS number
                 advertised by the remote peer (and reported in this
                 this field) must equal bgpPeerRemoteAs.

                 If the bgpPeerState is not 'established', then this field is
                 zero."
    ::= { bgpPeerEntry 98 }

   bgpPeerInPrfxes OBJECT-TYPE
    SYNTAX      Gauge32
    MAX-ACCESS  read-only
    STATUS      current
    DESCRIPTION "The total number of prefixes received from this peer.  This is
                 equivalent to the sum of bgpPrfxInPrfxes for all AFI/SAFI
                 combinations that this peer supports."
    ::= { bgpPeerEntry 99 }

   bgpPeerOutPrfxes OBJECT-TYPE
    SYNTAX      Gauge32
    MAX-ACCESS  read-only
    STATUS      current
    DESCRIPTION "The number of prefixes that are installed in all of this
                 peer's Adj-RIB-Outs.  This is equivalent to the sum of
                 bgpPrfxOutPrfxes for all AFI/SAFI combinations that this peer
                 supports.  Note that this value is impacted by the
                 bgpRmEntNonPersistentAros field since, if that field is set
                 to TRUE, routes are removed from the Adj-RIB-Out to reduce
                 occupancy."
    ::= { bgpPeerEntry 100 }

   bgpPeerOutPrfxesAdvertised OBJECT-TYPE
    SYNTAX      Gauge32
    MAX-ACCESS  read-only
    STATUS      current
    DESCRIPTION "The total number of prefixes advertised to this peer.  This is
                 equivalent to the sum of bgpPrfxOutPrfxesAdvertised for all
                 AFI/SAFI combinations that this peer supports.  This field is
                 not affected by the bgpRmEntNonPersistentAros field.  Note
                 that even if bgpRmEntNonPersistentAros is FALSE the value of
                 this field may differ from bgpPeerOutPrfxes since that field
                 includes recently withdrawn routes which are undergoing
                 suppression procedures."
    ::= { bgpPeerEntry 101 }

  bgpPeerTrapGrHelperState OBJECT-TYPE
    SYNTAX      TruthValue
    MAX-ACCESS  read-create
    STATUS      current
    DESCRIPTION  "This value indicates whether or not the Graceful Restart
                  helper trap is used.

                  If in use for this peer, DC-BGP will send a trap whenever
                  the peer restart status changes - in other words, whenever
                  the value of bgpPeerRstrStatus for the peer changes."
    DEFVAL       { false }
    ::= { bgpPeerEntry 102 }

  bgpPeerEnableAttributeDiscard OBJECT-TYPE
    SYNTAX      TruthValue
    MAX-ACCESS  read-create
    STATUS      current
    DESCRIPTION  "This value indicates whether or not the 'attribute
                  discard' error handling mechanism is used for BGP UPDATE
                  messages received from this peer.  This mechanism applies
                  when a BGP UPDATE message is received containing a
                  malformed AGGREGATOR, AS4_AGGREGATOR, AS4_PATH or
                  ATOMIC_AGGREGATE attribute.

                  When set to 'false', the error handling mechanism defined
                  in the original BGP specification is used, and the BGP
                  session is reset.  This can lead to session flapping and
                  network instability, even though routing is not adversely
                  affected by the presence of these malformed attributes.

                  When set to 'true', the alternative error handling
                  mechanism of 'attribute discard' is used, where the
                  attribute is dropped and the rest of the BGP UPDATE
                  message is processed as normal.

                  Use of 'attribute discard' error handling is fixed at the
                  start of a BGP session, so changes to this field take
                  effect at the start of the next session.

                  If the peer belongs to a peer group, then this field is
                  ignored and the value of bgpPeergrEnableAtrributeDiscard
                  is examined instead."
    DEFVAL       { false }
    ::= { bgpPeerEntry 103 }

------------------------------------------------------------------------------

  --
  -- Peer <AFI, SAFI> configuration table.
  --

  bgpPeerAfiSafiTable OBJECT-TYPE
  -- FAMILY-SHORT-NAME BGP_AFI
    SYNTAX      SEQUENCE OF BgpPeerAfiSafiEntry
    MAX-ACCESS  not-accessible
    STATUS      current
    DESCRIPTION "Peer <AFI, SAFI> configuration table.

                 This table allows a user to configure peer characteristics
                 on a per AFI/SAFI basis.

                 Rows in this table cannot be created or destroyed manually.
                 A table entry for each supported address family is created
                 automatically when an entry in the bgpPeerTable is created.
                 The entries are destroyed when the bgpPeerTable entry
                 is destroyed."
    ::= { bgpPeerData 2 }

  bgpPeerAfiSafiEntry OBJECT-TYPE
    SYNTAX      BgpPeerAfiSafiEntry
    MAX-ACCESS  not-accessible
    STATUS      current
    DESCRIPTION "Peer <AFI, SAFI> configuration table entry."
    INDEX { bgpRmEntIndex,
            bgpPeerLocalAddrType,
            bgpPeerLocalAddr,
            bgpPeerLocalPort,
            bgpPeerRemoteAddrType,
            bgpPeerRemoteAddr,
            bgpPeerRemotePort,
            bgpPeerLocalAddrScopeId,
            bgpPeerAfiSafiAfi,
            bgpPeerAfiSafiSafi }
    ::= { bgpPeerAfiSafiTable 1 }

  BgpPeerAfiSafiEntry ::= SEQUENCE {
      bgpPeerAfiSafiAfi                   BgpAfi,
      bgpPeerAfiSafiSafi                  BgpSafi,
      bgpPeerAfiSafiDisable               TruthValue,
      bgpPeerAfiSafiConfigRtRefresh       TruthValue,
      bgpPeerAfiSafiAllowLocalAs          Unsigned32,
      bgpPeerAfiSafiDisableSndLpDetect    TruthValue,
      bgpPeerAfiSafiNxtHopSlf             TruthValue,
      bgpPeerAfiSafiOrigDefault           TruthValue,
      bgpPeerAfiSafiOrigDefaultRtMap      Unsigned32,
      bgpPeerAfiSafiSoftResetStore        TruthValue,
      bgpPeerAfiSafiConfigMaxPrfx         Unsigned32,
      bgpPeerAfiSafiConfigDropWarn        BgpDropOrWarn,
      bgpPeerAfiSafiTrapPrefix	          TruthValue,
      bgpPeerAfiSafiConfigThreshold       Unsigned32,
      bgpPeerAfiSafiMaxPrfxHold           Unsigned32,
      bgpPeerAfiSafiMaxOrfEntries         Unsigned32
      }

  bgpPeerAfiSafiAfi OBJECT-TYPE
    SYNTAX      BgpAfi
    MAX-ACCESS  not-accessible
    STATUS      current
    DESCRIPTION "The AFI index into the peer <AFI, SAFI> table."
    ::= { bgpPeerAfiSafiEntry 8 }

  bgpPeerAfiSafiSafi OBJECT-TYPE
    SYNTAX      BgpSafi
    MAX-ACCESS  not-accessible
    STATUS      current
    DESCRIPTION "The SAFI index into the peer <AFI, SAFI> table."
    ::= { bgpPeerAfiSafiEntry 9 }

  bgpPeerAfiSafiDisable OBJECT-TYPE
    SYNTAX      TruthValue
    MAX-ACCESS  read-create
    STATUS      current
    DESCRIPTION "When bgpPeerAfiSafiDisable is 'true', BGP will not advertise
                 Multiprotocol support to the peer for this address family.

                 When bgpPeerAfiSafiDisable is 'false', BGP will advertise
                 Multiprotocol support to the peer if support for the address
                 family has been enabled in the corresponding
                 bgpRmAfiSafiTable entry.

                 Any update to this object will take effect the next time
                 that the bgpPeerTable entry is activated (bgpPeerAdminStatus
                 is set to 'adminStatusUp')."
    DEFVAL { true }
    ::= { bgpPeerAfiSafiEntry 10 }

  bgpPeerAfiSafiConfigRtRefresh OBJECT-TYPE
    SYNTAX      TruthValue
    MAX-ACCESS  read-create
    STATUS      current
    DESCRIPTION "Set this to 'true' to trigger BGP to send a Route Refresh
                 to the peer for this address family.

                 Setting the object will only have an effect if a BGP session
                 to the peer is active.

                 This object always has the value 'false' when read."
    DEFVAL { false }
    ::= { bgpPeerAfiSafiEntry 11 }

  bgpPeerAfiSafiAllowLocalAs OBJECT-TYPE
    SYNTAX      Unsigned32 (0..255)
    MAX-ACCESS  read-create
    STATUS      current
    DESCRIPTION "The number of instances of the local AS identifier that may
                 be contained in the route's AS-Path without rejecting the
                 route.

                 The AS-Path attribute of a BGP route contains the identifiers
                 of the Autonomous Systems traversed by the route.  When
                 a route is received with an AS-Path containing the local
                 AS identifier, it normally indicates a routing loop, and
                 the default behavior is to reject the route.  This object
                 allows this behavior to be over-ridden.

                 This is useful, for example, for VPN routes, where routes
                 from one CE router are advertised to other CE routers sites
                 through a provider's BGP network.  Two CE routers in
                 the same AS can enable this feature to prevent routes from
                 the other CE from being discarded.

                 If bgpPeerAllowLocalAs is set to a non-zero value, then that
                 value is used for all address families, and the value of
                 bgpPeerAfiSafiAllowLocalAs is ignored.

                 To configure values independently for each address family, set
                 bgpPeerAllowLocalAs to 0 and set the values of
                 bgpPeerAfiSafiAllowLocalAs as required.

                 Changing the value of this object while the peer is active
                 triggers BGP to refresh its routes from the peer."
    DEFVAL { 0 }
    ::= { bgpPeerAfiSafiEntry 12 }

  bgpPeerAfiSafiDisableSndLpDetect OBJECT-TYPE
    SYNTAX      TruthValue
    MAX-ACCESS  read-create
    STATUS      current
    DESCRIPTION "Gives finer control of the sender-side loop detection
                 configuration provided by bgpPeerDisableSenderLoopDetect.

                 By default, BGP performs sender side loop detection.  That
                 is, it will not advertise a route to a peer if the AS-Path
                 of the route already contains the peer's AS number.  A
                 peer would typically discard such routes, so this is
                 normally a useful optimization.

                 However, the peer may be configured to accept such routes
                 (see bgpPeerAfiSafiAllowLocalAs).  In this case it is
                 necessary to disable sender-side loop detection.

                 When bgpPeerDisableSenderLoopDetect is 'true', BGP
                 disables sender-side loop detection for those address
                 families for which bgpPeerAfiSafiDisableSndLpDetect is
                 'true'.

                 When bgpPeerDisableSenderLoopDetect is 'false',
                 sender-side loop detection is not disable for any address
                 families.

                 If the value of this object is changed while the peer session
                 is active, BGP will check for any routes that need to be
                 advertised or withdrawn as a result of the change."
    DEFVAL { true }
    ::= { bgpPeerAfiSafiEntry 13 }

  bgpPeerAfiSafiNxtHopSlf OBJECT-TYPE
    SYNTAX      TruthValue
    MAX-ACCESS  read-create
    STATUS      current
    DESCRIPTION "Gives finer control of the next-hop-self configuration
                 provided by bgpPeerNxtHopSlf.

                 When bgpPeerNxtHopSlf is 'false', BGP does not perform
                 next-hop-self for any address family.

                 When bgpPeerNxtHopSlf is 'true', BGP performs next-hop-self
                 for those address families for which bgpPeerAfiSafiNxtHopSlf
                 is 'true'.

                 If the value of this object is changed while the peer session
                 is active, BGP will check for any routes that need to be
                 advertised or withdrawn as a result of the change."
    DEFVAL { true }
    ::= { bgpPeerAfiSafiEntry 14 }

  bgpPeerAfiSafiOrigDefault OBJECT-TYPE
    SYNTAX      TruthValue
    MAX-ACCESS  read-create
    STATUS      current
    DESCRIPTION "Indicates whether BGP should originate a default route to
                 the peer for this address family.

                 BGP cannot originate default VPN routes and so
                 bgpPeerAfiSafiOrigDefault cannot be set to 'true' if
                 bgpPeerAfiSafiSafi is 'mplsBgpVpn'.

                 This is because there is no single default route for a VPN
                 address family - there may be one for each VRF.  If a
                 default VPN route is required, it should should be
                 redistributed from the corresponding VRF.  This ensures
                 that the default VPN route is advertised by BGP along with
                 the associated label, route distinguisher and route
                 targets.

                 Similarly, BGP does not support the allocation of a label
                 for a default route, and so bgpPeerAfiSafiOrigDefault
                 cannot be set to 'true' if bgpPeerAfiSafiSafi is
                 'labeled'.

                 Default routes are meaningless for L2VPN auto-discovery
                 and signaling, so bgpPeerAfiSafiOrigDefault cannot be set
                 to 'true' if bgpPeerAfiSafiAfi is 'l2vpn'.

                 The origination of default routes may optionally be
                 conditional based on policy.  If this is required, then
                 set bgpPeerAfiSafiOrigDefaultRtMap to specify a route map.

                 If no route map is specified
                 (bgpPeerAfiSafiOrigDefaultRtMap is zero), then default
                 route origination is based solely on the setting of
                 bgpPeerAfiSafiOrigDefault."
    DEFVAL { false }
    ::= { bgpPeerAfiSafiEntry 15 }

  bgpPeerAfiSafiOrigDefaultRtMap OBJECT-TYPE
    SYNTAX      Unsigned32
    MAX-ACCESS  read-create
    STATUS      current
    DESCRIPTION "Configured policy for origination of default routes.

                 The value of bgpPeerAfiSafiOrigDefaultRtMap is only examined
                 if bgpPeerAfiSafiOrigDefault is 'true'.

                 It identifies a route map consisting of all rows in the
                 bgpRouteMapTable with bgpRouteMapIndex set to
                 bgpPeerAfiSafiOrigDefaultRtMap.

                 The route map has two purposes.

                - The match clauses are used for conditional advertisement
                  of the default route.  A default route is only originated
                  for an address family if bgpPeerAfiSafiOrigDefault
                  is 'true' and if there is at least one route in the loc-RIB
                  matching the route map.

                - The set clauses of the route map determine the attributes
                  of the originated default route.

                 Note that route maps may consist of multiple bgpRouteMapTable
                 entries.  These bgpRouteMapTable entries can be configured
                 to match a specific address family.  Any such bgpRouteMapTable
                 entry that does not match the address family for this
                 bgpPeerAfiSafiTable entry is ignored.

                 These route maps should be configured as follows.

                - To restrict a route map to a particular AFI/SAFI, specify
                  bgpRouteMapMaAfi and bgpRouteMapMaSafi.

                - Each route map should specify an IP prefix list to match
                  on.  This is not mandated by DC-BGP, but other types of
                  matches may have a performance impact.

                - Each IP prefix match is assumed to be an exact match.  In
                  other words, DC-BGP treats each bgpIpPreTable entry as
                  having bgpIpPreLe = bgpIpPreLen, and bgpIpPreGe = 0."
    DEFVAL { 0 }
    ::= { bgpPeerAfiSafiEntry 16 }

  bgpPeerAfiSafiSoftResetStore OBJECT-TYPE
    SYNTAX      TruthValue
    MAX-ACCESS  read-create
    STATUS      current
    DESCRIPTION "Gives finer control of the soft reset configuration provided
                 by bgpPeerSoftResetWithStoredInfo.

                 When bgpPeerSoftResetWithStoredInfo is 'false', BGP does not
                 perform soft reset for any address family.

                 When bgpPeerSoftResetWithStoredInfo is 'true', BGP performs
                 soft reset for those address families for which
                 bgpPeerAfiSafiSoftResetStore is 'true'.

                 Any update to this object will take effect the next time
                 that the peer session reactivates."
    DEFVAL { true }
    ::= { bgpPeerAfiSafiEntry 17 }

  bgpPeerAfiSafiConfigMaxPrfx OBJECT-TYPE
    SYNTAX      Unsigned32
    MAX-ACCESS  read-create
    STATUS      current
    DESCRIPTION "Gives finer control of the maximum prefix configuration
                 provided by bgpPeerConfigMaxPrfx.

                 To configure address family specific values for the maximum
                 number of prefixes that can be accepted from the peer,
                 set bgpPeerConfigMaxPrfx to zero, and set
                 bgpPeerAfiSafiConfigMaxPrfx to the limit for this address
                 family."
    DEFVAL { 0 }
    ::= { bgpPeerAfiSafiEntry 18 }

  bgpPeerAfiSafiConfigDropWarn OBJECT-TYPE
    SYNTAX      BgpDropOrWarn
    MAX-ACCESS  read-create
    STATUS      current
    DESCRIPTION "Gives finer control of the configuration provided by
                 bgpPeerConfigDropWarn, which determines the behavior when the
                 maximum prefix limit is reached.

                 To configure whether the session is dropped or a warning is
                 behavior independently for different address
                 families, set bgpPeerConfigDropWarn to 'warn', and set
                 the value of bgpPeerAfiSafiConfigDropWarn for each address
                 family as needed."
    DEFVAL { drop }
    ::= { bgpPeerAfiSafiEntry 19 }

  bgpPeerAfiSafiTrapPrefix OBJECT-TYPE
    SYNTAX      TruthValue
    MAX-ACCESS  read-create
    STATUS      current
    DESCRIPTION "Gives finer control of the configuration provided by
                 bgpPeerTrapPrefix, which determines whether BGP issues an
                 SNMP trap when the number of prefixes received from this
                 peer for this address family reaches the maximum number of
                 prefixes allowed, set by bgpPeerConfigThreshold or
                 bgpPeerAfiSafiConfigMaxPrfx, or the warning threshold set by
                 bgpPeerConfigMaxPrfx or bgpPeerAfiSafiConfigThreshold.

                 To disable sending of traps for all address families, set
                 bgpPeerTrapPrefix to 'false'.

                 To enable the sending of traps, set bgpPeerTrapPrefix to
                 'true' and set bgpPeerTrapPrefix to 'true' for those address
                 families for which this behavior is required."
    DEFVAL { true }
    ::= { bgpPeerAfiSafiEntry 20 }

  bgpPeerAfiSafiConfigThreshold OBJECT-TYPE
    SYNTAX      Unsigned32 (0..100)
    MAX-ACCESS  read-create
    STATUS      current
    DESCRIPTION "Gives finer control of the threshold configuration
                 provided by bgpPeerConfigThreshold.  When the number of
                 prefixes received from this peer for this address family
                 reaches this threshold, BGP issues a warning.  The action
                 carried out by BGP depends on the value of
                 bgpPeerTrapPrefix and bgpPeerAfiSafiTrapPrefix.

                 This field is not used if bgpPeerConfigMaxPrfx and
                 bgpPeerAfiSafiConfigMaxPrfx are set to zero.

                 To configure a threshold for individual families, set
                 bgpPeerConfigThreshold to zero and set
                 bgpPeerAfiSafiConfigThreshold to the required threshold for
                 each address family."
    DEFVAL { 75 }
    ::= { bgpPeerAfiSafiEntry 21 }

  bgpPeerAfiSafiMaxPrfxHold OBJECT-TYPE
    SYNTAX      Unsigned32 (0..86400)
    MAX-ACCESS  read-create
    STATUS      current
    DESCRIPTION "Gives finer control of the configuration provided by
                 bgpPeerMaxPrfxHold, which determines the time interval in
                 seconds between when this BGP session is torn down due to
                 the number of prefixes received from this peer exceeding the
                 maximum in bgpPeerConfigMaxPrfx(AfiSafi) and when BGP
                 attempts to reestablish the session.

                 To configure a time interval for individual families, set
                 bgpPeerMaxPrfxHold to zero and set bgpPeerAfiSafiMaxPrfxHold
                 to the required time interval for each address family.

                 If both bgpPeerMaxPrfxHold and bgpPeerAfiSafiMaxPrfxHold are
                 set to zero for an address family, the session is not
                 reestablished.  An attempt to configure a non-zero value
                 less than 30 seconds is rejected."
    DEFVAL { 90 }
    ::= { bgpPeerAfiSafiEntry 22 }

  bgpPeerAfiSafiMaxOrfEntries OBJECT-TYPE
    SYNTAX      Unsigned32
    MAX-ACCESS  read-create
    STATUS      current
    DESCRIPTION "Gives finer control of the maximum number of ORF entries
                 configuration provided by bgpPeerMaxOrfEntries.

                 To configure address family specific values for the maximum
                 number of ORF entries that can be accepted from the peer,
                 set bgpPeerMaxOrfEntries to zero, and set
                 bgpPeerAfiSafiMaxOrfEntries to the limit for this address
                 family."
    DEFVAL { 0 }
    ::= { bgpPeerAfiSafiEntry 23 }

-------------------------------------------------------------------------------

  bgpPeerCaps OBJECT IDENTIFIER ::= { bgpPeer 2 }

  --
  -- Received Capabilities
  --
  -- This table contains information about the capabilities received from
  -- peers.  Each row in the table corresponds to a capability received from a
  -- peer.
  --

  bgpPeerCapsRcvdTable OBJECT-TYPE
  -- FAMILY-SHORT-NAME BGP_PCP
    SYNTAX      SEQUENCE OF BgpPeerCapsRcvdEntry
    MAX-ACCESS  not-accessible
    STATUS      current
    DESCRIPTION "This table contains contains the capabilities
                 that are supported for a given peer.
                 It is equivalent to the bgpM2PeerCapsReceivedTable."
    ::= { bgpPeerCaps 1 }

  bgpPeerCapsRcvdEntry OBJECT-TYPE
    SYNTAX      BgpPeerCapsRcvdEntry
    MAX-ACCESS  not-accessible
    STATUS      current
    DESCRIPTION "These entries are keyed by a peer index and the BGP
                 Capability Code and index."
    INDEX { bgpRmEntIndex,
            bgpPeerIndex,
            bgpPeerCapRcvdCode,
            bgpPeerCapRcvdIndex }
    ::= { bgpPeerCapsRcvdTable 1 }

  BgpPeerCapsRcvdEntry ::= SEQUENCE {
      bgpPeerCapRcvdCode         Unsigned32,
      bgpPeerCapRcvdIndex        Unsigned32,
      bgpPeerCapRcvdValue        OCTET STRING
      }

  bgpPeerCapRcvdCode OBJECT-TYPE
    SYNTAX      Unsigned32 (0..255)
    MAX-ACCESS  not-accessible
    STATUS      current
    DESCRIPTION "The BGP Capability Advertisement Capability Code."
    ::= { bgpPeerCapsRcvdEntry 3 }

  bgpPeerCapRcvdIndex OBJECT-TYPE
    SYNTAX      Unsigned32 (1..128)
    MAX-ACCESS  not-accessible
    STATUS      current
    DESCRIPTION "Multiple instances of a given capability may be sent
                 by a BGP speaker.  This variable is used to index them."
    ::= { bgpPeerCapsRcvdEntry 4 }

  bgpPeerCapRcvdValue OBJECT-TYPE
    SYNTAX      OCTET STRING (SIZE(0..255))
    MAX-ACCESS  read-only
    STATUS      current
    DESCRIPTION "The value of the announced capability."
    ::= { bgpPeerCapsRcvdEntry 5 }

  --
  -- Sent Capabilities
  --
  -- This table contains information about the capabilities sent to peers.
  -- Each row in the table corresponds to a capability sent to a peer.
  --

  bgpPeerCapsSentTable OBJECT-TYPE
  -- FAMILY-SHORT-NAME BGP_PCP
    SYNTAX      SEQUENCE OF BgpPeerCapsSentEntry
    MAX-ACCESS  not-accessible
    STATUS      current
    DESCRIPTION "This table contains contains the capabilities
                 that are announced to a given peer.
                 It is equivalent to the bgpM2PeerCapsAnnouncedTable."
    ::= { bgpPeerCaps 2 }

  bgpPeerCapsSentEntry OBJECT-TYPE
    SYNTAX      BgpPeerCapsSentEntry
    MAX-ACCESS  not-accessible
    STATUS      current
    DESCRIPTION "These entries are keyed by a peer index and the BGP
                 Capability Code and index."
    INDEX { bgpRmEntIndex,
            bgpPeerIndex,
            bgpPeerCapSentCode,
            bgpPeerCapSentIndex }
    ::= { bgpPeerCapsSentTable 1 }

  BgpPeerCapsSentEntry ::= SEQUENCE {
      bgpPeerCapSentCode         Unsigned32,
      bgpPeerCapSentIndex        Unsigned32,
      bgpPeerCapSentValue        OCTET STRING
      }

  bgpPeerCapSentCode OBJECT-TYPE
    SYNTAX      Unsigned32 (0..255)
    MAX-ACCESS  not-accessible
    STATUS      current
    DESCRIPTION "The BGP Capability Advertisement Capability Code."
    ::= { bgpPeerCapsSentEntry 3 }

  bgpPeerCapSentIndex OBJECT-TYPE
    SYNTAX      Unsigned32 (1..128)
    MAX-ACCESS  not-accessible
    STATUS      current
    DESCRIPTION "Multiple instances of a given capability may be sent
                 by a BGP speaker.  This variable is used to index them."
    ::= { bgpPeerCapsSentEntry 4 }

  bgpPeerCapSentValue OBJECT-TYPE
    SYNTAX      OCTET STRING (SIZE(0..255))
    MAX-ACCESS  read-only
    STATUS      current
    DESCRIPTION "The value of the announced capability."
    ::= { bgpPeerCapsSentEntry 5 }

-------------------------------------------------------------------------------

  bgpPeerCntrs OBJECT IDENTIFIER ::= { bgpPeer 3 }

  --
  -- Per-Peer Prefix Counters
  --
  -- A statistics table keeping track of the number of prefixes received and
  -- sent on a per peer per AFI/SAFI basis.
  --

  bgpPrfxCntrsTable OBJECT-TYPE
  -- FAMILY-SHORT-NAME BGP_PCT
    SYNTAX      SEQUENCE OF BgpPrfxCntrsEntry
    MAX-ACCESS  not-accessible
    STATUS      current
    DESCRIPTION "Additional per-peer, per AFI/SAFI counters for prefixes.
                 It is equivalent to the bgpM2PrefixCountersTable."
    ::= { bgpPeerCntrs 1 }

  bgpPrfxCntrsEntry OBJECT-TYPE
    SYNTAX      BgpPrfxCntrsEntry
    MAX-ACCESS  not-accessible
    STATUS      current
    DESCRIPTION "Entry containing information about a bgp-peer's prefix
                 counters."
    INDEX { bgpRmEntIndex,
            bgpPeerIndex,
            bgpPrfxCntrsAfi,
            bgpPrfxCntrsSafi }
    ::= { bgpPrfxCntrsTable 1 }

  BgpPrfxCntrsEntry ::= SEQUENCE {
      bgpPrfxCntrsAfi               BgpAfi,
      bgpPrfxCntrsSafi              BgpSafi,
      bgpPrfxInPrfxes               Gauge32,
      bgpPrfxInPrfxesAccepted       Gauge32,
      bgpPrfxInPrfxesRejected       Gauge32,
      bgpPrfxOutPrfxes              Gauge32,
      bgpPrfxOutPrfxesAdvertised    Gauge32,
      bgpPrfxCntrsUserData          OCTET STRING,
      bgpPrfxInPrfxesFlapped        Gauge32,
      bgpPrfxInPrfxesFlapSuppressed Gauge32,
      bgpPrfxInPrfxesFlapHistory    Gauge32,
      bgpPrfxInPrfxesActive         Gauge32,
      bgpPrfxInPrfxesDeniedByPol    Gauge32,
      bgpPrfxNumLocRibRoutes        Gauge32
      }

  bgpPrfxCntrsAfi OBJECT-TYPE
    SYNTAX      BgpAfi
    MAX-ACCESS  not-accessible
    STATUS      current
    DESCRIPTION "The AFI index of the per-peer, per prefix counters."
    ::= { bgpPrfxCntrsEntry 3 }

  bgpPrfxCntrsSafi OBJECT-TYPE
    SYNTAX      BgpSafi
    MAX-ACCESS  not-accessible
    STATUS      current
    DESCRIPTION "The SAFI index of the per-peer, per prefix counters."
    ::= { bgpPrfxCntrsEntry 4 }

  bgpPrfxInPrfxes OBJECT-TYPE
    SYNTAX      Gauge32
    MAX-ACCESS  read-only
    STATUS      current
    DESCRIPTION "The number of prefixes received from a peer and are
                 stored in the Adj-RIB-In for that peer."
    ::= { bgpPrfxCntrsEntry 5 }

  bgpPrfxInPrfxesAccepted OBJECT-TYPE
    SYNTAX      Gauge32
    MAX-ACCESS  read-only
    STATUS      current
    DESCRIPTION "The number of prefixes for a peer that are installed
                 in the Adj-RIB-In and are eligible to become active
                 in the Loc-Rib."
    ::= { bgpPrfxCntrsEntry 6 }

  bgpPrfxInPrfxesRejected OBJECT-TYPE
    SYNTAX      Gauge32
    MAX-ACCESS  read-only
    STATUS      current
    DESCRIPTION "The number of prefixes for a peer that are installed
                 in the Adj-RIB-In and are NOT eligible to become active
                 in the Loc-Rib."
    ::= { bgpPrfxCntrsEntry 7 }

  bgpPrfxOutPrfxes OBJECT-TYPE
    SYNTAX      Gauge32
    MAX-ACCESS  read-only
    STATUS      current
    DESCRIPTION "The number of prefixes for a peer that are installed
                 in that peer's Adj-RIB-Out.  Note that this value is impacted
                 by the bgpRmEntNonPersistentAros field since, if that field
                 is set to TRUE, routes are removed from the Adj-RIB-Out
                 to reduce occupancy."
    ::= { bgpPrfxCntrsEntry 8 }

  bgpPrfxOutPrfxesAdvertised OBJECT-TYPE
    SYNTAX      Gauge32
    MAX-ACCESS  read-only
    STATUS      current
    DESCRIPTION "The number of advertised prefixes currently associated with
                 the peer.  This field is not affected by the
                 bgpRmEntNonPersistentAros field.  Note that even if
                 bgpRmEntNonPersistentAros is FALSE the value of this field may
                 differ from bgpPrfxOutPrfxes since that field includes
                 recently withdrawn routes which are undergoing suppression
                 procedures."
    ::= { bgpPrfxCntrsEntry 9 }

  bgpPrfxCntrsUserData OBJECT-TYPE
    SYNTAX      OCTET STRING(SIZE (4))
    MAX-ACCESS  read-only
    STATUS      current
    DESCRIPTION "User data for this BGP prefix counters entry."
    ::= { bgpPrfxCntrsEntry 10 }

  bgpPrfxInPrfxesFlapped OBJECT-TYPE
    SYNTAX      Gauge32
    MAX-ACCESS  read-only
    STATUS      current
    DESCRIPTION "The number of prefixes for a peer that are installed in
                 the Adj-RIB-In and for which RIB Manager is tracking a route
                 flap damping penalty."
    ::= { bgpPrfxCntrsEntry 11 }

  bgpPrfxInPrfxesFlapSuppressed OBJECT-TYPE
    SYNTAX      Gauge32
    MAX-ACCESS  read-only
    STATUS      current
    DESCRIPTION "The number of prefixes for a peer that are installed in
                 the Adj-RIB-In and that are suppressed as a result of route
                 flapping."
    ::= { bgpPrfxCntrsEntry 12 }

  bgpPrfxInPrfxesFlapHistory OBJECT-TYPE
    SYNTAX      Gauge32
    MAX-ACCESS  read-only
    STATUS      current
    DESCRIPTION "The number of prefixes for a peer that are not currently
                 in the Adj-RIB-In, but which have an associated route flap
                 damping penalty."
    ::= { bgpPrfxCntrsEntry 13 }

  bgpPrfxInPrfxesActive OBJECT-TYPE
    SYNTAX      Gauge32
    MAX-ACCESS  read-only
    STATUS      current
    DESCRIPTION "The number of prefixes for a peer that are installed in
                 the Adj-RIB-In and are marked as 'active' in the Loc-Rib.

                 This field only contains the count of prefixes for AFI/SAFIs
                 for which bgpRmAfiSafiAdvertiseInactive is set to 'true'."
    ::= { bgpPrfxCntrsEntry 14 }

  bgpPrfxInPrfxesDeniedByPol OBJECT-TYPE
    SYNTAX      Gauge32
    MAX-ACCESS  read-only
    STATUS      current
    DESCRIPTION "When 'soft reset with stored routing information' is enabled
                 for a peer with the given AFI/SAFI, this is the number of
                 stored prefixes from the peer that have failed import policy
                 checks and so have not been installed in the Adj-RIB-In.

                 Otherwise, this field is set to zero."
    ::= { bgpPrfxCntrsEntry 15 }

  bgpPrfxNumLocRibRoutes OBJECT-TYPE
    SYNTAX      Gauge32
    MAX-ACCESS  read-only
    STATUS      current
    DESCRIPTION "The number of prefixes for a peer that are installed in
                 the Adj-RIB-In and are included as the 'best' route in the
                 Loc-RIB."
    ::= { bgpPrfxCntrsEntry 16 }

-------------------------------------------------------------------------------

  bgpRib OBJECT IDENTIFIER ::= { bgpMib 4 }

  --
  -- BGP NLRI Data
  --
  -- This table contains per route information including routes, attributes
  -- and flap statistics if the route is being damped.
  --

  bgpNlriTable OBJECT-TYPE
  -- FAMILY-SHORT-NAME BGP_NLR
    SYNTAX      SEQUENCE OF BgpNlriEntry
    MAX-ACCESS  not-accessible
    STATUS      current
    DESCRIPTION "The BGP-4 Received Path Attribute Table contains information
                 about paths to destination networks received from all BGP4
                 peers.  It is equivalent to the bgpM2NlriTable, with
                 additional fields from the bgpM2PathAttrTable, and fields
                 to monitor the Route Flap damping state of the NLRI.

                 This table must contain an identical set of fields to the
                 bgpNlriPrefixTable.  All non-index fields must be in the same
                 order in this table and the bgpNlriPrefixTable."
    ::= { bgpRib 1 }

  bgpNlriEntry OBJECT-TYPE
    SYNTAX      BgpNlriEntry
    MAX-ACCESS  not-accessible
    STATUS      current
    DESCRIPTION "Information about a path to a network."
    INDEX { bgpRmEntIndex,
            bgpNlriPeerOrAfm,
            bgpNlriPeerAfmIndex,
            bgpNlriAfi,
            bgpNlriSafi,
            bgpNlriPrfx,
            bgpNlriPrfxLen }
    ::= { bgpNlriTable 1 }

  BgpNlriEntry ::= SEQUENCE {
      bgpNlriPeerOrAfm                 BgpPeerOrAfm,
      bgpNlriPeerAfmIndex              Unsigned32,
      bgpNlriAfi                       BgpAfi,
      bgpNlriSafi                      BgpSafi,
      bgpNlriPrfx                      InetAddress,
      bgpNlriPrfxLen                   InetAddressPrefixLength,
      bgpNlriBest                      TruthValue,
      bgpNlriAsSize                    BgpAsSize,
      bgpNlriASPathStr                 OCTET STRING,
      bgpPathAttrOrigin                BgpOriginCode,
      bgpPathAttrNextHop               InetAddress,
      bgpPathAttrMultiExitDisc         Unsigned32,
      bgpPathAttrLocalPref             Unsigned32,
      bgpPathAttrAtomicAggregate       BgpPathAttrAtomicAggPresence,
      bgpPathAttrAggregatorAS          BgpAutonomousSystemNumber,
      bgpPathAttrAggregatorAddr        BgpIdentifier,
      bgpPathAttrCalcLocalPref         Unsigned32,
      bgpPathAttrOrigId                BgpIdentifier,
      bgpPathAttrWeight                Unsigned32,
      bgpFlapStatsConfig               Unsigned32,
      bgpFlapStatsPenalty              Unsigned32,
      bgpFlapStatsFlapcnt              Unsigned32,
      bgpFlapStatsSupprsd              TruthValue,
      bgpFlapStatsTimeleft             Unsigned32,
      bgpFlapStatsCleardamp            TruthValue,
      bgpFlapStatsClearstat            TruthValue,
      bgpNlriEcmp                      TruthValue,
      bgpPathAttrAsPathLimAs           BgpAutonomousSystemNumber,
      bgpPathAttrAsPathLimUpper        Unsigned32,
      bgpNlriIsActive                  BgpNlriIsActiveFlag,
      bgpNlriUserData                  OCTET STRING,
      bgpNlriStale                     TruthValue,
      bgpNlriFlapStartTime             TimeStamp,
      bgpNlriLinkLocalNextHop          InetAddress
      }

  bgpNlriPeerOrAfm OBJECT-TYPE
    SYNTAX      BgpPeerOrAfm
    MAX-ACCESS  not-accessible
    STATUS      current
    DESCRIPTION "Whether this route was learned from a BGP peer or an AFM."
    ::= { bgpNlriEntry 2 }

  bgpNlriPeerAfmIndex OBJECT-TYPE
    SYNTAX      Unsigned32
    MAX-ACCESS  not-accessible
    STATUS      current
    DESCRIPTION "The index of either the BGP peer or AFM this route was learned
                 from.  If bgpNlriPeerOrAfm is peer, this field is equivalent
                 to a bgpPeerIndex.  If bgpNlriPeerOrAfm is afm, this field is
                 equivalent to a bgpRmAfmJoin."
    ::= { bgpNlriEntry 3 }

  bgpNlriAfi OBJECT-TYPE
    SYNTAX      BgpAfi
    MAX-ACCESS  not-accessible
    STATUS      current
    DESCRIPTION "The address family of the prefix for this NLRI."
    ::= { bgpNlriEntry 4 }

  bgpNlriSafi OBJECT-TYPE
    SYNTAX      BgpSafi
    MAX-ACCESS  not-accessible
    STATUS      current
    DESCRIPTION "The subsequent address family of the prefix for this NLRI."
    ::= { bgpNlriEntry 5 }

  bgpNlriPrfx OBJECT-TYPE
    SYNTAX      InetAddress (SIZE(0..32))
    MAX-ACCESS  not-accessible
    STATUS      current
    DESCRIPTION "An  address prefix in the Network Layer Reachability
                 Information field.

                 The prefix length is specified by bgpNlriPrfxLen.  Any bits
                 beyond the length specified by bgpNlriPrfxLen are zeroed.

                 This field contains the full line format BGP NLRI omitting
                 any NLRI length field.

                 For SAFI 128 the NLRI includes the MPLS label and Route
                 Distinguisher as well as the IPv4 or IPv6 address prefix."
    ::= { bgpNlriEntry 6 }

  bgpNlriPrfxLen OBJECT-TYPE
    SYNTAX      InetAddressPrefixLength
    MAX-ACCESS  not-accessible
    STATUS      current
    DESCRIPTION "Length in bits of the IP address prefix in the Network Layer
                 Reachability Information field."
    ::= { bgpNlriEntry 7 }

  bgpNlriBest OBJECT-TYPE
    SYNTAX      TruthValue
    MAX-ACCESS  read-only
    STATUS      current
    DESCRIPTION "An indication of whether or not this route was chosen as the
                 best BGP4 route."
    ::= { bgpNlriEntry 8 }

  bgpNlriAsSize OBJECT-TYPE
    SYNTAX      BgpAsSize
    MAX-ACCESS  read-only
    STATUS      current
    DESCRIPTION "Whether the bgpNlriASPathStr field contains two or four byte
                 AS numbers."
    ::= { bgpNlriEntry 9 }

  bgpNlriASPathStr OBJECT-TYPE
    SYNTAX      OCTET STRING  (SIZE (0..128))
    MAX-ACCESS  read-only
    STATUS      current
    DESCRIPTION "This is a string depicting the autonomous system path to this
                 network which was received from the peer which advertised it.
                 If bgpRmEntAsSize is four-octet and the peer does not support
                 four octet AS numbers this string represents the AS_PATH
                 formed by combining the AS_PATH and AS4_PATH attributes as
                 detailed in RFC 4893.  Two-octet AS numbers appear as
                 four-octet numbers by adding two bytes of zero padding.  The
                 format of the string is simply the AS_PATH attribute.  It can
                 be converted to a more readable format by the management
                 agent."
    ::= { bgpNlriEntry 10 }

  bgpPathAttrOrigin OBJECT-TYPE
    SYNTAX      BgpOriginCode
    MAX-ACCESS  read-only
    STATUS      current
    DESCRIPTION "The ultimate origin of the path information."
    ::= { bgpNlriEntry 11 }

  bgpPathAttrNextHop OBJECT-TYPE
    SYNTAX      InetAddress (SIZE(0..32))
    MAX-ACCESS  read-only
    STATUS      current
    DESCRIPTION "The address of the border router that should be used to access
                 the destination network.  This address is the nexthop address
                 received in the UPDATE packet.  The address family of this
                 object will be the same as that of the prefix in this row.

                 Note that for RFC 2545 style double nexthops, this object
                 will always contain the global scope nexthop.
                 bgpNlriLinkLocalNextHop will contain the linklocal scope
                 nexthop, if it is present."
    ::= { bgpNlriEntry 12 }

  bgpPathAttrMultiExitDisc OBJECT-TYPE
    SYNTAX      Unsigned32
    MAX-ACCESS  read-only
    STATUS      current
    DESCRIPTION "This metric is used to discriminate between multiple exit
                 points to an adjacent autonomous system."
    ::= { bgpNlriEntry 13 }

  bgpPathAttrLocalPref OBJECT-TYPE
    SYNTAX      Unsigned32
    MAX-ACCESS  read-only
    STATUS      current
    DESCRIPTION "The originating BGP4 speaker's degree of preference for an
                 advertised route."
    ::= { bgpNlriEntry 14 }

  bgpPathAttrAtomicAggregate OBJECT-TYPE
    SYNTAX      BgpPathAttrAtomicAggPresence
    MAX-ACCESS  read-only
    STATUS      current
    DESCRIPTION "When this object is set to AMB_BGP_ATOMIC_AGGR_PRESENT, the
                 ATOMIC_AGGREGATE Path Attribute is present and indicates that
                 the NLRI MUST NOT be made more specific."
    ::= { bgpNlriEntry 15 }

  bgpPathAttrAggregatorAS OBJECT-TYPE
    SYNTAX      BgpAutonomousSystemNumber
    MAX-ACCESS  read-only
    STATUS      current
    DESCRIPTION "The AS number of the last BGP4 speaker that performed route
                 aggregation."
    ::= { bgpNlriEntry 16 }

  bgpPathAttrAggregatorAddr OBJECT-TYPE
    SYNTAX      BgpIdentifier
    MAX-ACCESS  read-only
    STATUS      current
    DESCRIPTION "The IP address of the last BGP4 speaker that performed route
                 aggregation.  A value of 0000 indicates the absence of this
                 attribute.  Note propagation of AS of zero is illegal in
                 the Internet."
    ::= { bgpNlriEntry 17 }

  bgpPathAttrCalcLocalPref OBJECT-TYPE
    SYNTAX      Unsigned32
    MAX-ACCESS  read-only
    STATUS      current
    DESCRIPTION "The degree of preference calculated by the receiving BGP4
                 speaker for an advertised route."
    ::= { bgpNlriEntry 18 }

  bgpPathAttrOrigId OBJECT-TYPE
    SYNTAX      BgpIdentifier
    MAX-ACCESS  read-only
    STATUS      current
    DESCRIPTION "The Originator-ID identifying the router that initially
                 advertised this destination to a Route Reflector.  A
                 value of 0.0.0.0 indicates the absence of this attribute."
    ::= { bgpNlriEntry 19 }

  bgpPathAttrWeight OBJECT-TYPE
    SYNTAX      Unsigned32
    MAX-ACCESS  read-only
    STATUS      current
    DESCRIPTION "The local degree of preference assigned to this route."
    ::= { bgpNlriEntry 20 }

  bgpFlapStatsConfig OBJECT-TYPE
    SYNTAX      Unsigned32
    MAX-ACCESS  read-only
    STATUS      current
    DESCRIPTION "The index of the bgpFlapConfigTable containing the
                 configuration settings being applied to this route for
                 damping."
    ::= { bgpNlriEntry 21 }

  bgpFlapStatsPenalty OBJECT-TYPE
    SYNTAX       Unsigned32
    MAX-ACCESS   read-only
    STATUS       current
    DESCRIPTION "The current penalty value of this route.  If it is greater
                 than the cutoff threshold the route is suppressed."
    ::= { bgpNlriEntry 22 }

  bgpFlapStatsFlapcnt OBJECT-TYPE
    SYNTAX      Unsigned32
    MAX-ACCESS  read-only
    STATUS      current
    DESCRIPTION "The number of times this route has flapped since statistics
                 were last cleared."
    ::= { bgpNlriEntry 23 }

  bgpFlapStatsSupprsd OBJECT-TYPE
    SYNTAX      TruthValue
    MAX-ACCESS  read-only
    STATUS      current
    DESCRIPTION "Whether or not this route is suppressed."
    ::= { bgpNlriEntry 24 }

  bgpFlapStatsTimeleft OBJECT-TYPE
    SYNTAX      Unsigned32
    UNITS       "seconds"
    MAX-ACCESS  read-only
    STATUS      current
    DESCRIPTION "The time left until this route is no longer suppressed.  Only
                 valid if the route is suppressed."
    ::= { bgpNlriEntry 25 }

  bgpFlapStatsCleardamp OBJECT-TYPE
    SYNTAX      TruthValue
    MAX-ACCESS  read-create
    STATUS      current
    DESCRIPTION "This value is set to TRUE to clear all the damping information
                 of this route, and unsupress it if it is suppressed.
                 Specifically the following fields are cleared:
                 - bgpFlapStatsPenalty
                 - bgpFlapStatsFlapcnt
                 - bgpFlapStatsSupprsd
                 - bgpFlapStatsTimeleft.
                 Reading the value of this field has no meaning."
    DEFVAL { false }
    ::= { bgpNlriEntry 26 }

  bgpFlapStatsClearstat OBJECT-TYPE
    SYNTAX      TruthValue
    MAX-ACCESS  read-create
    STATUS      current
    DESCRIPTION "This value is set to clear just the bgpFlapStatsFlapcnt field.
                 This will not unsupress a suppressed route.  Reading the value
                 of this field has no meaning."
    DEFVAL { false }
    ::= { bgpNlriEntry 27 }

  bgpNlriEcmp   OBJECT-TYPE
    SYNTAX      TruthValue
    MAX-ACCESS  read-only
    STATUS      current
    DESCRIPTION "Whether or not this route was installed into the
                 Forwarding Table as an ECMP route (it may or may not be
                 the best BGP4 route advertised to BGP peers)."
    ::= { bgpNlriEntry 28 }

  bgpPathAttrAsPathLimAs OBJECT-TYPE
    SYNTAX      BgpAutonomousSystemNumber
    MAX-ACCESS  read-only
    STATUS      current
    DESCRIPTION "The AS number of the speaker that attached the AS_PATHLIMIT
                 attribute.  A value of 0 indicates the absence of this
                 attribute.  Note that propagation of AS of zero is illegal in
                 the Internet."
    ::= { bgpNlriEntry 29 }

  bgpPathAttrAsPathLimUpper OBJECT-TYPE
    SYNTAX      Unsigned32 (0..255)
    MAX-ACCESS  read-only
    STATUS      current
    DESCRIPTION "The upper bound on the number of ASes in the AS_PATH
                 associated with this route before the route will be filtered.
                 Only valid if bgpPathAttrAsPathLimAs is non-zero."
    ::= { bgpNlriEntry 30 }

  bgpNlriIsActive OBJECT-TYPE
    SYNTAX      BgpNlriIsActiveFlag
    MAX-ACCESS  read-only
    STATUS      current
    DESCRIPTION "An indication of whether or not this route is installed in
                 the forwarding table.

                 If bgpRmAfiSafiAdvertiseInactive is set to 'false', then
                 this is set to

                 - 'active' if the route is installed in the forwarding
                   table, or is a route redistributed from another routing
                   protocol instance

                 - 'inactive' otherwise.

                 If bgpRmAfiSafiAdvertiseInactive is set to 'true', BGP does
                 not track active routes.  In this case, bgpNlriIsActive is
                 set to 'notTracked'."
    ::= { bgpNlriEntry 31 }

  bgpNlriUserData OBJECT-TYPE
    SYNTAX      OCTET STRING(SIZE (4))
    MAX-ACCESS  read-only
    STATUS      current
    DESCRIPTION "User data for this BGP NLRI entry."
    ::= { bgpNlriEntry 32 }

  bgpNlriStale OBJECT-TYPE
    SYNTAX      TruthValue
    MAX-ACCESS  read-only
    STATUS      current
    DESCRIPTION "Whether or not this route was last sent by the peer before
                 BGP detected that the peer was restarting.  If the route is
                 not re-advertised by the peer before the restart completes,
                 BGP will remove the route from its database.  This flag is
                 set to 'false' if the peer is not restarting, or if the
                 route has been advertised by the peer since the restart."
    ::= { bgpNlriEntry 33 }

  bgpNlriFlapStartTime OBJECT-TYPE
    SYNTAX      TimeStamp
    MAX-ACCESS  read-only
    STATUS      current
    DESCRIPTION "The value of sysUpTime when this route first flapped.
                 This field is only valid if bgpFlapStatsPenalty is non-zero."
    ::= { bgpNlriEntry 34 }

  bgpNlriLinkLocalNextHop OBJECT-TYPE
    SYNTAX      InetAddress (SIZE(0..32))
    MAX-ACCESS  read-only
    STATUS      current
    DESCRIPTION "The IPv6 link-local address of the border router that
                 should be used to access the destination network.  This
                 object is only valid for a prefix with a received RFC 2545
                 style double nexthop."
    ::= { bgpNlriEntry 35 }

-------------------------------------------------------------------------------

  --
  -- BGP Unknown Path Attribute table
  --
  -- BGP 4 Path unknown attribute.  There is one row in  this table for each
  -- attribute not known by this BGP implementation (or agent instrumentation),
  -- but provided from a peer.
  --

  bgpPathAttrUnknownTable OBJECT-TYPE
  -- FAMILY-SHORT-NAME BGP_UNA
    SYNTAX      SEQUENCE OF BgpPathAttrUnknownEntry
    MAX-ACCESS  not-accessible
    STATUS      current
    DESCRIPTION "The BGP-4 Path Attribute Unknown Table contains the per
                 network path (NLRI) data on the path attributes advertised
                 with a route but not known to the local BGP implementation
                 or not otherwise capable of being returned from this agent.

                 The absence of row data for a given index value for
                 bgpPathAttrUnknownType indicates a lack of such unknown
                 attribute information for the indicated network path.

                 It is equivalent to the bgpM2PathAttrUnknownTable."
    ::= { bgpRib 2 }

  bgpPathAttrUnknownEntry OBJECT-TYPE
    SYNTAX      BgpPathAttrUnknownEntry
    MAX-ACCESS  not-accessible
    STATUS      current
    DESCRIPTION "Information about an unknown attribute provided with a path to
                 a network."
    INDEX { bgpRmEntIndex,
            bgpNlriPeerOrAfm,
            bgpNlriPeerAfmIndex,
            bgpNlriAfi,
            bgpNlriSafi,
            bgpNlriPrfx,
            bgpNlriPrfxLen,
            bgpPathAttrUnknownType }
    ::= { bgpPathAttrUnknownTable 1 }

  BgpPathAttrUnknownEntry ::= SEQUENCE {
      bgpPathAttrUnknownType       Unsigned32,
      bgpPathAttrUnknownValue      OCTET STRING,
      bgpPathAttrUnknownUserData   OCTET STRING
      }

  bgpPathAttrUnknownType OBJECT-TYPE
    SYNTAX      Unsigned32
    MAX-ACCESS  not-accessible
    STATUS      current
    DESCRIPTION "The attribute type advertised with this unknown attribute by
                 the peer.  This is the one octet type code field and does not
                 include the attribute flags.  These are included in the
                 bgpPathAttrUnknownValue field."
    ::= { bgpPathAttrUnknownEntry 8 }

  bgpPathAttrUnknownValue OBJECT-TYPE
    SYNTAX      OCTET STRING (SIZE(0..128))
    MAX-ACCESS  read-only
    STATUS      current
    DESCRIPTION "Value of path attribute not understood by the base BGP-4
                 document.  This will begin with the flags, code and length.
                 Note that only unknown optional-transitive attributes are
                 stored here.  Optional non-transitive attributes are discarded
                 as they do not need to be kept, while unknown attributes
                 claiming to be well-known will result in a Notification.
                 Octets beyond the maximum size, if any, are not recorded by
                 this row object.  This could lead to some truncation of the
                 recorded attributes."
    ::= { bgpPathAttrUnknownEntry 9 }

  bgpPathAttrUnknownUserData OBJECT-TYPE
    SYNTAX      OCTET STRING(SIZE (4))
    MAX-ACCESS  read-only
    STATUS      current
    DESCRIPTION "User data for this path attribute."
    ::= { bgpPathAttrUnknownEntry 10 }

-------------------------------------------------------------------------------

  --
  -- Path Attribute Extensions
  --

  bgpPathAttrExtensions OBJECT IDENTIFIER ::= { bgpRib 3 }

  bgpPathAttrNonCapExts OBJECT IDENTIFIER ::= { bgpPathAttrExtensions 1 }

  bgpPathAttrCapExts OBJECT IDENTIFIER ::= { bgpPathAttrExtensions 2 }

  --
  -- Path Attribute Route Reflection Extensions
  --

  bgpPathAttrRouteReflectionExts
  OBJECT IDENTIFIER ::= { bgpPathAttrNonCapExts 1966 }

  --
  -- Cluster table
  --
  -- This table holds the clusters passed through on a given path.
  --

  bgpPathAttrClusterTable OBJECT-TYPE
  -- FAMILY-SHORT-NAME BGP_CLU
    SYNTAX      SEQUENCE OF BgpPathAttrClusterEntry
    MAX-ACCESS  not-accessible
    STATUS      current
    DESCRIPTION "The BGP-4 Path Attribute Cluster Table contains the per
                 network path (NLRI) data on the reflection path which a
                 route has traversed.  The absence of row data for a given
                 network path indicates a lack of this attribute information
                 for the indicated network path.
                 It is equivalent to the bgpM2PathAttrClusterTable."
    ::= { bgpPathAttrRouteReflectionExts 2 }

  bgpPathAttrClusterEntry OBJECT-TYPE
    SYNTAX      BgpPathAttrClusterEntry
    MAX-ACCESS  not-accessible
    STATUS      current
    DESCRIPTION "Information about a cluster traversal provided with a path to
                 a network."
    INDEX { bgpRmEntIndex,
            bgpNlriPeerOrAfm,
            bgpNlriPeerAfmIndex,
            bgpNlriAfi,
            bgpNlriSafi,
            bgpNlriPrfx,
            bgpNlriPrfxLen,
            bgpPathAttrClusterIndex }
    ::= { bgpPathAttrClusterTable 1 }

  BgpPathAttrClusterEntry ::= SEQUENCE {
      bgpPathAttrClusterIndex      Unsigned32,
      bgpPathAttrClusterValue      Unsigned32,
      bgpPathAttrClusterUserData   OCTET STRING
      }

  bgpPathAttrClusterIndex OBJECT-TYPE
    SYNTAX      Unsigned32
    MAX-ACCESS  not-accessible
    STATUS      current
    DESCRIPTION "An integral index for a row in this table."
    ::= { bgpPathAttrClusterEntry 8 }

  bgpPathAttrClusterValue OBJECT-TYPE
    SYNTAX      Unsigned32
    MAX-ACCESS  read-only
    STATUS      current
    DESCRIPTION "A four octet long value representing a part of the
                 reflection path that the route has passed.  Each such four
                 octet long value represents the ID of a cluster that
                 the route has traversed.  The sequence of this path as
                 received in the route advertisement will be preserved in
                 the sequence of bgpPathAttrClusterTable rows (and the
                 bgpPathAttrClusterValue's in each row) as returned for a given
                 network path, and the monotonically increasing sequence of
                 bgpPathAttrClusterIndex values for that network path."
    ::= { bgpPathAttrClusterEntry 9 }

  bgpPathAttrClusterUserData OBJECT-TYPE
    SYNTAX      OCTET STRING(SIZE (4))
    MAX-ACCESS  read-only
    STATUS      current
    DESCRIPTION "User data for this path attribute."
    ::= { bgpPathAttrClusterEntry 10 }

  --
  -- BGP Communities
  --
  -- This table holds information on the communities the indexed route belongs
  -- to.
  --

  bgpPathAttrCommunityExts OBJECT IDENTIFIER ::=
    { bgpPathAttrNonCapExts 1997 }

  bgpPathAttrCommTable OBJECT-TYPE
  -- FAMILY-SHORT-NAME BGP_CMM
    SYNTAX      SEQUENCE OF BgpPathAttrCommEntry
    MAX-ACCESS  not-accessible
    STATUS      current
    DESCRIPTION "The BGP-4 Path Attribute Community Table contains the per
                 network path (NLRI) data on the community membership
                 advertised with a route.  The absence of row data for a given
                 network path indicates a lack of this attribute information
                 for the indicated network path.
                 It is equivalent to the bgpM2PathAttrCommTable."
    ::= { bgpPathAttrCommunityExts 1 }

  bgpPathAttrCommEntry OBJECT-TYPE
    SYNTAX      BgpPathAttrCommEntry
    MAX-ACCESS  not-accessible
    STATUS      current
    DESCRIPTION "Information about a community association provided with a path
                 to a network."
    INDEX { bgpRmEntIndex,
            bgpNlriPeerOrAfm,
            bgpNlriPeerAfmIndex,
            bgpNlriAfi,
            bgpNlriSafi,
            bgpNlriPrfx,
            bgpNlriPrfxLen,
            bgpPathAttrCommIndex }
    ::= { bgpPathAttrCommTable 1 }

  BgpPathAttrCommEntry ::= SEQUENCE {
      bgpPathAttrCommIndex      Unsigned32,
      bgpPathAttrCommValue      BgpCommunity,
      bgpPathAttrCommUserData   OCTET STRING
      }

  bgpPathAttrCommIndex OBJECT-TYPE
    SYNTAX      Unsigned32
    MAX-ACCESS  not-accessible
    STATUS      current
    DESCRIPTION "An integer index for a row in this table."
    ::= { bgpPathAttrCommEntry 8 }

  bgpPathAttrCommValue  OBJECT-TYPE
    SYNTAX      BgpCommunity
    MAX-ACCESS  read-only
    STATUS      current
    DESCRIPTION "A value representing a community.   There are certain
                 4-octet long values which could be returned in this
                 columnar row data that carry additional semantics."
    ::= { bgpPathAttrCommEntry 9 }

  bgpPathAttrCommUserData OBJECT-TYPE
    SYNTAX      OCTET STRING(SIZE (4))
    MAX-ACCESS  read-only
    STATUS      current
    DESCRIPTION "User data for this path attribute."
    ::= { bgpPathAttrCommEntry 10 }

  --
  -- BGP Extended Communities
  --
  -- This table holds information on the extended communities the indexed route
  -- belongs to.
  --
  -- Note that the OID used here (2547) should be changed when one is finalised
  -- for the equivalent table in the main BGP MIBv2.
  --

  bgpPathAttrExtCommunityExts OBJECT IDENTIFIER ::=
    { bgpPathAttrNonCapExts 2547 }

  bgpPathAttrExtCommTable OBJECT-TYPE
  -- FAMILY-SHORT-NAME BGP_ECM
    SYNTAX      SEQUENCE OF BgpPathAttrExtCommEntry
    MAX-ACCESS  not-accessible
    STATUS      current
    DESCRIPTION "The BGP-4 Path Attribute Extended Community Table contains the
                 per network path (NLRI) data on the extended community
                 membership advertised with a route.  The absence of row data
                 for a given network path indicates a lack of this attribute
                 information for the indicated network path.
                 It is equivalent to the bgpM2PathAttrExtCommTable."
    ::= { bgpPathAttrExtCommunityExts 1 }

  bgpPathAttrExtCommEntry OBJECT-TYPE
    SYNTAX      BgpPathAttrExtCommEntry
    MAX-ACCESS  not-accessible
    STATUS      current
    DESCRIPTION "Information about an extended community association provided
                 with a path to a network."
    INDEX { bgpRmEntIndex,
            bgpNlriPeerOrAfm,
            bgpNlriPeerAfmIndex,
            bgpNlriAfi,
            bgpNlriSafi,
            bgpNlriPrfx,
            bgpNlriPrfxLen,
            bgpPathAttrExtCommIndex }
    ::= { bgpPathAttrExtCommTable 1 }

  BgpPathAttrExtCommEntry ::= SEQUENCE {
      bgpPathAttrExtCommIndex     Unsigned32,
      bgpPathAttrExtCommValue     BgpExtendedCommunity,
      bgpPathAttrExtCommUserData  OCTET STRING
      }

  bgpPathAttrExtCommIndex OBJECT-TYPE
    SYNTAX      Unsigned32
    MAX-ACCESS  not-accessible
    STATUS      current
    DESCRIPTION "An integer index for a row in this table."
    ::= { bgpPathAttrExtCommEntry 8 }

  bgpPathAttrExtCommValue  OBJECT-TYPE
    SYNTAX      BgpExtendedCommunity
    MAX-ACCESS  read-only
    STATUS      current
    DESCRIPTION "A value representing an extended community.   There are
                 certain 8-octet long values which could be returned in this
                 columnar row data that carry additional semantics."
    ::= { bgpPathAttrExtCommEntry 9 }

  bgpPathAttrExtCommUserData OBJECT-TYPE
    SYNTAX      OCTET STRING(SIZE (4))
    MAX-ACCESS  read-only
    STATUS      current
    DESCRIPTION "User data for this path attribute."
    ::= { bgpPathAttrExtCommEntry 10 }

-------------------------------------------------------------------------------

  --
  -- BGP Adj-RIB Out Table
  --
  -- This table contains the set of routes advertised to each peer.
  --

  bgpAdjRibOutTable OBJECT-TYPE
  -- FAMILY-SHORT-NAME BGP_ARO
    SYNTAX      SEQUENCE OF BgpAdjRibOutEntry
    MAX-ACCESS  not-accessible
    STATUS      current
    DESCRIPTION "The BGP Adj-RIB-Out Table contains the set of routes
                 advertised to each peer."
    ::= { bgpRib 4 }

  bgpAdjRibOutEntry OBJECT-TYPE
    SYNTAX      BgpAdjRibOutEntry
    MAX-ACCESS  not-accessible
    STATUS      current
    DESCRIPTION "Information about a path to a network that has been
                 advertised to a peer.  The route has been
                 explicitly advertised in an UPDATE message sent to the
                 peer, unless bgpAdjRibOutLocalAggrType has the value
                 suppressedAggregatedRoute(4), in which case the route
                 has only been advertised as part of an aggregate
                 route."
    INDEX { bgpRmEntIndex,
            bgpPeerIndex,
            bgpAdjRibOutAfi,
            bgpAdjRibOutSafi,
            bgpAdjRibOutPrfx,
            bgpAdjRibOutPrfxLen }
    ::= { bgpAdjRibOutTable 1 }

  BgpAdjRibOutEntry ::= SEQUENCE {
      bgpAdjRibOutAfi                  BgpAfi,
      bgpAdjRibOutSafi                 BgpSafi,
      bgpAdjRibOutPrfx                 InetAddress,
      bgpAdjRibOutPrfxLen              InetAddressPrefixLength,
      bgpAdjRibOutAdvertStatus         INTEGER,
      bgpAdjRibOutLocalAggrType        INTEGER,
      bgpAdjRibOutAsSize               BgpAsSize,
      bgpAdjRibOutASPathStr            OCTET STRING,
      bgpAdjRibOutOrigin               BgpOriginCode,
      bgpAdjRibOutNextHop              InetAddress,
      bgpAdjRibOutMultiExitDisc        Unsigned32,
      bgpAdjRibOutLocalPref            Unsigned32,
      bgpAdjRibOutAtomicAggregate      BgpPathAttrAtomicAggPresence,
      bgpAdjRibOutAggregatorAS         BgpAutonomousSystemNumber,
      bgpAdjRibOutAggregatorAddr       BgpIdentifier,
      bgpAdjRibOutOrigId               BgpIdentifier,
      bgpAdjRibOutAsLimAs              BgpAutonomousSystemNumber,
      bgpAdjRibOutAsLimUpper           Unsigned32,
      bgpAdjRibOutUserData             OCTET STRING,
      bgpAdjRibOutEcmp                 TruthValue,
      bgpAdjRibOutStale                TruthValue,
      bgpAdjRibOutLinkLocalNextHop     InetAddress
      }

  bgpAdjRibOutAfi OBJECT-TYPE
    SYNTAX      BgpAfi
    MAX-ACCESS  not-accessible
    STATUS      current
    DESCRIPTION "The address family of the prefix for this Adj-RIB Out
                 route."
    ::= { bgpAdjRibOutEntry 3 }

  bgpAdjRibOutSafi OBJECT-TYPE
    SYNTAX      BgpSafi
    MAX-ACCESS  not-accessible
    STATUS      current
    DESCRIPTION "The subsequent address family of the prefix for
                 this Adj-RIB Out route."
    ::= { bgpAdjRibOutEntry 4 }

  bgpAdjRibOutPrfx OBJECT-TYPE
    SYNTAX      InetAddress (SIZE(0..32))
    MAX-ACCESS  not-accessible
    STATUS      current
    DESCRIPTION "An address prefix in the Network Layer Reachability
                 Information field for this Adj-RIB Out route.

                 The prefix length is specified by bgpAdjRibOutPrfxLen.
                 Any bits beyond the length specified by
                 bgpAdjRibOutPrfxLen are zeroed.

                 This field contains the full line format BGP NLRI omitting
                 any NLRI length field.

                 For SAFI 128 the NLRI includes the MPLS label and Route
                 Distinguisher as well as the IPv4 or IPv6 address prefix."
    ::= { bgpAdjRibOutEntry 5 }

  bgpAdjRibOutPrfxLen OBJECT-TYPE
    SYNTAX      InetAddressPrefixLength
    MAX-ACCESS  not-accessible
    STATUS      current
    DESCRIPTION "Length in bits of the address prefix contained in the
                 bgpAdjRibOutPrfx object."
    ::= { bgpAdjRibOutEntry 6 }

  bgpAdjRibOutAdvertStatus OBJECT-TYPE
    SYNTAX      INTEGER {
                  advertised(1),
                  suppressed(2),
                  pendingWithdrawal(3),
                  withdrawn(4)
                }
    MAX-ACCESS  read-only
    STATUS      current
    DESCRIPTION "This object indicates the current state of
                 advertisement of the route to the peer.

                 A value of advertised(1) indicates that the route has
                 been advertised to the peer.

                 A value of suppressed(2) indicates that the route is
                 not currently advertised to the peer, but will be
                 advertised when a minimum advertisement interval timer
                 expires (either the bgpPeerMinASOriginationInterval or
                 bgpPeerMinRouteAdvertiseInterval).

                 A value of pendingWithdrawal(3) indicates that the
                 route is currently advertised to the peer, but will be
                 withdrawn when the timer expires.

                 A value of withdrawn(4) indicates that the route has
                 been withdrawn from the peer, and this entry will be
                 removed from the Adj-RIB-Out on the expiry of the
                 timer."
    ::= { bgpAdjRibOutEntry 7 }

  bgpAdjRibOutLocalAggrType OBJECT-TYPE
    SYNTAX      INTEGER {
                  noAggregation(1),
                  aggregateRoute(2),
                  unsuppAggregatedRoute(3),
                  suppressedAggregatedRoute(4)
                }
    MAX-ACCESS  read-only
    STATUS      current
    DESCRIPTION "This object indicates any aggregation processing that
                 has been applied to this Adj-RIB-Out route.

                 A value of noAggregation(1) indicates that this route
                 does not aggregate any other routes, and is not
                 aggregated by any route.

                 A value of aggregateRoute(2) indicates that this route
                 is a locally configured aggregating route,
                 corresponding to an entry in the bgpAggregateTable.

                 A value of unsuppAggregatedRoute(3) indicates that this
                 route has been aggregated by a locally configured
                 aggregate route and is not suppressed - the route is
                 still explicitly advertised to the peer.

                 A value of suppressedAggregatedRoute(4) indicates that
                 this route has been aggregated by a locally configured
                 aggregate route and is flagged such that it should not be
                 advertised along with the aggregate route.  Typically such
                 routes are not installed on an Adj-RIB-Out.  If however the
                 aggregate route itself is not permitted to be added to the
                 Adj-RIB-Out then suppressed routes are advertised if they
                 themselves are permitted by policy."
    ::= { bgpAdjRibOutEntry 8 }

  bgpAdjRibOutAsSize OBJECT-TYPE
    SYNTAX      BgpAsSize
    MAX-ACCESS  read-only
    STATUS      current
    DESCRIPTION "Whether the bgpAdjRibOutASPathStr object contains
                 two or four byte AS numbers."
    ::= { bgpAdjRibOutEntry 9 }

  bgpAdjRibOutASPathStr OBJECT-TYPE
    SYNTAX      OCTET STRING  (SIZE (0..128))
    MAX-ACCESS  read-only
    STATUS      current
    DESCRIPTION "This is a string containing the autonomous system path sent to
                 this peer in the AS_PATH attribute for this Adj-RIB-Out route.
                 If this path contains four-octet AS numbers and the peer does
                 not support these a two-octet AS_PATH attribute and associated
                 AS4_PATH attribute will be advertised to the peer instead as
                 detailed in RFC 4893.  However, this field will report the
                 four-octet AS_PATH that would  have been advertised to the
                 peer if it had supported four-byte AS numbers.  Two-octet AS
                 numbers appear as four-octet numbers by adding two bytes of
                 zero padding.  The format of the string is simply the AS_PATH
                 attribute.  This can be converted to a more readable format by
                 the management agent."
    ::= { bgpAdjRibOutEntry 10 }

  bgpAdjRibOutOrigin OBJECT-TYPE
    SYNTAX      BgpOriginCode
    MAX-ACCESS  read-only
    STATUS      current
    DESCRIPTION "The ultimate origin of the path information."
    ::= { bgpAdjRibOutEntry 11 }

  bgpAdjRibOutNextHop OBJECT-TYPE
    SYNTAX      InetAddress (SIZE(0..32))
    MAX-ACCESS  read-only
    STATUS      current
    DESCRIPTION "The next hop address transmitted in the UPDATE packet.
                 The address family of this object is the same as that
                 of bgpAdjRibOutPrfx.

                 Note that for RFC 2545 style double nexthops, this object
                 will always contain the global scope nexthop.
                 bgpAdjRibOutLinkLocalNextHop will contain the linklocal
                 scope nexthop, if it is present."
    ::= { bgpAdjRibOutEntry 12 }

  bgpAdjRibOutMultiExitDisc OBJECT-TYPE
    SYNTAX      Unsigned32
    MAX-ACCESS  read-only
    STATUS      current
    DESCRIPTION "This metric is used to discriminate between multiple
                 exit points to an adjacent autonomous system."
    ::= { bgpAdjRibOutEntry 13 }

  bgpAdjRibOutLocalPref OBJECT-TYPE
    SYNTAX      Unsigned32
    MAX-ACCESS  read-only
    STATUS      current
    DESCRIPTION "The local preference for this Adj-RIB-Out route, as
                 transmitted in the UPDATE message sent to the peer."
    ::= { bgpAdjRibOutEntry 14 }

  bgpAdjRibOutAtomicAggregate OBJECT-TYPE
    SYNTAX      BgpPathAttrAtomicAggPresence
    MAX-ACCESS  read-only
    STATUS      current
    DESCRIPTION "When this object is set to atomicAggregatePresent, the
                 ATOMIC_AGGREGATE Path Attribute was included in the
                 UPDATE sent to the peer for this Adj-RIB-Out route."
    ::= { bgpAdjRibOutEntry 15 }

  bgpAdjRibOutAggregatorAS OBJECT-TYPE
    SYNTAX      BgpAutonomousSystemNumber
    MAX-ACCESS  read-only
    STATUS      current
    DESCRIPTION "The AS number of the last BGP4 speaker that performed
                 route aggregation."
    ::= { bgpAdjRibOutEntry 16 }

  bgpAdjRibOutAggregatorAddr OBJECT-TYPE
    SYNTAX      BgpIdentifier
    MAX-ACCESS  read-only
    STATUS      current
    DESCRIPTION "The IP address of the last BGP4 speaker that performed
                 route aggregation.  A value of 0.0.0.0 indicates that
                 this attribute was not included in the UPDATE message
                 sent to the peer."
    ::= { bgpAdjRibOutEntry 17 }

  bgpAdjRibOutOrigId OBJECT-TYPE
    SYNTAX      BgpIdentifier
    MAX-ACCESS  read-only
    STATUS      current
    DESCRIPTION "The Originator-ID identifying the router that initially
                 advertised this destination to a Route Reflector.  A
                 value of 0.0.0.0 indicates the absence of this
                 attribute."
    ::= { bgpAdjRibOutEntry 18 }

  bgpAdjRibOutAsLimAs OBJECT-TYPE
    SYNTAX       BgpAutonomousSystemNumber
    MAX-ACCESS   read-only
    STATUS       current
    DESCRIPTION  "If non-zero this is the number of the AS that attached the
                  AS_PATHLIMIT attribute."
        ::= { bgpAdjRibOutEntry 19 }

  bgpAdjRibOutAsLimUpper OBJECT-TYPE
    SYNTAX      Unsigned32  (0..255)
    MAX-ACCESS  read-only
    STATUS      current
    DESCRIPTION "The upper bound on the number of ASes in the AS_PATH attribute
                 after which the route will be filtered.  Only valid if
                 bgpAdjRibOutAsLimAs is non-zero."
        ::= { bgpAdjRibOutEntry 20 }

  bgpAdjRibOutUserData OBJECT-TYPE
    SYNTAX      OCTET STRING(SIZE (4))
    MAX-ACCESS  read-only
    STATUS      current
    DESCRIPTION "User data for this BGP ARO entry."
    ::= { bgpAdjRibOutEntry 21 }

  bgpAdjRibOutEcmp OBJECT-TYPE
    SYNTAX      TruthValue
    MAX-ACCESS  read-only
    STATUS      current
    DESCRIPTION "Whether or not this route was installed into the
                 Forwarding Table as an ECMP route."
    ::= { bgpAdjRibOutEntry 22 }

  bgpAdjRibOutStale OBJECT-TYPE
    SYNTAX      TruthValue
    MAX-ACCESS  read-only
    STATUS      current
    DESCRIPTION "Whether or not this route was last sent by the peer before
                 BGP detected that the peer was restarting.  If the route is
                 not re-advertised by the peer before the restart completes,
                 BGP will remove the route from its database.  This flag is
                 set to 'false' if the peer is not restarting, or if the
                 route has been advertised by the peer since the restart."
    ::= { bgpAdjRibOutEntry 23 }

  bgpAdjRibOutLinkLocalNextHop OBJECT-TYPE
    SYNTAX      InetAddress (SIZE(0..32))
    MAX-ACCESS  read-only
    STATUS      current
    DESCRIPTION "The IPv6 link-local address sent in the UPDATE message.
                 This object is only valid if an RFC 2545 style double
                 nexthop was sent in the UPDATE."
    ::= { bgpAdjRibOutEntry 24 }

-------------------------------------------------------------------------------

  bgpPib OBJECT IDENTIFIER ::= { bgpMib 5 }

-- All Policy tables are DC-BGP specific.  When configuring one row to
-- point to another in a different table (for example when setting a row
-- in the config table to refer to a route map), the referred to row (the
-- route map) must be present and row active.  Similarly in reverse the
-- referred to row cannot be deactivated if it is the last in the map, and
-- the referring row is still present.  The referred to row can also not
-- be deactivated if any potential referer has a SET pending.  (For
-- example, a route map row cannot be de-activated if any config rows have
-- a set pending, as they could then refer to a non-present row).

--
-- DC-BGP Route Map Table
--
-- This table is used to create and manage DC-BGP route maps.  Route Maps are
-- the centre of DC-BGP policy formation and essentially form a filter.  A row
-- in this table cannot be destroyed if there is a SET pending for any of the
-- associated list tables (AS path lists, (extended) community lists, ip prefix
-- lists).
--
-- Certain restrictions apply to an entry in this table if it represents one or
-- more ORFs.  If the ORF association is remote then the entry has been created
-- as a result of advertisements from a peer in which case all fields are
-- read-only.
--
-- If the ORF association is local then the entry represents ORF information to
-- be advertised to peers in which case the following applies:
--
-- The MaAfi and MaSafi fields MUST be assigned.
-- The MaComm, MaExtCom, MaAddr and Continue fields are the only other fields
-- that may be specified.  All other fields are deemed inconsistent.
--

  bgpRouteMapTable OBJECT-TYPE
  -- FAMILY-SHORT-NAME BGP_MAP
    SYNTAX      SEQUENCE OF BgpRouteMapEntry
    MAX-ACCESS  not-accessible
    STATUS      current
    DESCRIPTION "The table of DC-BGP Route Maps.  If a particular match or set
                 category does not apply to a route map then do not define the
                 corresponding field in the MIB row."
    ::= { bgpPib 1 }

  bgpRouteMapEntry OBJECT-TYPE
    SYNTAX      BgpRouteMapEntry
    MAX-ACCESS  not-accessible
    STATUS      current
    DESCRIPTION "Each entry represents a filter consisting of Match and Set
                 entries."
    INDEX { bgpRmEntIndex,
            bgpRouteMapIndex,
            bgpRouteMapNumber }
    ::= { bgpRouteMapTable 1 }

  BgpRouteMapEntry ::= SEQUENCE {
      bgpRouteMapIndex             Unsigned32,
      bgpRouteMapNumber            Unsigned32,
      bgpRouteMapRowStatus         RowStatus,
      bgpRouteMapMaAfi             BgpAfi,
      bgpRouteMapMaAfiDef          TruthValue,
      bgpRouteMapMaSafi            BgpSafi,
      bgpRouteMapMaSafiDef         TruthValue,
      bgpRouteMapMaAs              DisplayString,
      bgpRouteMapMaComm            DisplayString,
      bgpRouteMapMaExtComm         DisplayString,
      bgpRouteMapMaAddr            TruthValue,
      bgpRouteMapMaNext            TruthValue,
      bgpRouteMapMaSource          TruthValue,
      bgpRouteMapMaMed             Unsigned32,
      bgpRouteMapMaMedDef          TruthValue,
      bgpRouteMapMaUser            TruthValue,
      bgpRouteMapSeAs              Integer32,
      bgpRouteMapSeAsAct           BgpAsPathAction,
      bgpRouteMapSeComm            DisplayString,
      bgpRouteMapSeCommAct         BgpCommunityAction,
      bgpRouteMapSeExtComm         DisplayString,
      bgpRouteMapSeExtCommAct      BgpCommunityAction,
      bgpRouteMapSeLocPref         Integer32,
      bgpRouteMapSeLocPrefDef      TruthValue,
      bgpRouteMapSeMed             Unsigned32,
      bgpRouteMapSeMedDef          TruthValue,
      bgpRouteMapSeNext            InetAddress,
      bgpRouteMapSeOrigin          BgpOriginCode,
      bgpRouteMapSeOriginDef       TruthValue,
      bgpRouteMapSeWeight          Integer32,
      bgpRouteMapSeWeightDef       TruthValue,
      bgpRouteMapSeFlap            Unsigned32,
      bgpRouteMapSeUser            TruthValue,
      bgpRouteMapHitcnt            Integer32,
      bgpRouteMapClearcnt          TruthValue,
      bgpRouteMapUserInfo          OCTET STRING,
      bgpRouteMapType              BgpPermitOrDeny,
      bgpRouteMapContinue          Unsigned32,
      bgpRouteMapOrfAssoc          BgpOrfAssociation,
      bgpRouteMapSeAsLimUpper      Unsigned32,
      bgpRouteMapSeAsLimDef        TruthValue,
      bgpRouteMapMaOrigin          BgpOriginCode,
      bgpRouteMapMaOriginDef       TruthValue,
      bgpRouteMapSeMedDelta        Unsigned32,
      bgpRouteMapSeMedDeltaTyp     BgpMedDeltaType,
      bgpRouteMapSeMedIgp          TruthValue,
      bgpRouteMapSeAsPrependCount  Unsigned32,
      bgpRouteMapSeAsPrependSize   BgpAsSize,
      bgpRouteMapSeAsPrependAsVals OCTET STRING,
      bgpRouteMapMaAnd             TruthValue
      }

  bgpRouteMapIndex OBJECT-TYPE
    SYNTAX      Unsigned32 (1..4278190079)
    MAX-ACCESS  not-accessible
    STATUS      current
    DESCRIPTION "The index of this bgpRouteMapEntry.  This is the Index used by
                 Neighbors to reference the Route Map.  Route map indexes
                 0xFFnnnnnn, are reserved for representing ORFs advertised by
                 peers with bgpPeerIdentifier nnnnnn."
    ::= { bgpRouteMapEntry 2 }

  bgpRouteMapNumber OBJECT-TYPE
    SYNTAX      Unsigned32
    MAX-ACCESS  not-accessible
    STATUS      current
    DESCRIPTION "The index of this bgpRouteMapEntry.  This is a number used to
                 reference more than one filter per route map index."
    ::= { bgpRouteMapEntry 3 }

  bgpRouteMapRowStatus OBJECT-TYPE
    SYNTAX      RowStatus
    MAX-ACCESS  read-create
    STATUS      current
    DESCRIPTION "Used to create and delete a Route Map."
    ::= { bgpRouteMapEntry 4 }

  bgpRouteMapMaAfi OBJECT-TYPE
    SYNTAX      BgpAfi
    MAX-ACCESS  read-create
    STATUS      current
    DESCRIPTION "The AFI index to match the AFI type against.  This value must
                 be set if the bgpRouteMapSeNext field is defined.  This value
                 is only used if bgpRouteMapMaAfiDef is TRUE."
    DEFVAL { ipv4 }
    ::= { bgpRouteMapEntry 5 }

  bgpRouteMapMaAfiDef OBJECT-TYPE
    SYNTAX      TruthValue
    MAX-ACCESS  read-create
    STATUS      current
    DESCRIPTION "Whether or not the value in bgpRouteMapMaAfi should be used
                 for matching."
    DEFVAL { false }
    ::= { bgpRouteMapEntry 6 }

  bgpRouteMapMaSafi OBJECT-TYPE
    SYNTAX      BgpSafi
    MAX-ACCESS  read-create
    STATUS      current
    DESCRIPTION "The SAFI index to match the AFI type against.  This value must
                 be set if the bgpRouteMapSeNext field is defined.  This value
                 is only used if bgpRouteMapMaSafiDef is TRUE."
    DEFVAL { unicast }
    ::= { bgpRouteMapEntry 7 }

  bgpRouteMapMaSafiDef OBJECT-TYPE
    SYNTAX      TruthValue
    MAX-ACCESS  read-create
    STATUS      current
    DESCRIPTION "Whether or not the value in bgpRouteMapMaSafi should be used
                 for matching."
    DEFVAL { false }
    ::= { bgpRouteMapEntry 8 }

  bgpRouteMapMaAs OBJECT-TYPE
    SYNTAX      DisplayString (SIZE(0..127))
    MAX-ACCESS  read-create
    STATUS      current
    DESCRIPTION "Contains the regular expression to use when matching the
                 AS-Path for a route.  This is stored here in ASCII format.
                 AS numbers are matched as decimal numbers.  For example,
                 the AS number '0x0123' should be represented in the
                 regular expression string as '291'.  The string is not
                 NULL-terminated.  A NULL string or a ma_as_exp_len value
                 of zero indicates that the field is not in use."
    ::= { bgpRouteMapEntry 9 }

  bgpRouteMapMaComm OBJECT-TYPE
    SYNTAX      DisplayString (SIZE(0..127))
    MAX-ACCESS  read-create
    STATUS      current
    DESCRIPTION "If not representing one or more ORF entries this contains the
                 regular expression to use when matching elements of the
                 community list for a route.  If representing ORF entries then
                 instead of a regular expression this contains a simple comma
                 separated list of communities which are or-ed together when
                 matching.  In both cases this is stored here in ASCII format.
                 Communities are matched using new-format decimal notation.
                 For example, the community '0x00120101' should be represented
                 in the string as '18:257'.  The string is not NULL-terminated.
                 A NULL string or a ma_comm_exp_len of zero indicates that the
                 field is not in use."
    ::= { bgpRouteMapEntry 10 }

  bgpRouteMapMaExtComm OBJECT-TYPE
    SYNTAX      DisplayString (SIZE(0..127))
    MAX-ACCESS  read-create
    STATUS      current
    DESCRIPTION "If not representing one or more ORF entries this contains
                 the regular expression to use when matching elements of the
                 extended community list for a route.

                 If representing ORF entries then instead of a regular
                 expression this contains a simple comma separated list of
                 extended communities which are or-ed together when matching.
                 In both cases this is stored here in ASCII format.  Extended
                 communities are matched as hexadecimal numbers.  For
                 example, the extended community '0x11223344556677' should be
                 represented in the string as '0011223344556677' (leading
                 zeroes are necessary to make the length up to 8 bytes). The
                 string is not NULL-terminated.  A NULL string or a
                 match_ext_comm_exp_len value of zero indicates that the
                 field is not in use."
    ::= { bgpRouteMapEntry 11 }

  bgpRouteMapMaAddr OBJECT-TYPE
    SYNTAX      TruthValue
    MAX-ACCESS  read-only
    STATUS      current
    DESCRIPTION "Whether or not there is an IP Address prefix table to match
                 the NLRI attribute against."
    DEFVAL { false }
    ::= { bgpRouteMapEntry 12 }

  bgpRouteMapMaNext OBJECT-TYPE
    SYNTAX      TruthValue
    MAX-ACCESS  read-only
    STATUS      current
    DESCRIPTION "Whether or not there is an IP Address prefix table to match
                 the Next Hop attribute against."
    DEFVAL { false }
    ::= { bgpRouteMapEntry 13 }

  bgpRouteMapMaSource OBJECT-TYPE
    SYNTAX      TruthValue
    MAX-ACCESS  read-only
    STATUS      current
    DESCRIPTION "Whether or not there is an IP Address prefix table to match
                 the source address against."
    DEFVAL { false }
    ::= { bgpRouteMapEntry 14 }

  bgpRouteMapMaMed OBJECT-TYPE
    SYNTAX      Unsigned32
    MAX-ACCESS  read-create
    STATUS      current
    DESCRIPTION "The value to match the Multiple Exit Descriminator attribute
                 against.  A value of 0 indicates a match on no MED or a MED
                 of 0.  This value is only used if bgpRouteMapMaMedDef is
                 TRUE."
    DEFVAL { 0 }
    ::= { bgpRouteMapEntry 15 }

  bgpRouteMapMaMedDef OBJECT-TYPE
    SYNTAX      TruthValue
    MAX-ACCESS  read-create
    STATUS      current
    DESCRIPTION "Whether or not the value in bgpRouteMapMaMed should be used
                 for matching."
    DEFVAL { false }
    ::= { bgpRouteMapEntry 16 }

  bgpRouteMapMaUser OBJECT-TYPE
    SYNTAX      TruthValue
    MAX-ACCESS  read-create
    STATUS      current
    DESCRIPTION "Set to TRUE if the user exit for matching is to be called."
    DEFVAL { false }
    ::= { bgpRouteMapEntry 17 }

  bgpRouteMapSeAs OBJECT-TYPE
    SYNTAX      Integer32 (0..255)
    MAX-ACCESS  read-create
    STATUS      current
    DESCRIPTION "The number of times the local AS number is prepended to
                 the AS path if there is a match.  This is only relevant if
                 the route map is being used for exporting routes, or for
                 setting attributes for an aggregate route which does not
                 have the AS_SET option set.  This value is only used if
                 the value of bgpRouteMapSeAsAct is AMB_BGP_PATH_SET or
                 AMB_BGP_REM_MATCH_AND_SET."
    DEFVAL { 0 }
    ::= { bgpRouteMapEntry 18 }

  bgpRouteMapSeAsAct OBJECT-TYPE
    SYNTAX      BgpAsPathAction
    MAX-ACCESS  read-create
    STATUS      current
    DESCRIPTION "Whether or not the value in bgpRouteMapSeAs should be used
                 for updating attributes.  The possible action values are:
                 AMB_BGP_PATH_NONE - Ignore bgpRouteMapSeAs and do nothing.
                 AMB_BGP_PATH_SET - Prepend the local AS number the number
                 of times specified by bgpRouteMapSeAs.
                 AMB_BGP_PATH_REM_MATCH - Remove all AS numbers in the
                 AS-Path matched by the regular expression in
                 bgpRouteMapMaAs.
                 AMB_BGP_PATH_REM_MATCH_AND_SET - Remove all AS numbers in
                 the AS-Path matched by the regular expression in
                 bgpRouteMapMaAs and prepend the local AS number the number
                 of times specified by bgpRouteMapSeAs."
    DEFVAL { none }
    ::= { bgpRouteMapEntry 19 }

  bgpRouteMapSeComm OBJECT-TYPE
    SYNTAX      DisplayString (SIZE(0..127))
    MAX-ACCESS  read-create
    STATUS      current
    DESCRIPTION "Contains the regular expression used when executing the
                 action defined by bgpRouteMapSeCommAct.  Allowed values
                 depend on the value of bgpRouteMapSeCommAct - see the
                 comment for bgpRouteMapSeCommAct."
    ::= { bgpRouteMapEntry 20 }

  bgpRouteMapSeCommAct OBJECT-TYPE
    SYNTAX      BgpCommunityAction
    MAX-ACCESS  read-create
    STATUS      current
    DESCRIPTION "The action to take on the community list if this route map
                 matches the route.  Note that if the action is
                 AMB_BGP_SET_SPECIFIC or AMB_BGP_REMOVE_ALL_AND_SET, the
                 field bgpRouteMapSeComm must only contain a string
                 representation of a single specific community value, which
                 will be added to the route.  If the action is
                 AMB_BGP_REMOVE_SPECIFIC, then the bgpRouteMapSeComm field
                 must contain a regular expression string that matches the
                 community (or communities) to be removed.  The possible
                 action values are:

                 AMB_BGP_NONE - Ignore the value of bgpRouteMapSeComm and
                 do nothing.
                 AMB_BGP_REMOVE_ALL - Ignore the value of bgpRouteMapSeComm
                 and remove all communities from the route.
                 AMB_BGP_REMOVE_SPECIFIC - Remove from the route all
                 communities that match the regular expression in
                 bgpRouteMapSeComm.
                 AMB_BGP_SET_SPECIFIC - Append the community in
                 bgpRouteMapSeComm to the communities list.
                 AMB_BGP_REMOVE_ALL_AND_SET - Remove all communities from
                 the route and replace them with the community in
                 bgpRouteMapSeComm."
    DEFVAL { none }
    ::= { bgpRouteMapEntry 21 }

  bgpRouteMapSeExtComm OBJECT-TYPE
    SYNTAX      DisplayString (SIZE(0..127))
    MAX-ACCESS  read-create
    STATUS      current
    DESCRIPTION "Contains the regular expression used when executing the
                 action defined by bgpRouteMapSeExtCommAct.  This field may
                 be ignored depending on the value of
                 bgpRouteMapSeExtCommAct - see the comment for
                 bgpRouteMapSeExtCommAct."
    ::= { bgpRouteMapEntry 22 }

  bgpRouteMapSeExtCommAct OBJECT-TYPE
    SYNTAX      BgpCommunityAction
    MAX-ACCESS  read-create
    STATUS      current
    DESCRIPTION "The action to take on the extended community list if this
                 route map matches the route.  Note that if the action is
                 AMB_BGP_SET_SPECIFIC or AMB_BGP_REMOVE_ALL_AND_SET, the
                 bgpRouteMapSeExtComm field should only contain a single
                 specific extended community value, which will be added to
                 the route.  If the action is AMB_BGP_REMOVE_SPECIFIC, then
                 the bgpRouteMapSeExtComm field must contain a regular
                 expression string that matches the extended community (or
                 communities) to be removed.  The
                 possible action values are:

                 AMB_BGP_NONE - Ignore the value of bgpRouteMapSeExtComm
                 and do nothing.
                 AMB_BGP_REMOVE_ALL - Ignore the value of
                 bgpRouteMapSeExtComm and remove all extended communities
                 from the route.
                 AMB_BGP_REMOVE_SPECIFIC - Remove from the route all
                 extended communities that match the regular expression in
                 bgpRouteMapSeExtComm.
                 AMB_BGP_SET_SPECIFIC - Append the extended community in
                 bgpRouteMapSeExtComm to the extended communities list.
                 AMB_BGP_REMOVE_ALL_AND_SET - Remove all extended
                 communities from the route and replace them with the
                 extended community in bgpRouteMapSeExtComm."
    DEFVAL { none }
    ::= { bgpRouteMapEntry 23 }

  bgpRouteMapSeLocPref OBJECT-TYPE
    SYNTAX      Integer32
    MAX-ACCESS  read-create
    STATUS      current
    DESCRIPTION "The value to set the Local Pref to if there is a match.  This
                 value is only used if bgpRouteMapSeLocPrefDef is TRUE."
    DEFVAL { 0 }
    ::= { bgpRouteMapEntry 24 }

  bgpRouteMapSeLocPrefDef OBJECT-TYPE
    SYNTAX      TruthValue
    MAX-ACCESS  read-create
    STATUS      current
    DESCRIPTION "Whether or not the value in bgpRouteMapSeLocPref should be
                 used for updating attributes."
    DEFVAL { false }
    ::= { bgpRouteMapEntry 25 }

  bgpRouteMapSeMed OBJECT-TYPE
    SYNTAX      Unsigned32
    MAX-ACCESS  read-create
    STATUS      current
    DESCRIPTION "The value to set the MED to if there is a match.  A value of
                 0 indicates that the MED should be removed.  This value is
                 only used if bgpRouteMapSeMedDef is TRUE."
    DEFVAL { 0 }
    ::= { bgpRouteMapEntry 26 }

  bgpRouteMapSeMedDef OBJECT-TYPE
    SYNTAX      TruthValue
    MAX-ACCESS  read-create
    STATUS      current
    DESCRIPTION "Whether or not the value in bgpRouteMapSeMed should be
                 used for updating attributes.

                 This field must be set to FALSE if either
                 bgpRouteMapSeMedDelta is non-zero or bgpRouteMapSeMedIgp is
                 set to TRUE."
    DEFVAL { false }
    ::= { bgpRouteMapEntry 27 }

  bgpRouteMapSeNext OBJECT-TYPE
    SYNTAX      InetAddress (SIZE(0..32))
    MAX-ACCESS  read-create
    STATUS      current
    DESCRIPTION "The value to set the Next Hop to if there is a match.

                 Note that if this is set then the match AFI and SAFI fields
                 (bgpRouteMapMaAfi, bgpRouteMapMaSafi) must also be set to
                 ensure the right address type is being set.

                 The value is a BGP next hop in line format, as encoded in a
                 NEXT_HOP or MP_REACH_NLRI attribute with
                 AFI/SAFI = bgpRouteMapMaAfi/bgpRouteMapMaSafi.

                 Since a value of 0 is not allowed as a next hop, the default
                 value implies this field is not defined."
    DEFVAL { '00'h }
    ::= { bgpRouteMapEntry 28 }

  bgpRouteMapSeOrigin OBJECT-TYPE
    SYNTAX      BgpOriginCode
    MAX-ACCESS  read-create
    STATUS      current
    DESCRIPTION "The value to set the Origin to if there is a match.  This
                 value is only used if bgpRouteMapSeOriginDef is TRUE."
    DEFVAL { originIncomplete }
    ::= { bgpRouteMapEntry 29 }

  bgpRouteMapSeOriginDef OBJECT-TYPE
    SYNTAX      TruthValue
    MAX-ACCESS  read-create
    STATUS      current
    DESCRIPTION "Whether or not the value in bgpRouteMapSeOrigin should be
                 used for updating attributes."
    DEFVAL { false }
    ::= { bgpRouteMapEntry 30 }

  bgpRouteMapSeWeight OBJECT-TYPE
    SYNTAX      Integer32
    MAX-ACCESS  read-create
    STATUS      current
    DESCRIPTION "The value to set the Weight to if there is a match.  This
                 value is only used if bgpRouteMapSeWeightDef is TRUE."
    DEFVAL { 0 }
    ::= { bgpRouteMapEntry 31 }

  bgpRouteMapSeWeightDef OBJECT-TYPE
    SYNTAX      TruthValue
    MAX-ACCESS  read-create
    STATUS      current
    DESCRIPTION "Whether or not the value in bgpRouteMapSeWeight should be
                 used for updating attributes."
    DEFVAL { false }
    ::= { bgpRouteMapEntry 32 }

  bgpRouteMapSeFlap OBJECT-TYPE
    SYNTAX      Unsigned32
    MAX-ACCESS  read-create
    STATUS      current
    DESCRIPTION "The index of the flap config table to use if there is a
                 match.  Since an index of 0 is not allowed, the default value
                 of 0 implies this field is not defined."
    DEFVAL { 0 }
    ::= { bgpRouteMapEntry 33 }

  bgpRouteMapSeUser OBJECT-TYPE
    SYNTAX      TruthValue
    MAX-ACCESS  read-create
    STATUS      current
    DESCRIPTION "Set to TRUE if the user exit for Sets is to be called."
    DEFVAL { false }
    ::= { bgpRouteMapEntry 34 }

  bgpRouteMapHitcnt OBJECT-TYPE
    SYNTAX      Integer32
    MAX-ACCESS  read-only
    STATUS      current
    DESCRIPTION "The number of times this row has been matched on."
    ::= { bgpRouteMapEntry 35 }

  bgpRouteMapClearcnt OBJECT-TYPE
    SYNTAX      TruthValue
    MAX-ACCESS  read-create
    STATUS      current
    DESCRIPTION "Set to TRUE to clear the counter associated with this row.
                 Reading the value of this field has no meaning."
    DEFVAL { false }
    ::= { bgpRouteMapEntry 36 }

  bgpRouteMapUserInfo OBJECT-TYPE
    SYNTAX      OCTET STRING (SIZE (255))
    MAX-ACCESS  read-create
    STATUS      current
    DESCRIPTION "A byte array to allow the user to put in information.  This
                 information will be passed to user exits."
    ::= { bgpRouteMapEntry 37 }

  bgpRouteMapType OBJECT-TYPE
    SYNTAX      BgpPermitOrDeny
    MAX-ACCESS  read-create
    STATUS      current
    DESCRIPTION "The type of route map entry.  This is only relevant for
                 policy filtering route maps.  It indicates the action
                 which should apply to a route which matches the route map
                 entry.  This field is ignored for route maps used for
                 aggregation."
    DEFVAL { permit }
    ::= { bgpRouteMapEntry 38 }

  bgpRouteMapContinue OBJECT-TYPE
    SYNTAX      Unsigned32
    MAX-ACCESS  read-create
    STATUS      current
    DESCRIPTION "Field containing the number of the route map clause to
                 continue processing at.  This is only valid for route
                 maps of type permit which are being used for policy
                 filtering.  If the route map matches, the set commands
                 for the matching clause will be applied, and filtering
                 will then continue from the route map clause specified in
                 this field.  If no continue clause is specified (value of
                 0), or the referenced route map clause does not exist,
                 then processing for the given route will be complete.
                 The continue field references the bgpRouteMapNumber field
                 of the desired clause.  In order to prevent processing
                 loops, the continue clause must have a higher number than
                 the current clause."
    DEFVAL { 0 }
    ::= { bgpRouteMapEntry 39 }

  bgpRouteMapOrfAssoc OBJECT-TYPE
    SYNTAX      BgpOrfAssociation
    MAX-ACCESS  read-create
    STATUS      current
    DESCRIPTION "The type of association (if any) this route map has with the
                 ORF protocol.  If set to local then the filtering information
                 contained within this route map will be advertised to peers
                 that advertise the appropriate ORF support.  If remote then
                 this route map was created in response to ORF(s) received
                 from a peer.  Note that there can be a maximum of one local
                 and one remote ORF Route Map per AFI/SAFI, per neighbor.
                 Note that all fields contained within this Route Map are
                 read-only if the value is remote."
    DEFVAL { noAssociation }
    ::= { bgpRouteMapEntry 40 }

  bgpRouteMapSeAsLimUpper OBJECT-TYPE
    SYNTAX       Unsigned32  (0..255)
    MAX-ACCESS   read-create
    STATUS       current
    DESCRIPTION  "If there is a match this will cause the AS_PATHLIMIT
                  attribute to be added if it does not already exist.  If
                  it does exist then it will be replaced.  In either case the
                  specified limit and the local AS will be set.  This can be
                  used for traffic engineering purposes in association with a
                  less specific prefix.  A value of zero is permissible and
                  restricts advertisement of locally generated routes to IBGP
                  peers.  However, an AS_PATHLIMIT with an upper bound value of
                  0 will not be externally visible.  That is, it will not be
                  included in UPDATEs.

                  This value is only used if bgpRouteMapSeAsLimitDef is TRUE."
    DEFVAL { 1 }
    ::= { bgpRouteMapEntry 41 }

  bgpRouteMapSeAsLimDef OBJECT-TYPE
    SYNTAX      TruthValue
    MAX-ACCESS  read-create
    STATUS      current
    DESCRIPTION "Whether or not the value in bgpRouteMapSeAsLimit should be
                 used for updating attributes."
    DEFVAL { false }
    ::= { bgpRouteMapEntry 42 }

  bgpRouteMapMaOrigin OBJECT-TYPE
    SYNTAX      BgpOriginCode
    MAX-ACCESS  read-create
    STATUS      current
    DESCRIPTION "The value to match the Origin attribute against.  This
                 value is only used if bgpRouteMapMaOriginDef is TRUE."
    DEFVAL { originIncomplete }
    ::= { bgpRouteMapEntry 43 }

  bgpRouteMapMaOriginDef OBJECT-TYPE
    SYNTAX      TruthValue
    MAX-ACCESS  read-create
    STATUS      current
    DESCRIPTION "Whether or not the value in bgpRouteMapMaOrigin should be
                 used for matching."
    DEFVAL { false }
    ::= { bgpRouteMapEntry 44 }

  bgpRouteMapSeMedDelta OBJECT-TYPE
    SYNTAX      Unsigned32
    MAX-ACCESS  read-create
    STATUS      current
    DESCRIPTION "If there is a match this will cause the MED attribute to
                 be incremented (or decremented) by the value specified.  The
                 direction of the value change is defined by
                 bgpRouteMapSeMedDeltaType.

                 The resulting MED value will not wrap, but will take a
                 minimum value of 0 and a maximum value of 4294967295.

                 This field is disabled by setting the value to zero.  The
                 field must be disabled if either bgpRouteMapSeMedDef or
                 bgpRouteMapSeMedIgp is set to TRUE."
    DEFVAL { 0 }
    ::= { bgpRouteMapEntry 45 }

  bgpRouteMapSeMedDeltaTyp OBJECT-TYPE
    SYNTAX      BgpMedDeltaType
    MAX-ACCESS  read-create
    STATUS      current
    DESCRIPTION "Whether to increment or decrement the MED attribute by the
                 value in bgpRouteMapSeMedDelta."
    DEFVAL { increment }
    ::= { bgpRouteMapEntry 46 }

  bgpRouteMapSeMedIgp OBJECT-TYPE
    SYNTAX      TruthValue
    MAX-ACCESS  read-create
    STATUS      current
    DESCRIPTION "If there is a match this will cause the MED attribute to
                 be set to the IGP distance to the next hop.

                 This field must be set to FALSE if either bgpRouteMapSeMedDef
                 is set to TRUE or bgpRouteMapSeMedDelta is non-zero."
    DEFVAL { false }
    ::= { bgpRouteMapEntry 47 }

  bgpRouteMapSeAsPrependCount OBJECT-TYPE
    SYNTAX      Unsigned32
    MAX-ACCESS  read-create
    STATUS      current
    DESCRIPTION "To prepend AS numbers to the AS-Path, set
                 bgpRouteMapSeAsPrependCount to the count of the AS numbers
                 to prepend, set bgpRouteMapSeAsPrependSize to indicate
                 whether the values are 2 or 4 octet AS numbers and fill in
                 bgpRouteMapSeAsPrependAsVals with the AS numbers themselves.

                 When exporting routes to EBGP, BGP applies the AS-prepend
                 rule before prepending the local AS number as required by
                 the BGP specification.  This ensures that the local AS
                 number is always the first AS number in the AS path in this
                 case.

                 This field can only be updated if the row is not active."
    DEFVAL { 0 }
    ::= { bgpRouteMapEntry 48 }

  bgpRouteMapSeAsPrependSize OBJECT-TYPE
    SYNTAX      BgpAsSize
    MAX-ACCESS  read-create
    STATUS      current
    DESCRIPTION "The size of AS numbers in the field
                 bgpRouteMapSeAsPrependAsVals to prepend to the AS path if
                 there is a match.  This field is only used if
                 bgpRouteMapSeAsPrependCount is non-zero.

                 This field can only be updated if the row is not active."
    DEFVAL { twoOctet }
    ::= { bgpRouteMapEntry 49 }

  bgpRouteMapSeAsPrependAsVals OBJECT-TYPE
    SYNTAX      OCTET STRING (SIZE (0..128))
    MAX-ACCESS  read-create
    STATUS      current
    DESCRIPTION "An array containing the AS numbers to prepend to the AS
                 path if there is a match.  The length of each AS number is
                 given by bgpRouteMapSeAsPrependSize.  This field is only
                 used if bgpRouteMapSeAsPrependCount is non-zero.

                 The count of AS numbers is given by
                 bgpRouteMapSeAsPrependCount.

                 This field can only be updated if the row is not active."
    ::= { bgpRouteMapEntry 50 }

  bgpRouteMapMaAnd OBJECT-TYPE
    SYNTAX      TruthValue
    MAX-ACCESS  read-create
    STATUS      current
    DESCRIPTION "Indicates that the match statements in this route map
                 should be logically ANDed with the match statements in the
                 route map indicated by bgpRouteMapContinue.  This field is
                 only relevant for policy route maps.

                 If the route map indicated by bgpRouteMapContinue is not
                 found then the match will fail.

                 All route maps in a series must have the same
                 bgpRouteMapType.

                 If this field is set then no set statements can be
                 configured in the row.

                 This field can only be updated if the row is not active."
    DEFVAL { false }
    ::= { bgpRouteMapEntry 51 }

-------------------------------------------------------------------------------

--
-- DC-BGP IP Prefix List Table
--
-- This table is used to create and manage DC-BGP IP Prefix Lists.  This is
-- tied to a single route map and used when a route attribute (NLRI, Next Hop
-- or source address) is being matched against any one of a list of IP
-- addresses.  Note that when the associated route map is destroyed, this
-- entry will also be destroyed.
--
-- Certain ORF related restrictions apply to entries in this table.  If an
-- entry in this table represents an ORF entry learned from a peer then all
-- fields are read-only.  For locally created entries the bgpIpPreMatchType
-- field is ignored unless the entry is linked to a route map with
-- bgpRouteMapOrfAssoc set to local.
--

  bgpIpPreTable OBJECT-TYPE
  -- FAMILY-SHORT-NAME BGP_IPP
    SYNTAX      SEQUENCE OF BgpIpPreEntry
    MAX-ACCESS  not-accessible
    STATUS      current
    DESCRIPTION "The table of DC-BGP IP Prefix Lists."
    ::= { bgpPib 2 }

  bgpIpPreEntry OBJECT-TYPE
    SYNTAX      BgpIpPreEntry
    MAX-ACCESS  not-accessible
    STATUS      current
    DESCRIPTION "Each entry represents an IP Prefix."
    INDEX { bgpRmEntIndex,
            bgpRouteMapIndex,
            bgpRouteMapNumber,
            bgpIpPreMatch,
            bgpIpPreNumber }
    ::= { bgpIpPreTable 1 }

  BgpIpPreEntry ::= SEQUENCE {
      bgpIpPreMatch       BgpIpMatchType,
      bgpIpPreNumber      Unsigned32,
      bgpIpPreRowStatus   RowStatus,
      bgpIpPreAfi         BgpAfi,
      bgpIpPreSafi        BgpSafi,
      bgpIpPreAddr        InetAddress,
      bgpIpPreLen         InetAddressPrefixLength,
      bgpIpPreGe          Integer32,
      bgpIpPreLe          Integer32,
      bgpIpPreType        BgpPermitOrDeny
      }

  bgpIpPreMatch OBJECT-TYPE
    SYNTAX      BgpIpMatchType
    MAX-ACCESS  not-accessible
    STATUS      current
    DESCRIPTION "The index of this bgpIpPreEntry.  This decides what match
                 command is used by the route map this list is tied to."
    ::= { bgpIpPreEntry 4 }

  bgpIpPreNumber OBJECT-TYPE
    SYNTAX      Unsigned32
    MAX-ACCESS  not-accessible
    STATUS      current
    DESCRIPTION "The index of this bgpIpPreEntry.  This number is used to
                 reference more than one filter per route map index."
    ::= { bgpIpPreEntry 5 }

  bgpIpPreRowStatus OBJECT-TYPE
    SYNTAX      RowStatus
    MAX-ACCESS  read-create
    STATUS      current
    DESCRIPTION "Used to create and delete a Prefix."
    ::= { bgpIpPreEntry 6 }

  bgpIpPreAfi OBJECT-TYPE
    SYNTAX      BgpAfi
    MAX-ACCESS  read-create
    STATUS      current
    DESCRIPTION "The AFI of the address prefix.

                 This MIB is intended for IP prefix matching, so AFI = IPv4
                 and IPv6 are supported but AFI = L2VPN is not supported."
    DEFVAL { ipv4 }
    ::= { bgpIpPreEntry 7 }

  bgpIpPreSafi OBJECT-TYPE
    SYNTAX      BgpSafi
    MAX-ACCESS  read-create
    STATUS      current
    DESCRIPTION "The SAFI of the address prefix.

                 This MIB is intended for IP prefix matching, so AFI/SAFI =
                 l2VPN/VPLS is not supported."
    DEFVAL { unicast }
    ::= { bgpIpPreEntry 8 }

  bgpIpPreAddr OBJECT-TYPE
    SYNTAX      InetAddress (SIZE(0..32))
    MAX-ACCESS  read-create
    STATUS      current
    DESCRIPTION "The Address part of the prefix.

                 This is matched against the line format BGP NLRI omitting
                 any NLRI length field and any leading MPLS labels.

                 For SAFI 128 this includes the Route Distinguisher as well
                 as the IPv4 or IPv6 address prefix."
    DEFVAL { '00'h }
    ::= { bgpIpPreEntry 9 }

  bgpIpPreLen OBJECT-TYPE
    SYNTAX      InetAddressPrefixLength
    MAX-ACCESS  read-create
    STATUS      current
    DESCRIPTION "The Length (in bits) part of the prefix (as in the 16 in a
                 128.128/16 prefix).  When attempting to match a prefix to this
                 address, only the first len bits of the match prefix are
                 checked.  This allows for wildcard matching when combined with
                 le and/or ge."
    DEFVAL { 0 }
    ::= { bgpIpPreEntry 10 }

  bgpIpPreGe OBJECT-TYPE
    SYNTAX      Integer32
    MAX-ACCESS  read-create
    STATUS      current
    DESCRIPTION "The GE value of the prefix.  GE and LE allow the range of the
                 prefix length to be matched on to be varied.  The range is
                 assumed to be from ge-value to the address length of the
                 family if only the ge attribute is specified, and from len to
                 le-value if only the le attribute is specified.

                 A specified ge-value and/or le-value must satisfy the
                 following condition:

                 len <= ge-value <= le-value <= address length of family."
    DEFVAL { 0 }
    ::= { bgpIpPreEntry 11 }

  bgpIpPreLe OBJECT-TYPE
    SYNTAX      Integer32
    MAX-ACCESS  read-create
    STATUS      current
    DESCRIPTION "The LE value of the prefix.  GE and LE allow the range of the
                 prefix length to be matched on to be varied.  The range is
                 assumed to be from ge-value to the address length of the
                 family if only the ge attribute is specified, and from len to
                 le-value if only the le attribute is specified.

                 A specified ge-value and/or le-value must satisfy the
                 following condition:

                 len <= ge-value <= le-value <= address length of family."
    DEFVAL { 0 }
    ::= { bgpIpPreEntry 12 }

  bgpIpPreType OBJECT-TYPE
    SYNTAX       BgpPermitOrDeny
    MAX-ACCESS   read-create
    STATUS       current
    DESCRIPTION  "The type of this prefix.  This is only applicable if this
                  prefix is linked to a route map with an ORF association and
                  allows the entry to override the action of the route map.
                  This field is ignored otherwise."
    DEFVAL { permit }
    ::= { bgpIpPreEntry 13 }

-------------------------------------------------------------------------------

--
-- DC-BGP Peer Group Table
--
-- This table is used to create and manage Peer Groups.
--

  bgpPeergrTable OBJECT-TYPE
  -- FAMILY-SHORT-NAME BGP_PGR
    SYNTAX      SEQUENCE OF BgpPeergrEntry
    MAX-ACCESS  not-accessible
    STATUS      current
    DESCRIPTION "The table of peer groups."
    ::= { bgpPib 7 }

  bgpPeergrEntry OBJECT-TYPE
    SYNTAX      BgpPeergrEntry
    MAX-ACCESS  not-accessible
    STATUS      current
    DESCRIPTION "Each entry represents a peer group."
    INDEX { bgpRmEntIndex,
            bgpPeergrIndex }
    ::= { bgpPeergrTable 1 }

  BgpPeergrEntry ::= SEQUENCE {
      bgpPeergrIndex                   Unsigned32,
      bgpPeergrRowStatus               RowStatus,
      bgpPeergrConfig                  Unsigned32,
      bgpPeergrArea                    BgpIbgpOrEbgp,
      bgpPeergrAggrConfedAS            TruthValue,
      bgpPeergrSoftResetWithStoredInfo TruthValue,
      bgpPeergrAllowLocalAs            Unsigned32,
      bgpPeergrDisableSenderLoopDetect TruthValue,
      bgpPeergrNxtHopSlf               TruthValue,
      bgpPeergrThirdPtyNxtHop          TruthValue,
      bgpPeergrNxtHopPeer              TruthValue,
      bgpPeergrEnableAttributeDiscard  TruthValue
      }

  bgpPeergrIndex OBJECT-TYPE
    SYNTAX      Unsigned32
    MAX-ACCESS  not-accessible
    STATUS      current
    DESCRIPTION "The index of this bgpPeergrEntry.  This is the index of the
                 peer group."
    ::= { bgpPeergrEntry 2 }

  bgpPeergrRowStatus OBJECT-TYPE
    SYNTAX      RowStatus
    MAX-ACCESS  read-create
    STATUS      current
    DESCRIPTION "Used to create and delete a peer group."
    ::= { bgpPeergrEntry 3 }

  bgpPeergrConfig OBJECT-TYPE
    SYNTAX      Unsigned32
    MAX-ACCESS  read-create
    STATUS      current
    DESCRIPTION "The index of the Policy Configuration Table this peer group
                 uses for its policy setup.  A value of zero indicates that
                 the peer group is not associated with any config row."
    ::= { bgpPeergrEntry 4 }

  bgpPeergrArea OBJECT-TYPE
    SYNTAX      BgpIbgpOrEbgp
    MAX-ACCESS  read-create
    STATUS      current
    DESCRIPTION "Whether this peer group is for iBGP, confederation eBGP,
                 or eBGP peers.  This field can only be changed when the
                 row is not active."
    DEFVAL { ibgp }
    ::= { bgpPeergrEntry 5 }

  bgpPeergrAggrConfedAS OBJECT-TYPE
    SYNTAX      TruthValue
    MAX-ACCESS  read-create
    STATUS      current
    DESCRIPTION "This value indicates whether or not the neighbors in the
                 peer group understand aggregated confederation AS_PATH
                 information.  If set to FALSE, no confederation
                 AS_PATH information is included in aggregate AS_PATHs to
                 any of the peers in the peer group.  This field can only
                 be changed when the row is not active."
    DEFVAL { true }
    ::= { bgpPeergrEntry 6 }

  bgpPeergrSoftResetWithStoredInfo OBJECT-TYPE
    SYNTAX      TruthValue
    MAX-ACCESS  read-create
    STATUS      current
    DESCRIPTION "This object is used in conjunction with
                 bgpPeergrAfiSafiSoftResetStore to configure 'soft reset with
                 stored routing information'.  This option causes all routes
                 learned from peers in the peer group to be stored so that
                 the ARI can be recalculated (for example, due to a change in
                 import policy) without performing a route refresh or
                 restarting the peer session.

                 When bgpPeergrSoftResetWithStoredInfo is 'false', BGP does not
                 perform soft reset for any address family.

                 When bgpPeergrSoftResetWithStoredInfo is 'true', BGP performs
                 soft reset for those address families for which
                 bgpPeergrAfiSafiSoftResetStore is 'true'.

                 There is a significant occupancy impact associated with
                 this option.

                 IMPORTANT: Note that a change to this field does not affect
                 peer sessions that are already underway.  Restarting such
                 sessions will cause the new value to take effect.

                 Note that this option overlaps with route refresh (RR) and
                 Outbound Route Filter (ORF) behavior:  To clarify, when this
                 option is enabled, the following also occur for sessions
                 to peers associated with the peer group.

                 - Routes are stored in this way, even if the peer advertizes
                   support for RR or ORF.
                 - Route refresh and ORF capabilities continue to be advertized
                   (if configured).
                 - A route refresh will never be sent to this peer, apart from
                   one (containing no ORFs) at the start of the session if
                   both peers support ORF.
                 - ORFs are never sent to the peer.
                 - DC-BGP still responds to RR requests from the peer (if it
                   advertizes the RR capability).
                 - DC-BGP still accepts ORF requests from the peer (if it
                   advertizes the ORF capability)."
    DEFVAL { false }
    ::= { bgpPeergrEntry 7 }

   bgpPeergrAllowLocalAs OBJECT-TYPE
    SYNTAX      Unsigned32 (0..255)
    MAX-ACCESS  read-create
    STATUS      current
    DESCRIPTION "The number of instances of the local AS identifier that
                 may be contained in the route's AS-Path without rejecting
                 the route.

                 The AS-Path attribute of a BGP route contains the
                 identifiers of the Autonomous Systems traversed by the
                 route.  When a route is received with an AS-Path
                 containing the local AS identifier, it normally indicates
                 a routing loop, and the default behavior is to reject the
                 route.  This object allows this behavior to be
                 over-ridden.

                 This is useful, for example, for VPN routes, where routes
                 from one CE router are advertised to other CE routers
                 through a provider's BGP network.  Two CE routers in the
                 same AS can enable this feature to prevent routes from the
                 other CE from being discarded.

                 When bgpPeergrAllowLocalAs is set to a non-zero value,
                 that value is used for all address families, and the value
                 of bgpPeergrAfiSafiAllowLocalAs is ignored.

                 Alternatively, the value may be configured independently
                 for each address family.  To do this, set
                 bgpPeergrAllowLocalAs to 0 and set the value of
                 bgpPeergrAfiSafiAllowLocalAs for each address family.

                 Changing the value of this object while the peer is active
                 triggers BGP to refresh its routes from the peer."
    DEFVAL { 0 }
    ::= { bgpPeergrEntry 8 }

  bgpPeergrDisableSenderLoopDetect OBJECT-TYPE
    SYNTAX      TruthValue
    MAX-ACCESS  read-create
    STATUS      current
    DESCRIPTION "This field is used in conjunction with
                 bgpPeergrAfiSafiDisSndLpDetect to indicate whether BGP
                 should disable sender-side loop detection when sending
                 routes to the peer.

                 By default, BGP performs sender side loop detection.  That
                 is, it will not advertise a route to a peer if the AS-Path
                 of the route already contains the peer's AS number.  A
                 peer would typically discard such routes, so this is
                 normally a useful optimization.

                 However, the peer may be configured to accept such routes
                 (see bgpPeergrAllowLocalAs).  In this case it is necessary
                 to disable sender-side loop detection, by setting
                 bgpPeergrDisableSndLpDetect to 'true'.

                 Sender-side loop detection may be disabled independently
                 for each address family.  When bgpPeergrDisableSndLpDetect
                 is set to 'true', set bgpPeergrAfiSafiDisSndLpDetect to
                 'true' or 'false' to disable or enable sender-side loop
                 detection for each address family.

                 If the value is changed while the peer session is active, BGP
                 will check for any routes that need to be advertised or
                 withdrawn as a result of the change."
    DEFVAL { false }
    ::= { bgpPeergrEntry 9 }

  bgpPeergrNxtHopSlf OBJECT-TYPE
    SYNTAX      TruthValue
    MAX-ACCESS  read-create
    STATUS      current
    DESCRIPTION "Whether or not the peer group has next hop self configured.

                 Address family specific configuration of this option is
                 provided by the field bgpPeergrAfiSafiNxtHopSlf.

                 When bgpPeergrNxtHopSlf is 'false', BGP does not perform
                 next-hop-self for any address family.

                 When bgpPeergrNxtHopSlf is 'true', BGP performs
                 next-hop-self for those address families for which
                 bgpPeergrAfiSafiNxtHopSlf is 'true'."
    DEFVAL { false }
    ::= { bgpPeergrEntry 10 }

  bgpPeergrThirdPtyNxtHop OBJECT-TYPE
    SYNTAX      TruthValue
    MAX-ACCESS  read-create
    STATUS      current
    DESCRIPTION "Whether or not the local BGP speaker should advertise routes
                 received from this peer group using third party next hop
                 (this is optional behaviour described in the BGP
                 specification).

                 This field is only used when exporting routes to other EBGP
                 peers, and when bgpPeergrNxtHopSlf is 'false'."
    DEFVAL { true }
    ::= { bgpPeergrEntry 11 }

  bgpPeergrNxtHopPeer OBJECT-TYPE
    SYNTAX      TruthValue
    MAX-ACCESS  read-create
    STATUS      current
    DESCRIPTION "Whether or not the local BGP speaker should override the use
                 of third party next hop by an EBGP peer.  If an EBGP peer
                 speaker uses third party next hop, routes learnt from the peer
                 may specify a next hop belonging to a router that the local
                 BGP speaker does not peer with.

                 If this field is set to 'true', then all data forwarded along
                 a route learnt from an EBGP peer will be sent to the EBGP
                 peer.  The peer's address is put into the BGP next hop field
                 when the route is advertised to IBGP peers.

                 If set to 'false', then data is sent to the next hop
                 specified by the peer.  The field is only used when importing
                 routes from EBGP."
    DEFVAL { false }
    ::= { bgpPeergrEntry 12 }

  bgpPeergrEnableAttributeDiscard OBJECT-TYPE
    SYNTAX      TruthValue
    MAX-ACCESS  read-create
    STATUS      current
    DESCRIPTION "This value indicates whether or not the 'attribute
                 discard' error handling mechanism is used for BGP UPDATE
                 messages received from peers in this peer group.  This
                 mechanism applies when a BGP UPDATE message is received
                 containig a malformed AGGREGATOR, AS4_AGGREGATOR, AS4_PATH
                 or ATOMIC_AGGREGATE attribute.

                 When set to 'false', the error handling mechanism defined
                 in the original BGP specification is used, and the BGP
                 session is reset.  This can lead to session flapping and
                 network instability, even though routing is not adversely
                 affected by the presence of these malformed attributes.

                 When set to 'true', the alternative error handling
                 mechanism of 'attribute discard' is used, where the
                 attribute is dropped and the rest of the BGP UPDATE
                 message is processed as normal.

                 Use of 'attribute discard' error handling is fixed at the
                 start of a BGP session, so changes to this field take
                 effect at the start of the next session."
    DEFVAL { false }
    ::= { bgpPeergrEntry 13 }

-------------------------------------------------------------------------------

--
-- DC-BGP Config Table
--
-- This table is used to create and manage Policy Configuration set-ups that
-- are used either by a peer or a peer group.
--
-- Note that in use it is not compulsory to define the Route Map entries.
-- However, it would be unusual not to have any defined unless this is an
-- entry for a neighbor which is in a peer group.
--

  bgpConfigTable OBJECT-TYPE
  -- FAMILY-SHORT-NAME BGP_CNF
    SYNTAX      SEQUENCE OF BgpConfigEntry
    MAX-ACCESS  not-accessible
    STATUS      current
    DESCRIPTION "The table of Policy Configuration."
    ::= { bgpPib 8 }

  bgpConfigEntry OBJECT-TYPE
    SYNTAX      BgpConfigEntry
    MAX-ACCESS  not-accessible
    STATUS      current
    DESCRIPTION "Each entry represents a policy configuration."
    INDEX { bgpRmEntIndex,
            bgpConfigIndex }
    ::= { bgpConfigTable 1 }

  BgpConfigEntry ::= SEQUENCE {
      bgpConfigIndex            Unsigned32,
      bgpConfigRowStatus        RowStatus,
      bgpConfigRtgrimpe         Unsigned32,
      bgpConfigRtgrimde         Unsigned32,
      bgpConfigRtgrexpe         Unsigned32,
      bgpConfigRtgrexde         Unsigned32,
      bgpConfigDefImport        BgpPermitOrDeny,
      bgpConfigDefExport        BgpPermitOrDeny,
      bgpConfigNxtHopSlf        TruthValue,
      bgpConfigRemove           TruthValue,
      bgpConfigImportMap        Unsigned32,
      bgpConfigExportMap        Unsigned32,
      bgpConfigAdvertiseMap     Unsigned32,
      bgpConfigNonExistMap      Unsigned32,
      bgpConfigBlockCondAdv     TruthValue,
      bgpConfigThirdPtyNxtHop   TruthValue,
      bgpConfigNxtHopPeer       TruthValue,
      bgpConfigCondAdvOn        TruthValue
      }

  bgpConfigIndex OBJECT-TYPE
    SYNTAX      Unsigned32
    MAX-ACCESS  not-accessible
    STATUS      current
    DESCRIPTION "The index of this bgpConfigEntry.  This is the Index of the
                 Policy Configuration."
    ::= { bgpConfigEntry 2 }

  bgpConfigRowStatus OBJECT-TYPE
    SYNTAX      RowStatus
    MAX-ACCESS  read-create
    STATUS      current
    DESCRIPTION "Used to create and delete a Policy Configuration."
    ::= { bgpConfigEntry 3 }

  bgpConfigRtgrimpe OBJECT-TYPE
    SYNTAX      Unsigned32
    MAX-ACCESS  read-create
    STATUS      obsolete
    DESCRIPTION "The index of the Route Map Group this configuration uses for
                 permitted route imports.  The default value of 0 means no
                 route map group is defined."
    DEFVAL { 0 }
    ::= { bgpConfigEntry 4 }

  bgpConfigRtgrimde OBJECT-TYPE
    SYNTAX      Unsigned32
    MAX-ACCESS  read-create
    STATUS      obsolete
    DESCRIPTION "The index of the Route Map Group this configuration uses for
                 denied route imports.  The default value of 0 means no
                 route map group is defined."
    DEFVAL { 0 }
    ::= { bgpConfigEntry 5 }

  bgpConfigRtgrexpe OBJECT-TYPE
    SYNTAX      Unsigned32
    MAX-ACCESS  read-create
    STATUS      obsolete
    DESCRIPTION "The index of the Route Map Group this configuration uses for
                 permitted route exports.  The default value of 0 means no
                 route map group is defined."
    DEFVAL { 0 }
    ::= { bgpConfigEntry 6 }

  bgpConfigRtgrexde OBJECT-TYPE
    SYNTAX      Unsigned32
    MAX-ACCESS  read-create
    STATUS      obsolete
    DESCRIPTION "The index of the Route Map Group this configuration uses for
                 denied route exports.  The default value of 0 means no
                 route map group is defined."
    DEFVAL { 0 }
    ::= { bgpConfigEntry 7 }

  bgpConfigDefImport OBJECT-TYPE
    SYNTAX      BgpPermitOrDeny
    MAX-ACCESS  read-create
    STATUS      obsolete
    DESCRIPTION "Whether routes not covered by the two import route map groups
                 are permitted or denied by default."
    DEFVAL { permit }
    ::= { bgpConfigEntry 8 }

  bgpConfigDefExport OBJECT-TYPE
    SYNTAX      BgpPermitOrDeny
    MAX-ACCESS  read-create
    STATUS      obsolete
    DESCRIPTION "Whether routes not covered by the two export route map groups
                 are permitted or denied by default."
    DEFVAL { permit }
    ::= { bgpConfigEntry 9 }

  bgpConfigNxtHopSlf OBJECT-TYPE
    SYNTAX      TruthValue
    MAX-ACCESS  read-create
    STATUS      obsolete
    DESCRIPTION "This field is now deprecated."
    DEFVAL { false }
    ::= { bgpConfigEntry 10 }

  bgpConfigRemove OBJECT-TYPE
    SYNTAX      TruthValue
    MAX-ACCESS  read-create
    STATUS      current
    DESCRIPTION "Whether private AS numbers are removed from the AS path before
                 sending an update to this peer.  This is only relevant for an
                 eBGP peer."
    DEFVAL { true }
    ::= { bgpConfigEntry 11 }

  bgpConfigImportMap OBJECT-TYPE
    SYNTAX      Unsigned32
    MAX-ACCESS  read-create
    STATUS      current
    DESCRIPTION "The index of the Route Map this configuration uses for
                 route imports.  The default value of 0 means no route map
                 is defined, and all routes will be imported."
    DEFVAL { 0 }
    ::= { bgpConfigEntry 12 }

  bgpConfigExportMap OBJECT-TYPE
    SYNTAX      Unsigned32
    MAX-ACCESS  read-create
    STATUS      current
    DESCRIPTION "The index of the Route Map this configuration uses for
                 route exports.  The default value of 0 means no route map
                 is defined, and all routes will be exported."
    DEFVAL { 0 }
    ::= { bgpConfigEntry 13 }

  bgpConfigAdvertiseMap OBJECT-TYPE
    SYNTAX      Unsigned32
    MAX-ACCESS  read-create
    STATUS      current
    DESCRIPTION "The index of the Route Map to use as an advertise map.
                 This is only applicable to conditional advertisement.  In
                 order for the policy configuration to be valid, both
                 advertise_map and non_exist_map must be specified.  Both
                 of these maps must be of type AMB_BGP_PERMIT and at least
                 specify an exact NLRI prefix match, although they may
                 specify additional match fields.  Routes matching the
                 advertise map will only be advertised to neighbors or peer
                 groups assigned this policy configuration if there are no
                 routes in the LocRIB which match the non-exist map."
    DEFVAL { 0 }
    ::= { bgpConfigEntry 14 }

  bgpConfigNonExistMap OBJECT-TYPE
    SYNTAX      Unsigned32
    MAX-ACCESS  read-create
    STATUS      current
    DESCRIPTION "The index of the Route Map to use as a non-exist map.  See
                 the above comment for the bgpConfigAdvertiseMap field for
                 a description of how this is used."
    DEFVAL { 0 }
    ::= { bgpConfigEntry 15 }

  bgpConfigBlockCondAdv OBJECT-TYPE
    SYNTAX      TruthValue
    MAX-ACCESS  read-only
    STATUS      current
    DESCRIPTION "Flag to indicate whether the route(s) that match the
                 advertise route-map are currently being blocked from
                 advertisement."
    ::= { bgpConfigEntry 16 }

  bgpConfigThirdPtyNxtHop OBJECT-TYPE
    SYNTAX      TruthValue
    MAX-ACCESS  read-create
    STATUS      obsolete
    DESCRIPTION "This field is now deprecated."
    DEFVAL { true }
    ::= { bgpConfigEntry 17 }

  bgpConfigNxtHopPeer OBJECT-TYPE
    SYNTAX      TruthValue
    MAX-ACCESS  read-create
    STATUS      obsolete
    DESCRIPTION "This field is now deprecated."
    DEFVAL { false }
    ::= { bgpConfigEntry 18 }

  bgpConfigCondAdvOn OBJECT-TYPE
    SYNTAX      TruthValue
    MAX-ACCESS  read-create
    STATUS      current
    DESCRIPTION "Whether or not Conditional Advertisement is enabled.  Set
                 this to AMB_FALSE before changing the conditional
                 advertisement configuration, as certain intermediate
                 configurations (eg.  advertise map defined without
                 non-exist map) are illegal.  Set to AMB_TRUE when
                 configuration is complete."
    DEFVAL { false }
    ::= { bgpConfigEntry 19 }

-------------------------------------------------------------------------------

--
-- DC-BGP Flap Config Table
--
-- This table is used to create and manage Route Flap Damping Configuration
-- parameters.
--

  bgpFlapConfigTable OBJECT-TYPE
  -- FAMILY-SHORT-NAME BGP_FLP
    SYNTAX      SEQUENCE OF BgpFlapConfigEntry
    MAX-ACCESS  not-accessible
    STATUS      current
    DESCRIPTION "The table of Route Flap Damping configuration parameters."
    ::= { bgpPib 9 }

  bgpFlapConfigEntry OBJECT-TYPE
    SYNTAX      BgpFlapConfigEntry
    MAX-ACCESS  not-accessible
    STATUS      current
    DESCRIPTION "Each entry represents a set of configuration parameters used
                 when damping a route.  It is expected there will not be many
                 entries in this table but no limit is put on this.  Note that
                 if a field is changed from using old parameters to new ones,
                 the new parameters do not take effect those routes that were
                 already damped using the old parameters.  This will work
                 itself out over time, and the operator has the option of
                 undamping a damped route if they desire."
    INDEX { bgpRmEntIndex,
            bgpFlapConfigIndex }
    ::= { bgpFlapConfigTable 1 }

  BgpFlapConfigEntry ::= SEQUENCE {
      bgpFlapConfigIndex       Unsigned32,
      bgpFlapConfigRowStatus   RowStatus,
      bgpFlapConfigCut         Integer32,
      bgpFlapConfigReuse       Integer32,
      bgpFlapConfigThold       Integer32,
      bgpFlapConfigDecayok     Integer32,
      bgpFlapConfigDecayng     Integer32,
      bgpFlapConfigTmaxok      Integer32,
      bgpFlapConfigTmaxng      Integer32
      }

  bgpFlapConfigIndex OBJECT-TYPE
    SYNTAX      Unsigned32
    MAX-ACCESS  not-accessible
    STATUS      current
    DESCRIPTION "The index of this bgpFlapConfigEntry.  This is the Index used
                 to reference this config setup from the route map."
    ::= { bgpFlapConfigEntry 2 }

  bgpFlapConfigRowStatus OBJECT-TYPE
    SYNTAX      RowStatus
    MAX-ACCESS  read-create
    STATUS      current
    DESCRIPTION "Used to create and delete a flap config set."
    ::= { bgpFlapConfigEntry 3 }

  bgpFlapConfigCut OBJECT-TYPE
    SYNTAX      Integer32
    MAX-ACCESS  read-create
    STATUS      current
    DESCRIPTION "The cutoff threshold expressed as a number of route
                 withdrawals.  Above this level, the route will be suppressed.
                 This value must be greater than or equal to
                 bgpFlapConfigReuse.  The scale used is 100 times that used in
                 RFC2439 so the suggested value is 125, not 1.25 as suggested
                 in the RFC."
    DEFVAL { 125 }
    ::= { bgpFlapConfigEntry 4 }

  bgpFlapConfigReuse OBJECT-TYPE
    SYNTAX      Integer32
    MAX-ACCESS  read-create
    STATUS      current
    DESCRIPTION "The reuse threshold expressed as a number of route
                 withdrawals.  Below this level the route will be reused.  The
                 scale used is 100 times that used in RFC2439 so the suggested
                 value is 50, not 0.5 as suggested in the RFC."
    DEFVAL { 50 }
    ::= { bgpFlapConfigEntry 5 }

  bgpFlapConfigThold OBJECT-TYPE
    SYNTAX      Integer32
    UNITS       "seconds"
    MAX-ACCESS  read-create
    STATUS      current
    DESCRIPTION "The maximum time a route can be suppressed for (held).  This
                 value must be less than or equal to bgpRmEntFlapReusemax in
                 the bgpRmEntTable."
    DEFVAL { 900 }
    ::= { bgpFlapConfigEntry 6 }

  bgpFlapConfigDecayok OBJECT-TYPE
    SYNTAX      Integer32
    UNITS       "seconds"
    MAX-ACCESS  read-create
    STATUS      current
    DESCRIPTION "The decay half life of the stability figure while the route is
                 still reachable (whether suppressed or not).  This value must
                 be less than bgpFlapConfigTmaxok."
    DEFVAL { 300 }
    ::= { bgpFlapConfigEntry 7 }

  bgpFlapConfigDecayng OBJECT-TYPE
    SYNTAX      Integer32
    UNITS       "seconds"
    MAX-ACCESS  read-create
    STATUS      current
    DESCRIPTION "The decay half life of the stability figure while the route is
                 not reachable (whether suppressed or not).  If it is not
                 defined or set to zero, no decay occurs if the route is
                 unreachable.  This value must be less than
                 bgpFlapConfigTmaxng."
    DEFVAL { 900 }
    ::= { bgpFlapConfigEntry 8 }

  bgpFlapConfigTmaxok OBJECT-TYPE
    SYNTAX      Integer32
    UNITS       "seconds"
    MAX-ACCESS  read-create
    STATUS      current
    DESCRIPTION "The decay memory limit.  The maximum time any memory of a
                 previous instability is retained given the route state is
                 unchanged and reachable.  This is generally used to
                 determine array sizes."
    DEFVAL { 900 }
    ::= { bgpFlapConfigEntry 9 }

  bgpFlapConfigTmaxng OBJECT-TYPE
    SYNTAX      Integer32
    UNITS       "seconds"
    MAX-ACCESS  read-create
    STATUS      current
    DESCRIPTION "The decay memory limit.  The maximum time any memory of a
                 previous instability is retained given the route state is
                 unchanged and unreachable.  This is generally used to
                 determine array sizes.  This value must be less than or equal
                 to bgpRmEntFlapFreemax in the bgpRmEntTable."
    DEFVAL { 1800 }
    ::= { bgpFlapConfigEntry 10 }

-------------------------------------------------------------------------------

--
-- DC-BGP Aggregate Address Table
--
-- This table is used to control how DC-BGP aggregates addresses.
--

  bgpAggregateTable OBJECT-TYPE
  -- FAMILY-SHORT-NAME BGP_AGA
    SYNTAX      SEQUENCE OF BgpAggregateEntry
    MAX-ACCESS  not-accessible
    STATUS      current
    DESCRIPTION "This table is used to control how DC-BGP aggregates
                 addresses.  Each entry in the table results in one aggregate
                 address being created.  This will result in an aggregate
                 entry in the routing table when at least one more specific
                 route matching the address specified is learnt.  If the
                 aggregate is marked as 'permanent', then an aggregate entry
                 is created in the routing table even if no more specific
                 matching routes are known.

                 The options allow configuration as to whether the AS_PATH
                 attribute keeps full information or not, and whether the more
                 specfic route is also entered in the routing table (the
                 summary only option).  These options can also be chosen on
                 a per route basis by matching on the advertise and suppress
                 route maps.

                 The attribute route map is used to set attributes of the
                 aggregated route if required.

                 It is possible to create overlapping entries in the table.
                 This can result in routes that match more than one
                 table entry.

                 -  If a route matches multiple aggregate addresses,
                 then it is suppressed any of the matching aggregates would
                 cause the route to be suppressed.

                 -  If a route matches the advertise map of an aggregate
                 address, then it is not aggregated by that aggregate address.
                 However, it may still be aggregated by other overlapping
                 aggregate addresses."
    ::= { bgpPib 10 }

  bgpAggregateEntry OBJECT-TYPE
    SYNTAX      BgpAggregateEntry
    MAX-ACCESS  not-accessible
    STATUS      current
    DESCRIPTION "Each entry represents a member of an aggregate address option
                 set."
    INDEX { bgpRmEntIndex,
            bgpAggrAfi,
            bgpAggrSafi,
            bgpAggrPrefix,
            bgpAggrPrefixLength }
    ::= { bgpAggregateTable 1 }

  BgpAggregateEntry ::= SEQUENCE {
      bgpAggrAfi              BgpAfi,
      bgpAggrSafi             BgpSafi,
      bgpAggrPrefix           InetAddress,
      bgpAggrPrefixLength     InetAddressPrefixLength,
      bgpAggrRowStatus        RowStatus,
      bgpAggrOptions          BgpAggregateOptions,
      bgpAggrSuppressMap      Unsigned32,
      bgpAggrAdvertiseMap     Unsigned32,
      bgpAggrAttributeMap     Unsigned32,
      bgpAggrPermanent        TruthValue
      }

  bgpAggrAfi OBJECT-TYPE
    SYNTAX      BgpAfi
    MAX-ACCESS  not-accessible
    STATUS      current
    DESCRIPTION "The AFI of the aggregating address."
    ::= { bgpAggregateEntry 2 }

  bgpAggrSafi OBJECT-TYPE
    SYNTAX      BgpSafi
    MAX-ACCESS  not-accessible
    STATUS      current
    DESCRIPTION "The SAFI of the aggregating address."
    ::= { bgpAggregateEntry 3 }

  bgpAggrPrefix OBJECT-TYPE
    SYNTAX      InetAddress (SIZE(0..32))
    MAX-ACCESS  not-accessible
    STATUS      current
    DESCRIPTION "The index of this bgpAggregateEntry.  This is the prefix of
                 the configured aggregating address."
    ::= { bgpAggregateEntry 4 }

  bgpAggrPrefixLength OBJECT-TYPE
    SYNTAX      InetAddressPrefixLength
    MAX-ACCESS  not-accessible
    STATUS      current
    DESCRIPTION "The index of this bgpAggregateEntry.  This is the length of
                 the prefix (in bits) of the configured aggregating address."
    ::= { bgpAggregateEntry 5 }

  bgpAggrRowStatus OBJECT-TYPE
    SYNTAX      RowStatus
    MAX-ACCESS  read-create
    STATUS      current
    DESCRIPTION "Used to create and delete an aggregate address option set."
    ::= { bgpAggregateEntry 6 }

  bgpAggrOptions OBJECT-TYPE
    SYNTAX      BgpAggregateOptions
    MAX-ACCESS  read-create
    STATUS      current
    DESCRIPTION "Options applied to this set of aggregate addresses.  Note with
                 no options, more specific routes are installed in the routing
                 table, but the AS_PATH will lose information as it will not
                 contain AS-SETs.  This is normally OK as it reduces route
                 flap.

                 Note that a route may be aggregated by multiple overlapping
                 aggregate addresses.  In this case, the route is suppressed
                 if any of the matching aggregates would cause the route to
                 be suppressed."
    DEFVAL { none }
    ::= { bgpAggregateEntry 7 }

  bgpAggrSuppressMap OBJECT-TYPE
    SYNTAX      Unsigned32
    MAX-ACCESS  read-create
    STATUS      current
    DESCRIPTION "The index of the Route Map used to suppress routes. The match
                 clauses of this route map are used to selectively suppress
                 more specific routes from being advertised.  No route map
                 should be defined here if a suppress option ('summary' or
                 'summaryAsSet') is configured in the bgpAggrOptions field."
    DEFVAL { 0 }
    ::= { bgpAggregateEntry 8 }

  bgpAggrAdvertiseMap OBJECT-TYPE
    SYNTAX      Unsigned32
    MAX-ACCESS  read-create
    STATUS      current
    DESCRIPTION "The index of the Route Map used to advertise routes. The match
                 clauses of this route map are used to select routes which
                 although they match the aggregate address, should not be
                 aggregated."
    DEFVAL { 0 }
    ::= { bgpAggregateEntry 9 }

  bgpAggrAttributeMap OBJECT-TYPE
    SYNTAX      Unsigned32
    MAX-ACCESS  read-create
    STATUS      current
    DESCRIPTION "The index of the Route Map used to set aggregated routes
                 attributes.  The set clauses of this route map are used to set
                 path attributes of the aggregated route."
    DEFVAL { 0 }
    ::= { bgpAggregateEntry 10 }

  bgpAggrPermanent OBJECT-TYPE
    SYNTAX      TruthValue
    MAX-ACCESS  read-create
    STATUS      current
    DESCRIPTION "If this field is set to TRUE, an aggregate entry is created in
                 the routing table and advertised to peers even if no
                 more-specific matching routes are known."
    DEFVAL { false }
    ::= { bgpAggregateEntry 11 }

-------------------------------------------------------------------------------

--
-- Cooperative Outbound Route Filtering Capability Table.
--
-- This table defines the Cooperative Route Filtering Capabilities.
-- Given a suitably configured corresponding entry in the bgpPeerOrfCapability
-- table these will be advertised to peers.

  bgpOrfCapabilityTable OBJECT-TYPE
  -- FAMILY-SHORT-NAME BGP_ORF_CAP
    SYNTAX      SEQUENCE OF BgpOrfCapabilityEntry
    MAX-ACCESS  not-accessible
    STATUS      current
    DESCRIPTION "DC-BGP ORF Capability Table."
    ::= { bgpPib 11 }

  bgpOrfCapabilityEntry OBJECT-TYPE
    SYNTAX      BgpOrfCapabilityEntry
    MAX-ACCESS  not-accessible
    STATUS      current
    DESCRIPTION "Entry containing information about support for an ORF
                 defined by <AFI, SAFI, ORF Type>."
    INDEX { bgpRmEntIndex,
            bgpOrfCapabilityAfi,
            bgpOrfCapabilitySafi,
            bgpOrfCapabilityOrfType }
    ::= { bgpOrfCapabilityTable 1 }

  BgpOrfCapabilityEntry ::= SEQUENCE {
      bgpOrfCapabilityAfi               BgpAfi,
      bgpOrfCapabilitySafi              BgpSafi,
      bgpOrfCapabilityOrfType           BgpOrfType,
      bgpOrfCapabilityAdminStatus       BgpAdminStatus,
      bgpOrfCapabilitySendReceive       BgpOrfSendReceive
      }

  bgpOrfCapabilityAfi OBJECT-TYPE
    SYNTAX      BgpAfi
    MAX-ACCESS  not-accessible
    STATUS      current
    DESCRIPTION "Specifies the address family with which this ORF is
                 associated."
    ::= { bgpOrfCapabilityEntry 2 }

  bgpOrfCapabilitySafi OBJECT-TYPE
    SYNTAX      BgpSafi
    MAX-ACCESS  not-accessible
    STATUS      current
    DESCRIPTION "Specifies the Subsequent Address Family Identifier with
                 which this ORF is associated."
    ::= { bgpOrfCapabilityEntry 3 }

  bgpOrfCapabilityOrfType OBJECT-TYPE
    SYNTAX      BgpOrfType
    MAX-ACCESS  not-accessible
    STATUS      current
    DESCRIPTION "Indicates the type of this ORF."
    ::= { bgpOrfCapabilityEntry 4 }

  bgpOrfCapabilityAdminStatus OBJECT-TYPE
    SYNTAX      BgpAdminStatus
    MAX-ACCESS  read-create
    STATUS      current
    DESCRIPTION "The administrative status for this ORF entry."
    DEFVAL { adminStatusDown }
    ::= { bgpOrfCapabilityEntry 5 }

  bgpOrfCapabilitySendReceive OBJECT-TYPE
    SYNTAX      BgpOrfSendReceive
    MAX-ACCESS  read-create
    STATUS      current
    DESCRIPTION "Indicates whether the sender is (a) willing to receive ORF
                 entries from its peer, (b) would like to send ORF entries
                 to its peer, or (c) both."
    DEFVAL { both }
    ::= { bgpOrfCapabilityEntry 6 }

-------------------------------------------------------------------------------

--
-- Cooperative Outbound Route Filtering Per Peer Capability Table.
--
-- This table defines the Cooperative Route Filtering Capabilities for a peer.
-- These will be advertised to the specified peer if, and only if, there is
-- a suitably configured corresponding entry in the bgpOrfCapabilityTable.

  bgpPeerOrfCapabilityTable OBJECT-TYPE
  -- FAMILY-SHORT-NAME BGP_PEER_ORF_CAP
    SYNTAX      SEQUENCE OF BgpPeerOrfCapabilityEntry
    MAX-ACCESS  not-accessible
    STATUS      current
    DESCRIPTION "DC-BGP Peer ORF Capability Table.

                 This table allows a user to configure ORF on a per peer basis.

                 Rows in this table cannot be created or destroyed manually.
                 A table entry is created for each supported address family and
                 ORF type when an entry in the bgpPeerTable is created.
                 The entries are destroyed when the bgpPeerTable entry
                 is destroyed."
    ::= { bgpPeerData 3 }

  bgpPeerOrfCapabilityEntry OBJECT-TYPE
    SYNTAX      BgpPeerOrfCapabilityEntry
    MAX-ACCESS  not-accessible
    STATUS      current
    DESCRIPTION "Entry containing peer specific information about support for
                 an ORF defined by <AFI, SAFI, ORF Type>."
    INDEX { bgpRmEntIndex,
            bgpPeerLocalAddrType,
            bgpPeerLocalAddr,
            bgpPeerLocalPort,
            bgpPeerRemoteAddrType,
            bgpPeerRemoteAddr,
            bgpPeerRemotePort,
            bgpPeerLocalAddrScopeId,
            bgpPeerOrfCapabilityAfi,
            bgpPeerOrfCapabilitySafi,
            bgpPeerOrfCapabilityOrfType }
    ::= { bgpPeerOrfCapabilityTable 1 }

  BgpPeerOrfCapabilityEntry ::= SEQUENCE {
      bgpPeerOrfCapabilityAfi               BgpAfi,
      bgpPeerOrfCapabilitySafi              BgpSafi,
      bgpPeerOrfCapabilityOrfType           BgpOrfType,
      bgpPeerOrfCapabilityAdminStatus       BgpAdminStatus,
      bgpPeerOrfCapabilitySendReceive       BgpOrfSendReceive
      }

  bgpPeerOrfCapabilityAfi OBJECT-TYPE
    SYNTAX      BgpAfi
    MAX-ACCESS  not-accessible
    STATUS      current
    DESCRIPTION "Specifies the address family with which this ORF is
                 associated."
    ::= { bgpPeerOrfCapabilityEntry 8 }

  bgpPeerOrfCapabilitySafi OBJECT-TYPE
    SYNTAX      BgpSafi
    MAX-ACCESS  not-accessible
    STATUS      current
    DESCRIPTION "Specifies the Subsequent Address Family Indentifier with
                 which this ORF is associated."
    ::= { bgpPeerOrfCapabilityEntry 9 }

  bgpPeerOrfCapabilityOrfType OBJECT-TYPE
    SYNTAX      BgpOrfType
    MAX-ACCESS  not-accessible
    STATUS      current
    DESCRIPTION "Indicates the type of this ORF."
    ::= { bgpPeerOrfCapabilityEntry 10 }

  bgpPeerOrfCapabilityAdminStatus OBJECT-TYPE
    SYNTAX      BgpAdminStatus
    MAX-ACCESS  read-create
    STATUS      current
    DESCRIPTION "The administrative status for this ORF entry."
    DEFVAL { adminStatusUp }
    ::= { bgpPeerOrfCapabilityEntry 11 }

  bgpPeerOrfCapabilitySendReceive OBJECT-TYPE
    SYNTAX      BgpOrfSendReceive
    MAX-ACCESS  read-create
    STATUS      current
    DESCRIPTION "Indicates whether the sender is (a) willing to receive ORF
                 entries from its peer, (b) would like to send ORF entries
                 to its peer, or (c) both.  This field will be logical-ANDed
                 with the bgpOrfCapabilitySendReceive field of the
                 corresponding entry in the bgpOrfCapabilityTable if one
                 exists.  Only if a corresponding entry exists AND
                 both entries indicate support will this be advertised to the
                 peer."
    DEFVAL { both }
    ::= { bgpPeerOrfCapabilityEntry 12 }

-------------------------------------------------------------------------------

  --
  -- Peer group <AFI, SAFI> configuration table.
  --

  bgpPeergrAfiSafiTable OBJECT-TYPE
  -- FAMILY-SHORT-NAME BGP_AFI
    SYNTAX      SEQUENCE OF BgpPeergrAfiSafiEntry
    MAX-ACCESS  not-accessible
    STATUS      current
    DESCRIPTION "Peer group <AFI, SAFI> configuration table.

                 This table allows a user to configure peer group
                 characteristics on a per AFI/SAFI basis.

                 Rows in this table cannot be created or destroyed manually.
                 A table entry for each supported address family is created
                 automatically when an entry in the bgpPeergrTable is created.
                 The entries are destroyed when the bgpPeergrTable entry
                 is destroyed."
    ::= { bgpPib 12 }

  bgpPeergrAfiSafiEntry OBJECT-TYPE
    SYNTAX      BgpPeergrAfiSafiEntry
    MAX-ACCESS  not-accessible
    STATUS      current
    DESCRIPTION "Peer group <AFI, SAFI> configuration table entry."
    INDEX { bgpRmEntIndex,
            bgpPeergrIndex,
            bgpPeergrAfiSafiAfi,
            bgpPeergrAfiSafiSafi }
    ::= { bgpPeergrAfiSafiTable 1 }

  BgpPeergrAfiSafiEntry ::= SEQUENCE {
      bgpPeergrAfiSafiAfi                BgpAfi,
      bgpPeergrAfiSafiSafi               BgpSafi,
      bgpPeergrAfiSafiAllowLocalAs       Unsigned32,
      bgpPeergrAfiSafiDisSndLpDetect     TruthValue,
      bgpPeergrAfiSafiNxtHopSlf          TruthValue,
      bgpPeergrAfiSafiOrigDefault        TruthValue,
      bgpPeergrAfiSafiOrigDefaultRtMap   Unsigned32,
      bgpPeergrAfiSafiSoftResetStore     TruthValue
      }

  bgpPeergrAfiSafiAfi OBJECT-TYPE
    SYNTAX      BgpAfi
    MAX-ACCESS  not-accessible
    STATUS      current
    DESCRIPTION "The AFI index into the peer group <AFI, SAFI> table."
    ::= { bgpPeergrAfiSafiEntry 3 }

  bgpPeergrAfiSafiSafi OBJECT-TYPE
    SYNTAX      BgpSafi
    MAX-ACCESS  not-accessible
    STATUS      current
    DESCRIPTION "The SAFI index into the peer group <AFI, SAFI> table."
    ::= { bgpPeergrAfiSafiEntry 4 }

  bgpPeergrAfiSafiAllowLocalAs OBJECT-TYPE
    SYNTAX      Unsigned32 (0..255)
    MAX-ACCESS  read-create
    STATUS      current
    DESCRIPTION "The number of instances of the local AS identifier that may
                 be contained in the route's AS-Path without rejecting the
                 route.

                 The AS-Path attribute of a BGP route contains the identifiers
                 of the Autonomous Systems traversed by the route.  When
                 a route is received with an AS-Path containing the local
                 AS identifier, it normally indicates a routing loop, and
                 the default behavior is to reject the route.  This object
                 allows this behavior to be over-ridden.

                 This is useful, for example, for VPN routes, where routes
                 from one CE router are advertised to other CE routers sites
                 through a provider's BGP network.  Two CE routers in
                 the same AS can enable this feature to prevent routes from
                 the other CE from being discarded.

                 Changing the value of this object triggers BGP to refresh its
                 routes from each active peer in the peer group."
    DEFVAL { 0 }
    ::= { bgpPeergrAfiSafiEntry 5 }

  bgpPeergrAfiSafiDisSndLpDetect OBJECT-TYPE
    SYNTAX      TruthValue
    MAX-ACCESS  read-create
    STATUS      current
    DESCRIPTION "Gives finer control of the sender-side loop detection
                 configuration provided by bgpPeergrDisableSenderLoopDetect.

                 By default, BGP performs sender side loop detection.  That
                 is, it will not advertise a route to a peer if the AS-Path
                 of the route already contains the peer's AS number.  A
                 peer would typically discard such routes, so this is
                 normally a useful optimization.

                 However, the peer may be configured to accept such routes
                 (see bgpPeergrAfiSafiAllowLocalAs).  In this case it is
                 necessary to disable sender-side loop detection.

                 When bgpPeergrDisableSenderLoopDetect is 'true', BGP
                 disables sender-side loop detection for those address
                 families for which bgpPeergrAfiSafiDisSndLpDetect is
                 'true'.

                 When bgpPeergrDisableSenderLoopDetect is 'false',
                 sender-side loop detection is not disable for any address
                 families.

                 If the value of this object is changed while a peer in the
                 peer group is active, BGP will check for any routes that need
                 to be advertised or withdrawn as a result of the change."
    DEFVAL { true }
    ::= { bgpPeergrAfiSafiEntry 6 }

  bgpPeergrAfiSafiNxtHopSlf OBJECT-TYPE
    SYNTAX      TruthValue
    MAX-ACCESS  read-create
    STATUS      current
    DESCRIPTION "Gives finer control of the next-hop-self configuration
                 provided by bgpPeergrNxtHopSlf.

                 When bgpPeergrNxtHopSlf is 'false', BGP does not perform
                 next-hop-self for any address family.

                 When bgpPeergrNxtHopSlf is 'true', BGP performs next-hop-self
                 for those address families for which bgpPeergrAfiSafiNxtHopSlf
                 is 'true'.

                 If the value of this object is changed while a peer session
                 is active, BGP will check for any routes that need to be
                 advertised or withdrawn as a result of the change."
    DEFVAL { true }
    ::= { bgpPeergrAfiSafiEntry 7 }

  bgpPeergrAfiSafiOrigDefault OBJECT-TYPE
    SYNTAX      TruthValue
    MAX-ACCESS  read-create
    STATUS      current
    DESCRIPTION "Indicates whether BGP should originate a default route to
                 the peer group for this address family.

                 BGP cannot originate default VPN routes and so
                 bgpPeergrAfiSafiOrigDefault cannot be set to 'true' if
                 bgpPeerAfiSafiSafi is 'mplsBgpVpn'.

                 This is because there is no single default route for a VPN
                 address family - there may be one for each VRF.  If a
                 default VPN route is required, it should should be
                 redistributed from the corresponding VRF.  This ensures
                 that the default VPN route is advertised by BGP along with
                 the associated label, route distinguisher and route
                 targets.

                 Similarly, BGP does not support the allocation of a label
                 for a default route, and so bgpPeergrAfiSafiOrigDefault
                 cannot be set to 'true' if bgpPeergrAfiSafiSafi is
                 'labeled'.

                 Default routes are meaningless for L2VPN auto-discovery
                 and signaling, so bgpPeergrAfiSafiOrigDefault cannot be
                 set to 'true' if bgpPeergrAfiSafiAfi is 'l2vpn'.

                 The origination of default routes may optionally be
                 conditional based on policy.  If this is required, then
                 set bgpPeergrAfiSafiOrigDefaultRtMap to specify a route
                 map.

                 If no route map is specified
                 (bgpPeergrAfiSafiOrigDefaultRtMap is zero), then default
                 route origination is based solely on the setting of
                 bgpPeergrAfiSafiOrigDefault."
    DEFVAL { false }
    ::= { bgpPeergrAfiSafiEntry 8 }

  bgpPeergrAfiSafiOrigDefaultRtMap OBJECT-TYPE
    SYNTAX      Unsigned32
    MAX-ACCESS  read-create
    STATUS      current
    DESCRIPTION "Configured policy for origination of default routes.

                 The value of bgpPeergrAfiSafiOrigDefaultRtMap is only examined
                 if bgpPeergrAfiSafiOrigDefault is 'true'.

                 It identifies a route map consisting of all rows in the
                 bgpRouteMapTable with bgpRouteMapIndex set to
                 bgpPeergrAfiSafiOrigDefaultRtMap.

                 The route map has two purposes.

                - The match clauses are used for conditional advertisement
                  of the default route.  A default route is only originated
                  for an address family if bgpPeergrAfiSafiOrigDefault
                  is 'true' and if there is at least one route in the loc-RIB
                  matching the route map.

                - The set clauses of the route map determine the attributes
                  of the originated default route.

                 Note that route maps may consist of multiple bgpRouteMapTable
                 entries.  These bgpRouteMapTable entries can be configured
                 to match a specific address family.  Any such bgpRouteMapTable
                 entry that does not match the address family for this
                 bgpPeergrAfiSafiTable entry is ignored.

                 These route maps should be configured as follows.

                - To restrict a route map to a particular AFI/SAFI, specify
                  bgpRouteMapMaAfi and bgpRouteMapMaSafi.

                - Each route map should specify an IP prefix list to match
                  on.  This is not mandated by DC-BGP, but other types of
                  matches may have a performance impact.

                - Each IP prefix match is assumed to be an exact match.  In
                  other words, DC-BGP treats each bgpIpPreTable entry as
                  having bgpIpPreLe = bgpIpPreLen, and bgpIpPreGe = 0."
    DEFVAL { 0 }
    ::= { bgpPeergrAfiSafiEntry 9 }

  bgpPeergrAfiSafiSoftResetStore OBJECT-TYPE
    SYNTAX      TruthValue
    MAX-ACCESS  read-create
    STATUS      current
    DESCRIPTION "Gives finer control of the soft reset configuration provided
                 by bgpPeergrSoftResetWithStoredInfo.

                 When bgpPeergrSoftResetWithStoredInfo is 'false', BGP does not
                 perform soft reset for any address family.

                 When bgpPeergrSoftResetWithStoredInfo is 'true', BGP performs
                 soft reset for those address families for which
                 bgpPeergrAfiSafiSoftResetStore is 'true'.

                 Any update to this object will take effect on each peer
                 the next time that the peer session reactivates."
    DEFVAL { true }
    ::= { bgpPeergrAfiSafiEntry 10 }

-------------------------------------------------------------------------------

  --
  -- BGP NLRI Prefix Data
  --
  -- This table contains per route information including routes, attributes
  -- and flap statistics if the route is being damped.  It is ordered by route
  -- prefix.
  --

  bgpNlriPrefixTable OBJECT-TYPE
  -- FAMILY-SHORT-NAME BGP_NLR_PRFX
    SYNTAX      SEQUENCE OF BgpNlriPrefixEntry
    MAX-ACCESS  not-accessible
    STATUS      current
    DESCRIPTION "This table contains information about paths to destination
                 networks received from all BGP4 peers.  It provides the same
                 information as the bgpNlriTable, but is ordered by route
                 prefix.

                 This table must contain an identical set of fields to the
                 bgpNlriTable.  All fields must be in the same order in this
                 table and the bgpNlriTable."
    ::= { bgpRib 5 }

  bgpNlriPrefixEntry OBJECT-TYPE
    SYNTAX      BgpNlriPrefixEntry
    MAX-ACCESS  not-accessible
    STATUS      current
    DESCRIPTION "Information about a path to a network."
    INDEX { bgpRmEntIndex,
            bgpNlriPrefixAfi,
            bgpNlriPrefixSafi,
            bgpNlriPrefixPrfx,
            bgpNlriPrefixPrfxLen,
            bgpNlriPrefixPeerOrAfm,
            bgpNlriPrefixPeerAfmIndex}
    ::= { bgpNlriPrefixTable 1 }

  BgpNlriPrefixEntry ::= SEQUENCE {
      bgpNlriPrefixPeerOrAfm           BgpPeerOrAfm,
      bgpNlriPrefixPeerAfmIndex        Unsigned32,
      bgpNlriPrefixAfi                 BgpAfi,
      bgpNlriPrefixSafi                BgpSafi,
      bgpNlriPrefixPrfx                InetAddress,
      bgpNlriPrefixPrfxLen             InetAddressPrefixLength,
      bgpNlriPrefixBest                TruthValue,
      bgpNlriPrefixAsSize              BgpAsSize,
      bgpNlriPrefixASPathStr           OCTET STRING,
      bgpNlriPrefixPathAttrOrigin      BgpOriginCode,
      bgpNlriPrefixPathAttrNextHop     InetAddress,
      bgpNlriPrefixPathAttrMultExtDisc Unsigned32,
      bgpNlriPrefixPathAttrLocalPref   Unsigned32,
      bgpNlriPrefixPathAttrAtomicAgg   BgpPathAttrAtomicAggPresence,
      bgpNlriPrefixPathAttrAggAS       BgpAutonomousSystemNumber,
      bgpNlriPrefixPathAttrAggAddr     BgpIdentifier,
      bgpNlriPrefixPathAttrCalcLclPref Unsigned32,
      bgpNlriPrefixPathAttrOrigId      BgpIdentifier,
      bgpNlriPrefixPathAttrWeight      Unsigned32,
      bgpNlriPrefixFlapStatsConfig     Unsigned32,
      bgpNlriPrefixFlapStatsPenalty    Unsigned32,
      bgpNlriPrefixFlapStatsFlapcnt    Unsigned32,
      bgpNlriPrefixFlapStatsSupprsd    TruthValue,
      bgpNlriPrefixFlapStatsTimeleft   Unsigned32,
      bgpNlriPrefixFlapStatsCleardamp  TruthValue,
      bgpNlriPrefixFlapStatsClearstat  TruthValue,
      bgpNlriPrefixEcmp                TruthValue,
      bgpNlriPrefixPathAttrAsPathLimAs BgpAutonomousSystemNumber,
      bgpNlriPrefixPthAttAsPthLimUpper Unsigned32,
      bgpNlriPrefixIsActive            BgpNlriIsActiveFlag,
      bgpNlriPrefixUserData            OCTET STRING,
      bgpNlriPrefixStale               TruthValue,
      bgpNlriPrefixFlapStartTime       TimeStamp,
      bgpNlriPrefixLinkLocalNextHop    InetAddress
      }

  bgpNlriPrefixPeerOrAfm OBJECT-TYPE
    SYNTAX      BgpPeerOrAfm
    MAX-ACCESS  not-accessible
    STATUS      current
    DESCRIPTION "Whether this route was learned from a BGP peer or an AFM."
    ::= { bgpNlriPrefixEntry 2 }

  bgpNlriPrefixPeerAfmIndex OBJECT-TYPE
    SYNTAX      Unsigned32
    MAX-ACCESS  not-accessible
    STATUS      current
    DESCRIPTION "The index of either the BGP peer or AFM this route was
                 learned from.  If bgpNlriPrefixPeerOrAfm is peer, this field
                 is equivalent to a bgpPeerIndex.  If bgpNlriPrefixPeerOrAfm
                 is afm, this field is equivalent to a bgpRmAfmJoin."
    ::= { bgpNlriPrefixEntry 3 }

  bgpNlriPrefixAfi OBJECT-TYPE
    SYNTAX      BgpAfi
    MAX-ACCESS  not-accessible
    STATUS      current
    DESCRIPTION "The address family of the prefix for this NLRI."
    ::= { bgpNlriPrefixEntry 4 }

  bgpNlriPrefixSafi OBJECT-TYPE
    SYNTAX      BgpSafi
    MAX-ACCESS  not-accessible
    STATUS      current
    DESCRIPTION "The subsequent address family of the prefix for this NLRI."
    ::= { bgpNlriPrefixEntry 5 }

  bgpNlriPrefixPrfx OBJECT-TYPE
    SYNTAX      InetAddress (SIZE(0..32))
    MAX-ACCESS  not-accessible
    STATUS      current
    DESCRIPTION "An address prefix in the Network Layer Reachability
                 Information field.

                 The prefix length is specified by bgpNlriPrefixPrfxLen.  Any
                 bits beyond the length specified by bgpNlriPrefixPrfxLen are
                 zeroed.

                 This field contains the full line format BGP NLRI omitting
                 any NLRI length field.

                 For SAFI 128 the NLRI includes the MPLS label and Route
                 Distinguisher as well as the IPv4 or IPv6 address prefix."
    ::= { bgpNlriPrefixEntry 6 }

  bgpNlriPrefixPrfxLen OBJECT-TYPE
    SYNTAX      InetAddressPrefixLength
    MAX-ACCESS  not-accessible
    STATUS      current
    DESCRIPTION "Length in bits of the IP address prefix in the Network Layer
                 Reachability Information field."
    ::= { bgpNlriPrefixEntry 7 }

  bgpNlriPrefixBest OBJECT-TYPE
    SYNTAX      TruthValue
    MAX-ACCESS  read-only
    STATUS      current
    DESCRIPTION "An indication of whether or not this route was chosen as the
                 best BGP4 route."
    ::= { bgpNlriPrefixEntry 8 }

  bgpNlriPrefixAsSize OBJECT-TYPE
    SYNTAX      BgpAsSize
    MAX-ACCESS  read-only
    STATUS      current
    DESCRIPTION "Whether the bgpNlriPrefixASPathStr field contains two or
                 four byte AS numbers."
    ::= { bgpNlriPrefixEntry 9 }

  bgpNlriPrefixASPathStr OBJECT-TYPE
    SYNTAX      OCTET STRING  (SIZE (0..128))
    MAX-ACCESS  read-only
    STATUS      current
    DESCRIPTION "This is a string depicting the autonomous system path to this
                 network which was received from the peer which advertised it.
                 If bgpRmEntAsSize is four-octet and the peer does not support
                 four octet AS numbers this string represents the AS_PATH
                 formed by combining the AS_PATH and AS4_PATH attributes as
                 detailed in RFC 4893.  Two-octet AS numbers appear as
                 four-octet numbers by adding two bytes of zero padding.  The
                 format of the string is simply the AS_PATH attribute.  It can
                 be converted to a more readable format by the management
                 agent."
    ::= { bgpNlriPrefixEntry 10 }

  bgpNlriPrefixPathAttrOrigin OBJECT-TYPE
    SYNTAX      BgpOriginCode
    MAX-ACCESS  read-only
    STATUS      current
    DESCRIPTION "The ultimate origin of the path information."
    ::= { bgpNlriPrefixEntry 11 }

  bgpNlriPrefixPathAttrNextHop OBJECT-TYPE
    SYNTAX      InetAddress (SIZE(0..32))
    MAX-ACCESS  read-only
    STATUS      current
    DESCRIPTION "The address of the border router that should be used to access
                 the destination network.  This address is the nexthop address
                 received in the UPDATE packet.  The address family of this
                 object will be the same as that of the prefix in this row.

                 Note that for RFC 2545 style double nexthops, this object
                 will always contain the global scope nexthop.
                 bgpNlriPrefixLinkLocalNextHop will contain the linklocal
                 scope nexthop, if it is present."
    ::= { bgpNlriPrefixEntry 12 }

  bgpNlriPrefixPathAttrMultExtDisc OBJECT-TYPE
    SYNTAX      Unsigned32
    MAX-ACCESS  read-only
    STATUS      current
    DESCRIPTION "This metric is used to discriminate between multiple exit
                 points to an adjacent autonomous system."
    ::= { bgpNlriPrefixEntry 13 }

  bgpNlriPrefixPathAttrLocalPref OBJECT-TYPE
    SYNTAX      Unsigned32
    MAX-ACCESS  read-only
    STATUS      current
    DESCRIPTION "The originating BGP4 speaker's degree of preference for an
                 advertised route."
    ::= { bgpNlriPrefixEntry 14 }

  bgpNlriPrefixPathAttrAtomicAgg OBJECT-TYPE
    SYNTAX      BgpPathAttrAtomicAggPresence
    MAX-ACCESS  read-only
    STATUS      current
    DESCRIPTION "When this object is set to AMB_BGP_ATOMIC_AGGR_PRESENT, the
                 ATOMIC_AGGREGATE Path Attribute is present and indicates that
                 the NLRI MUST NOT be made more specific."
    ::= { bgpNlriPrefixEntry 15 }

  bgpNlriPrefixPathAttrAggAS OBJECT-TYPE
    SYNTAX      BgpAutonomousSystemNumber
    MAX-ACCESS  read-only
    STATUS      current
    DESCRIPTION "The AS number of the last BGP4 speaker that performed route
                 aggregation."
    ::= { bgpNlriPrefixEntry 16 }

  bgpNlriPrefixPathAttrAggAddr OBJECT-TYPE
    SYNTAX      BgpIdentifier
    MAX-ACCESS  read-only
    STATUS      current
    DESCRIPTION "The IP address of the last BGP4 speaker that performed route
                 aggregation.  A value of 0000 indicates the absence of this
                 attribute.  Note propagation of AS of zero is illegal in
                 the Internet."
    ::= { bgpNlriPrefixEntry 17 }

  bgpNlriPrefixPathAttrCalcLclPref OBJECT-TYPE
    SYNTAX      Unsigned32
    MAX-ACCESS  read-only
    STATUS      current
    DESCRIPTION "The degree of preference calculated by the receiving BGP4
                 speaker for an advertised route."
    ::= { bgpNlriPrefixEntry 18 }

  bgpNlriPrefixPathAttrOrigId OBJECT-TYPE
    SYNTAX      BgpIdentifier
    MAX-ACCESS  read-only
    STATUS      current
    DESCRIPTION "The Originator-ID identifying the router that initially
                 advertised this destination to a Route Reflector.  A
                 value of 0.0.0.0 indicates the absence of this attribute."
    ::= { bgpNlriPrefixEntry 19 }

  bgpNlriPrefixPathAttrWeight OBJECT-TYPE
    SYNTAX      Unsigned32
    MAX-ACCESS  read-only
    STATUS      current
    DESCRIPTION "The local degree of preference assigned to this route."
    ::= { bgpNlriPrefixEntry 20 }

  bgpNlriPrefixFlapStatsConfig OBJECT-TYPE
    SYNTAX      Unsigned32
    MAX-ACCESS  read-only
    STATUS      current
    DESCRIPTION "The index of the bgpFlapConfigTable containing the
                 configuration settings being applied to this route for
                 damping."
    ::= { bgpNlriPrefixEntry 21 }

  bgpNlriPrefixFlapStatsPenalty OBJECT-TYPE
    SYNTAX       Unsigned32
    MAX-ACCESS   read-only
    STATUS       current
    DESCRIPTION "The current penalty value of this route.  If it is greater
                 than the cutoff threshold the route is suppressed."
    ::= { bgpNlriPrefixEntry 22 }

  bgpNlriPrefixFlapStatsFlapcnt OBJECT-TYPE
    SYNTAX      Unsigned32
    MAX-ACCESS  read-only
    STATUS      current
    DESCRIPTION "The number of times this route has flapped since statistics
                 were last cleared."
    ::= { bgpNlriPrefixEntry 23 }

  bgpNlriPrefixFlapStatsSupprsd OBJECT-TYPE
    SYNTAX      TruthValue
    MAX-ACCESS  read-only
    STATUS      current
    DESCRIPTION "Whether or not this route is suppressed."
    ::= { bgpNlriPrefixEntry 24 }

  bgpNlriPrefixFlapStatsTimeleft OBJECT-TYPE
    SYNTAX      Unsigned32
    UNITS       "seconds"
    MAX-ACCESS  read-only
    STATUS      current
    DESCRIPTION "The time left until this route is no longer suppressed.  Only
                 valid if the route is suppressed."
    ::= { bgpNlriPrefixEntry 25 }

  bgpNlriPrefixFlapStatsCleardamp OBJECT-TYPE
    SYNTAX      TruthValue
    MAX-ACCESS  read-only
    STATUS      current
    DESCRIPTION "This field is present to ensure that fields in the
                 bgpNlriPrefixTable correspond to fields in the bgpNlriTable.
                 It has no meaning when read."
    DEFVAL { false }
    ::= { bgpNlriPrefixEntry 26 }

  bgpNlriPrefixFlapStatsClearstat OBJECT-TYPE
    SYNTAX      TruthValue
    MAX-ACCESS  read-only
    STATUS      current
    DESCRIPTION "This field is present to ensure that fields in the
                 bgpNlriPrefixTable correspond to fields in the bgpNlriTable.
                 It has no meaning when read."
    DEFVAL { false }
    ::= { bgpNlriPrefixEntry 27 }

  bgpNlriPrefixEcmp   OBJECT-TYPE
    SYNTAX      TruthValue
    MAX-ACCESS  read-only
    STATUS      current
    DESCRIPTION "Whether or not this route was installed into the
                 Forwarding Table as an ECMP route (it may or may not be
                 the best BGP4 route advertised to BGP peers)."
    ::= { bgpNlriPrefixEntry 28 }

  bgpNlriPrefixPathAttrAsPathLimAs OBJECT-TYPE
    SYNTAX      BgpAutonomousSystemNumber
    MAX-ACCESS  read-only
    STATUS      current
    DESCRIPTION "The AS number of the speaker that attached the AS_PATHLIMIT
                 attribute.  A value of 0 indicates the absence of this
                 attribute.  Note that propagation of AS of zero is illegal in
                 the Internet."
    ::= { bgpNlriPrefixEntry 29 }

  bgpNlriPrefixPthAttAsPthLimUpper OBJECT-TYPE
    SYNTAX      Unsigned32 (0..255)
    MAX-ACCESS  read-only
    STATUS      current
    DESCRIPTION "The upper bound on the number of ASes in the AS_PATH
                 associated with this route before the route will be filtered.
                 Only valid if bgpPathAttrAsPathLimAs is non-zero."
    ::= { bgpNlriPrefixEntry 30 }

  bgpNlriPrefixIsActive OBJECT-TYPE
    SYNTAX      BgpNlriIsActiveFlag
    MAX-ACCESS  read-only
    STATUS      current
    DESCRIPTION "An indication of whether or not this route is installed in
                 the forwarding table.

                 If bgpRmAfiSafiAdvertiseInactive is set to 'false', then
                 this is set to

                 - 'active' if the route is installed in the forwarding
                   table, or is a route redistributed from another routing
                   protocol instance

                 - 'inactive' otherwise.

                 If bgpRmAfiSafiAdvertiseInactive is set to 'true', BGP does
                 not track active routes.  In this case, bgpNlriIsActive is
                 set to 'notTracked'."
    ::= { bgpNlriPrefixEntry 31 }

  bgpNlriPrefixUserData OBJECT-TYPE
    SYNTAX      OCTET STRING(SIZE (4))
    MAX-ACCESS  read-only
    STATUS      current
    DESCRIPTION "User data for this BGP NLRI prefix entry."
    ::= { bgpNlriPrefixEntry 32 }

  bgpNlriPrefixStale OBJECT-TYPE
    SYNTAX      TruthValue
    MAX-ACCESS  read-only
    STATUS      current
    DESCRIPTION "Whether or not this route was last sent by the peer before
                 BGP detected that the peer was restarting.  If the route is
                 not re-advertised by the peer before the restart completes,
                 BGP will remove the route from its database.  This flag is
                 set to 'false' if the peer is not restarting, or if the
                 route has been advertised by the peer since the restart."
    ::= { bgpNlriPrefixEntry 33 }

  bgpNlriPrefixFlapStartTime OBJECT-TYPE
    SYNTAX      TimeStamp
    MAX-ACCESS  read-only
    STATUS      current
    DESCRIPTION "The value of sysUpTime when this route flapped.  If RIB
                 Manager is not tracking a penalty for this route, this field
                 is set to zero."
    ::= { bgpNlriPrefixEntry 34 }

  bgpNlriPrefixLinkLocalNextHop OBJECT-TYPE
    SYNTAX      InetAddress (SIZE(0..32))
    MAX-ACCESS  read-only
    STATUS      current
    DESCRIPTION "The IPv6 link-local address of the border router that
                 should be used to access the destination network.  This
                 object is only valid for a prefix with a received RFC 2545
                 style double nexthop."
    ::= { bgpNlriPrefixEntry 35 }

-------------------------------------------------------------------------------

-- Tables for HAF information

  bgpHaf OBJECT IDENTIFIER ::= { bgpMib 6 }

--
-- RIB Manager AFM Join Table.
--
-- This table records the joins for which the RIB Manager is master.
-- RM currently has two types of MJ to RTM and VPN Manager.  There can be
-- multiple joins to either of these, which are initiated by creating a new row
-- in this table.
--

  bgpRmAfmJoinTable OBJECT-TYPE
  -- FAMILY-SHORT-NAME BGP_AFM
    SYNTAX      SEQUENCE OF BgpRmAfmJoinEntry
    MAX-ACCESS  not-accessible
    STATUS      current
    DESCRIPTION "Each entry in this table represents a join to an AFM for which
                 a RIB Manager entity is master."
    ::= { bgpHaf 1 }

  bgpRmAfmJoinEntry OBJECT-TYPE
    SYNTAX      BgpRmAfmJoinEntry
    MAX-ACCESS  not-accessible
    STATUS      current
    DESCRIPTION "Each entry represents a join to an AFM for which a RIB Manager
                 entity is master."
    INDEX { bgpRmEntIndex,
            bgpRmAfmJoin }
    ::= { bgpRmAfmJoinTable 1 }

  BgpRmAfmJoinEntry ::= SEQUENCE {
      bgpRmAfmJoin                  Unsigned32,
      bgpRmAfmRowStatus             RowStatus,
      bgpRmAfmAdminStatus           BgpAdminStatus,
      bgpRmAfmOperStatus            BgpOperStatus,
      bgpRmAfmPartnerIndex          Unsigned32,
      bgpRmAfmAfi                   BgpAfi,
      bgpRmAfmSafi                  BgpSafi,
      bgpRmAfmJoinStatus            BgpMjStatus,
      bgpRmAfmRestartTime           Unsigned32
    }

  bgpRmAfmJoin OBJECT-TYPE
    SYNTAX      Unsigned32
    MAX-ACCESS  not-accessible
    STATUS      current
    DESCRIPTION "Identifies a join for which a RIB Manager entity is master."
    ::= { bgpRmAfmJoinEntry 2 }

  bgpRmAfmRowStatus OBJECT-TYPE
    SYNTAX      RowStatus
    MAX-ACCESS  read-create
    STATUS      current
    DESCRIPTION "The row status for this table entry, used to create and
                 destroy table entries."
    ::= { bgpRmAfmJoinEntry 3 }

  bgpRmAfmAdminStatus OBJECT-TYPE
    SYNTAX      BgpAdminStatus
    MAX-ACCESS  read-create
    STATUS      current
    DESCRIPTION "The administrative status of this table entry, used to
                 activate and deactivate the join."
    DEFVAL      { adminStatusDown }
    ::= { bgpRmAfmJoinEntry 4 }

  bgpRmAfmOperStatus OBJECT-TYPE
    SYNTAX      BgpOperStatus
    MAX-ACCESS  read-only
    STATUS      current
    DESCRIPTION "The current operational status of this join."
    ::= { bgpRmAfmJoinEntry 5 }

  bgpRmAfmPartnerIndex OBJECT-TYPE
    SYNTAX      Unsigned32
    MAX-ACCESS  read-create
    STATUS      current
    DESCRIPTION "Index that identifies the slave entity for this join."
    DEFVAL      { 0 }
    ::= { bgpRmAfmJoinEntry 6 }

  bgpRmAfmAfi OBJECT-TYPE
    SYNTAX      BgpAfi
    MAX-ACCESS  read-create
    STATUS      current
    DESCRIPTION "Address Family Identifier for this join.  This field can only
                 be changed when the Admin Status is down."
    DEFVAL      { ipv4 }
    ::= { bgpRmAfmJoinEntry 7 }

  bgpRmAfmSafi OBJECT-TYPE
    SYNTAX      BgpSafi
    MAX-ACCESS  read-create
    STATUS      current
    DESCRIPTION "Subsequent Address Family Identifier for this join.  This
                 field can only be changed when the Admin Status is down."
    DEFVAL      { unicast }
    ::= { bgpRmAfmJoinEntry 8 }

  bgpRmAfmJoinStatus OBJECT-TYPE
    SYNTAX      BgpMjStatus
    MAX-ACCESS  read-only
    STATUS      current
    DESCRIPTION "The status of the master join."
    ::= { bgpRmAfmJoinEntry 9 }

  bgpRmAfmRestartTime OBJECT-TYPE
    SYNTAX      Unsigned32 (0..3600)
    UNITS       "seconds"
    MAX-ACCESS  read-create
    STATUS      current
    DESCRIPTION "This is the maximum time that DC-BGP will retain routes
                 from this AFM following failure of this join.  DC-BGP
                 will delete all retained stale routes from this AFM once
                 this time has passed.  A value of 0 indicates that routes from
                 this AFM will be discarded as soon as the join fails."
    DEFVAL { 60 }
    ::= { bgpRmAfmJoinEntry 10 }

-------------------------------------------------------------------------------
--
-- RIB Manager Neighbor Manager Join Table.
--
-- This is a read-only table.  It contains information on joins to Neighbor
-- Managers for which RIB Manager entities are acting as slaves.  Each row in
-- this table represents one slave join in a particular RIB Manager entity.
--

  bgpRmNmTable OBJECT-TYPE
  -- FAMILY-SHORT-NAME BGP_NMJ
    SYNTAX      SEQUENCE OF BgpRmNmEntry
    MAX-ACCESS  not-accessible
    STATUS      current
    DESCRIPTION "This table contains information on slave joins to Neighbor
                 Manager entities.  Each row in this table represents one
                 slave join in a particular RIB Manager entity."
    ::= { bgpHaf 2 }

  bgpRmNmEntry OBJECT-TYPE
    SYNTAX      BgpRmNmEntry
    MAX-ACCESS  not-accessible
    STATUS      current
    DESCRIPTION "Represents a join to a Neighbor Manager for which the RIB
                 Manager is slave."
    INDEX { bgpRmEntIndex,
            bgpRmNmMasterIndex}
    ::= { bgpRmNmTable 1 }

  BgpRmNmEntry ::= SEQUENCE {
      bgpRmNmMasterIndex            Unsigned32,
      bgpRmNmJoinStatus             BgpSjStatus
    }

  bgpRmNmMasterIndex OBJECT-TYPE
    SYNTAX      Unsigned32
    MAX-ACCESS  not-accessible
    STATUS      current
    DESCRIPTION "Index of the master entity.  This is the index received in
                 the join registration info sent from the master to the slave
                 on the join registration IPS."
    ::= { bgpRmNmEntry 2 }

  bgpRmNmJoinStatus OBJECT-TYPE
    SYNTAX      BgpSjStatus
    MAX-ACCESS  read-only
    STATUS      current
    DESCRIPTION "The status of the slave join."
    ::= { bgpRmNmEntry 3 }

-------------------------------------------------------------------------------

--
-- Neighbor Manager Master Join Table.
--
-- This is a read-only table which records the joins for which the Neighbor
-- Manager is master.  Each NM will have exactly two joins, one to an instance
-- of the RIB Manager, and one to the IP Sockets Stub.
--

  bgpNmMjTable OBJECT-TYPE
  -- FAMILY-SHORT-NAME BGP_NMJ
    SYNTAX      SEQUENCE OF BgpNmMjEntry
    MAX-ACCESS  not-accessible
    STATUS      current
    DESCRIPTION "Each entry in this table represents a join for which a
                 Neighbor Manager entity is master.  This table always
                 contains exactly three rows, one each for the joins from NM
                 to RM, the IP Sockets Stub and the BFD stub.

                 If NM is configured not to join to the BFD stub
                 (bgpNmEntBfdEntityIndex is zero), then the row for the BFD
                 join is still present, with bgpNmMjJoinStatus set to
                 mjNotJoined."
    ::= { bgpHaf 3 }

  bgpNmMjEntry OBJECT-TYPE
    SYNTAX      BgpNmMjEntry
    MAX-ACCESS  not-accessible
    STATUS      current
    DESCRIPTION "Each entry represents a join for which a Neighbor Manager
                 entity is master."
    INDEX { bgpNmMjEntity,
            bgpNmMjJoin }
    ::= { bgpNmMjTable 1 }

  BgpNmMjEntry ::= SEQUENCE {
      bgpNmMjEntity                   Unsigned32,
      bgpNmMjJoin                     Unsigned32,
      bgpNmMjJoinPartner              BgpComponentId,
      bgpNmMjPartnerIndex             Unsigned32,
      bgpNmMjJoinStatus               BgpMjStatus
    }

  bgpNmMjEntity OBJECT-TYPE
    SYNTAX      Unsigned32
    MAX-ACCESS  not-accessible
    STATUS      current
    DESCRIPTION "Identifies a Neighbor Manager Entity."
    ::= { bgpNmMjEntry 1 }

  bgpNmMjJoin OBJECT-TYPE
    SYNTAX      Unsigned32 (1..3)
    MAX-ACCESS  not-accessible
    STATUS      current
    DESCRIPTION "Identifies a join for which a Neighbor Manager entity is
                 master."
    ::= { bgpNmMjEntry 2 }

  bgpNmMjJoinPartner OBJECT-TYPE
    SYNTAX      BgpComponentId
    MAX-ACCESS  read-only
    STATUS      current
    DESCRIPTION "Identifies the type of process acting as slave on this join."
    ::= { bgpNmMjEntry 3 }

  bgpNmMjPartnerIndex OBJECT-TYPE
    SYNTAX      Unsigned32
    MAX-ACCESS  read-only
    STATUS      current
    DESCRIPTION "The index assigned to this join by NM.  This index is used by
                 FTI-specific handling code within System Manager to identify
                 the entity index of a slave entity suitable to act as join
                 partner."
    ::= { bgpNmMjEntry 4 }

  bgpNmMjJoinStatus OBJECT-TYPE
    SYNTAX      BgpMjStatus
    MAX-ACCESS  read-only
    STATUS      current
    DESCRIPTION "The status of the master join."
    ::= { bgpNmMjEntry 5 }

-------------------------------------------------------------------------------
--
-- RIB Manager Active Route Interface Join Table.
--
-- This is a read-only table.  It contains information on Active Route
-- Interface joins for which RIB Manager entities are acting as slaves.  Each
-- row in this table represents one slave join in a particular RIB Manager
-- entity.
--

  bgpRmArinhJoinTable OBJECT-TYPE
  -- FAMILY-SHORT-NAME BGP_ARIJ
    SYNTAX      SEQUENCE OF BgpRmArinhJoinEntry
    MAX-ACCESS  not-accessible
    STATUS      current
    DESCRIPTION "This read-only table contains information on Active Route
                 Interface slave joins used for querying next hops.  Each row
                 in this table represents one slave join in a particular
                 RIB Manager entity."
    ::= { bgpHaf 4 }

  bgpRmArinhJoinEntry OBJECT-TYPE
    SYNTAX      BgpRmArinhJoinEntry
    MAX-ACCESS  not-accessible
    STATUS      current
    DESCRIPTION "Represents an ARI join for which the RIB Manager is slave."
    INDEX { bgpRmEntIndex,
            bgpRmArinhAfi,
            bgpRmArinhSafi}
    ::= { bgpRmArinhJoinTable 1 }

  BgpRmArinhJoinEntry ::= SEQUENCE {
      bgpRmArinhAfi                   BgpAfi,
      bgpRmArinhSafi                  BgpSafi,
      bgpRmArinhJoinStatus            BgpSjStatus,
      bgpRmArinhEntIndex              Unsigned32
    }

  bgpRmArinhAfi OBJECT-TYPE
    SYNTAX      BgpAfi
    MAX-ACCESS  not-accessible
    STATUS      current
    DESCRIPTION "Specifies the address family identifier with which this ARI
                 join is associated."
    ::= { bgpRmArinhJoinEntry 2 }

  bgpRmArinhSafi OBJECT-TYPE
    SYNTAX      BgpSafi
    MAX-ACCESS  not-accessible
    STATUS      current
    DESCRIPTION "Specifies the subsequent address family identifier with which
                 this ARI join is associated."
    ::= { bgpRmArinhJoinEntry 3 }

  bgpRmArinhJoinStatus OBJECT-TYPE
    SYNTAX      BgpSjStatus
    MAX-ACCESS  read-only
    STATUS      current
    DESCRIPTION "The status of the ARI slave join for querying next hops."
    ::= { bgpRmArinhJoinEntry 4 }

  bgpRmArinhEntIndex OBJECT-TYPE
    SYNTAX      Unsigned32
    MAX-ACCESS  read-only
    STATUS      current
    DESCRIPTION "Identifies the ARI provider entity."
    ::= { bgpRmArinhJoinEntry 5 }

-------------------------------------------------------------------------------

-- Tables for NM information

  bgpNm OBJECT IDENTIFIER ::= { bgpMib 7 }

--
-- Neighbor Manager Entity Table.
--
-- This is the top-level MIB for the DC-BGP Neighbor Manager.  It controls
-- creation and global configuration of the Neighbor Manager.
--
-- In distributed systems, the NM entity index in this table is mapped to the
-- physical network interface used by the IP Sockets stub by FTI-Specific
-- Handling code within System Manager.
--

  bgpNmEntTable OBJECT-TYPE
  -- FAMILY-SHORT-NAME BGP_NM
    SYNTAX      SEQUENCE OF BgpNmEntEntry
    MAX-ACCESS  not-accessible
    STATUS      current
    DESCRIPTION "Each entry in this table represents a Neighbor Manager
                 entity.  Fields in an entry cannot be changed while the admin
                 status is up."
    ::= { bgpNm 1 }

  bgpNmEntEntry OBJECT-TYPE
    SYNTAX      BgpNmEntEntry
    MAX-ACCESS  not-accessible
    STATUS      current
    DESCRIPTION "Each entry represents a Neighbor Manager entity."
    INDEX { bgpNmEntIndex }
    ::= { bgpNmEntTable 1 }

  BgpNmEntEntry ::= SEQUENCE {
      bgpNmEntIndex                   Unsigned32,
      bgpNmEntRowStatus               RowStatus,
      bgpNmEntAdminStatus             BgpAdminStatus,
      bgpNmEntOperStatus              BgpOperStatus,
      bgpNmEntRmIndex                 Unsigned32,
      bgpNmEntSckIndex                Unsigned32,
      bgpNmEntBfdEntityIndex          Unsigned32
    }

  bgpNmEntIndex OBJECT-TYPE
    SYNTAX      Unsigned32
    MAX-ACCESS  not-accessible
    STATUS      current
    DESCRIPTION "Identifies the Neighbor Manager entity which should handle
                 this listen socket."
    ::= { bgpNmEntEntry 1 }

  bgpNmEntRowStatus OBJECT-TYPE
    SYNTAX      RowStatus
    MAX-ACCESS  read-create
    STATUS      current
    DESCRIPTION "The row status for this Neighbor Manager Entity Table entry,
                 used to create and destroy table entries."
    ::= { bgpNmEntEntry 2 }

  bgpNmEntAdminStatus OBJECT-TYPE
    SYNTAX      BgpAdminStatus
    MAX-ACCESS  read-create
    STATUS      current
    DESCRIPTION "The administrative status of this Neighbor Manager entity,
                 used to activate and deactivate NM."
    DEFVAL      { adminStatusDown }
    ::= { bgpNmEntEntry 3 }

  bgpNmEntOperStatus OBJECT-TYPE
    SYNTAX      BgpOperStatus
    MAX-ACCESS  read-only
    STATUS      current
    DESCRIPTION "The current operational status of this Neighbor Manager
                 entity."
    ::= { bgpNmEntEntry 4 }

  bgpNmEntRmIndex OBJECT-TYPE
    SYNTAX      Unsigned32
    MAX-ACCESS  read-create
    STATUS      current
    DESCRIPTION "Identifies a RIB Manager entity to which the Neighbor Manager
                 will join.  This index is mapped to an RM entity index by
                 FTI-Specific Handling code within System Manager.  This field
                 can only be changed when the Admin Status is down."
    ::= { bgpNmEntEntry 5 }

  bgpNmEntSckIndex OBJECT-TYPE
    SYNTAX      Unsigned32
    MAX-ACCESS  read-create
    STATUS      current
    DESCRIPTION "Identifies the SCK stub entity to join with.  This index
                 is used in the join user data, to enable FTI-specific code
                 within System Manager to select a suitable slave SCK stub
                 entity.  The status of the join is given by the row in the
                 bgpNmMjTable with bgpNmMjJoinPartner equal to
                 bgpComponentIpSockets. This field can only be changed when
                 the Admin Status is down."
    DEFVAL { 1 }
     ::= { bgpNmEntEntry 6 }

  bgpNmEntBfdEntityIndex OBJECT-TYPE
    SYNTAX      Unsigned32
    MAX-ACCESS  read-create
    STATUS      current
    DESCRIPTION "Identifies a BFD stub entity to which the Neighbor Manager
                 will join.

                 A value of zero indicates that no BFD provider is
                 available, or that NM should not join to any BFD provider.

                 If a BFD join is requested (bfdNmEntBfdEntityIndex is set
                 to a non-zero value), but the BFD join fails to activate,
                 then NM will also fail to activate.

                 This field can only be changed when the NM entity admin
                 status is down."
    DEFVAL      { 0 }
    ::= { bgpNmEntEntry 7 }

-------------------------------------------------------------------------------

--
-- Neighbor Manager Listen Table.
--
-- This table controls which addresses the instance of NM listens out for
-- incoming connections on.  To satisfy the requirements BGP, at least one row
-- must be configured per _RM_ entity, although it is expected there will be
-- at least one per NM.
--

  bgpNmListenTable OBJECT-TYPE
  -- FAMILY-SHORT-NAME BGP_LIS
    SYNTAX      SEQUENCE OF BgpNmListenEntry
    MAX-ACCESS  not-accessible
    STATUS      current
    DESCRIPTION "Each entry in this table represents a listen socket in the
                 Neighbor Manager entity."
    ::= { bgpNm 2 }

  bgpNmListenEntry OBJECT-TYPE
    SYNTAX      BgpNmListenEntry
    MAX-ACCESS  not-accessible
    STATUS      current
    DESCRIPTION "Each entry represents a listen socket."
    INDEX { bgpNmEntIndex,
            bgpNmListenIndex }
    ::= { bgpNmListenTable 1 }

  BgpNmListenEntry ::= SEQUENCE {
      bgpNmListenIndex                Unsigned32,
      bgpNmListenRowStatus            RowStatus,
      bgpNmListenAdminStatus          BgpAdminStatus,
      bgpNmListenOperStatus           BgpOperStatus,
      bgpNmListenAddrType             InetAddressType,
      bgpNmListenAddr                 InetAddress,
      bgpNmListenPort                 InetPortNumber,
      bgpNmListenAcceptAll            TruthValue,
      bgpNmListenAddrScopeId          Unsigned32
    }

  bgpNmListenIndex OBJECT-TYPE
    SYNTAX      Unsigned32
    MAX-ACCESS  not-accessible
    STATUS      current
    DESCRIPTION "Identifies this listen socket since each NM instance can have
                 more than one Listen socket configured."
    ::= { bgpNmListenEntry 2 }

  bgpNmListenRowStatus OBJECT-TYPE
    SYNTAX      RowStatus
    MAX-ACCESS  read-create
    STATUS      current
    DESCRIPTION "The row status for this Neighbor Manager Listen Table entry,
                 used to create and destroy table entries."
    ::= { bgpNmListenEntry 3 }

  bgpNmListenAdminStatus OBJECT-TYPE
    SYNTAX      BgpAdminStatus
    MAX-ACCESS  read-create
    STATUS      current
    DESCRIPTION "The administrative status of this Listen entry, used to
                 activate and deactivate the Listen socket."
    DEFVAL      { adminStatusDown }
    ::= { bgpNmListenEntry 4 }

  bgpNmListenOperStatus OBJECT-TYPE
    SYNTAX      BgpOperStatus
    MAX-ACCESS  read-only
    STATUS      current
    DESCRIPTION "The current operational status of this Listen socket."
    ::= { bgpNmListenEntry 5 }

  bgpNmListenAddrType OBJECT-TYPE
    SYNTAX      InetAddressType
    MAX-ACCESS  read-create
    STATUS      current
    DESCRIPTION "The address family of the address used to listen on.  This
                 determines the format of the bgpNmListenAddr field.  This
                 field can only be changed when the Admin Status is down.
                 Valid values are: AMB_INETWK_ADDR_TYPE_IPV4 and
                 AMB_INETWK_ADDR_TYPE_IPV6."
    ::= { bgpNmListenEntry 6 }

  bgpNmListenAddr OBJECT-TYPE
    SYNTAX      InetAddress (SIZE(0..32))
    MAX-ACCESS  read-create
    STATUS      current
    DESCRIPTION "The address used to listen on.  This field can only
                 be changed when the Admin Status is down.  If set to a zero
                 length address DC-BGP will listen on all addresses available
                 to this NM instance.
                 For a specific port you cannot listen on a specific address if
                 you are already listening on all addresses.  Similarly, for a
                 specific port you cannot listen on all addresses if you are
                 already listening on a specific address."
    ::= { bgpNmListenEntry 7 }

  bgpNmListenPort OBJECT-TYPE
    SYNTAX      InetPortNumber
    MAX-ACCESS  read-create
    STATUS      current
    DESCRIPTION "The port used to listen on.  This field can only
                 be changed when the Admin Status is down."
    DEFVAL      { 179 }
    ::= { bgpNmListenEntry 8 }

  bgpNmListenAcceptAll OBJECT-TYPE
    SYNTAX      TruthValue
    MAX-ACCESS  read-create
    STATUS      current
    DESCRIPTION "This is set to TRUE if this socket will accept incoming
                 connections from any peer.  The recommended value is FALSE.
                 This field can only be changed when the Admin Status is down."
    DEFVAL      { false }
    ::= { bgpNmListenEntry 9 }

  bgpNmListenAddrScopeId OBJECT-TYPE
    SYNTAX      Unsigned32
    MAX-ACCESS  read-create
    STATUS      current
    DESCRIPTION "The scope ID of the bgpNmListenAddr.  The scope ID is
                 required if the address is an IPv6 link-local address.
                 Otherwise, this field must be set to zero.  This field can
                 only be changed when the Admin Status is down."
    ::= { bgpNmListenEntry 10 }

-------------------------------------------------------------------------------

  --
  -- <AFI, SAFI> supported table
  --
  -- A table used to enable any of the <AFI, SAFI> combinations
  -- supported by DC-BGP RIB Manager.  This MIB is read-write only.  Rows
  -- cannot be created or destroyed, as support for an <AFI, SAFI> is
  -- determined by presence or otherwise of user-exit code, and is not a
  -- run-time decision.
  --

  bgpRmAfiSafiTable OBJECT-TYPE
  -- FAMILY-SHORT-NAME BGP_AFI
    SYNTAX      SEQUENCE OF BgpRmAfiSafiEntry
    MAX-ACCESS  not-accessible
    STATUS      current
    DESCRIPTION "Table of per-<AFI, SAFI> configuration information."
    ::= { bgpRm 2 }

  bgpRmAfiSafiEntry OBJECT-TYPE
    SYNTAX      BgpRmAfiSafiEntry
    MAX-ACCESS  not-accessible
    STATUS      current
    DESCRIPTION "Entry containing information about support for an
                 <AFI, SAFI>."
    INDEX { bgpRmEntIndex,
            bgpRmAfiSafiAfi,
            bgpRmAfiSafiSafi }
    ::= { bgpRmAfiSafiTable 1 }

  BgpRmAfiSafiEntry ::= SEQUENCE {
      bgpRmAfiSafiAfi                 BgpAfi,
      bgpRmAfiSafiSafi                BgpSafi,
      bgpRmAfiSafiAdminStatus         BgpAdminStatus,
      bgpRmAfiSafiStateKept           TruthValue,
      bgpRmAfiSafiAfmRequired         TruthValue,
      bgpRmAfiSafiLocRibBlocked       TruthValue,
      bgpRmAfiSafiAdvertiseInactive   TruthValue,
      bgpRmAfiSafiUserData            OCTET STRING,
      bgpRmAfiSafiIbgpPrefixes        Gauge32,
      bgpRmAfiSafiEbgpPrefixes        Gauge32,
      bgpRmAfiSafiRedistPrefixes      Gauge32,
      bgpRmAfiSafiInPrfxes            Gauge32,
      bgpRmAfiSafiInPrfxesAccepted    Gauge32,
      bgpRmAfiSafiInPrfxesRejected    Gauge32,
      bgpRmAfiSafiOutPrfxes           Gauge32,
      bgpRmAfiSafiOutPrfxesAdvertised Gauge32,
      bgpRmAfiSafiInPrfxesActive      Gauge32,
      bgpRmAfiSafiInPrfxesFlapped     Gauge32,
      bgpRmAfiSafiInPrfxesFlapSuppr   Gauge32,
      bgpRmAfiSafiInPrfxesFlapHistory Gauge32,
      bgpRmAfiSafiDefaultImportRule   BgpPermitOrDeny,
      bgpRmAfiSafiInPrfxesDeniedByPol Gauge32,
      bgpRmAfiSafiNumLocRibRoutes     Gauge32,
      bgpRmAfiSafiNextHopSafi         BgpSafi
      }

  bgpRmAfiSafiAfi OBJECT-TYPE
    SYNTAX      BgpAfi
    MAX-ACCESS  not-accessible
    STATUS      current
    DESCRIPTION "The AFI index into the <AFI, SAFI> table."
    ::= { bgpRmAfiSafiEntry 2 }

  bgpRmAfiSafiSafi OBJECT-TYPE
    SYNTAX      BgpSafi
    MAX-ACCESS  not-accessible
    STATUS      current
    DESCRIPTION "The SAFI index into the <AFI, SAFI> table."
    ::= { bgpRmAfiSafiEntry 3 }

  bgpRmAfiSafiAdminStatus OBJECT-TYPE
    SYNTAX      BgpAdminStatus
    MAX-ACCESS  read-create
    STATUS      current
    DESCRIPTION "The administrative status for this <AFI,SAFI>.  The IPv4
                 Unicast address family is always active (and therefore
                 admin-up).  The default for other address families is to
                 be admin-down.  This field can only be set while RM is admin
                 down, and may only be moved to down if there are no route
                 maps or aggregate addresses defined for this <AFI, SAFI>."
    DEFVAL { adminStatusDown }
    ::= { bgpRmAfiSafiEntry 4 }

  bgpRmAfiSafiStateKept OBJECT-TYPE
    SYNTAX      TruthValue
    MAX-ACCESS  read-create
    STATUS      current
    DESCRIPTION "This value is used only if Graceful Restart procedures
                 are supported (in other words if bgpRmEntRestartSupported
                 is true).  If set to true, then the Restart Capability
                 generated after a local restart will indicate that
                 forwarding state has been maintained for this address
                 family over the restart.  If set to false, then the
                 forwarding state flag in the Restart Capability for this
                 address family will be set to indicate that forwarding
                 state has not been maintained.  This field can only be set
                 while RM is admin down."
    DEFVAL { false }
    ::= { bgpRmAfiSafiEntry 5 }

  bgpRmAfiSafiAfmRequired OBJECT-TYPE
    SYNTAX      TruthValue
    MAX-ACCESS  read-create
    STATUS      current
    DESCRIPTION "If this flag is set, DC-BGP will require an active AFM
                 join to be present before advertising NLRI of this <AFI,
                 SAFI> to peers.  This ensures that routes are not advertised
                 to peers that are not known to the local forwarding table."
    DEFVAL { true }
    ::= { bgpRmAfiSafiEntry 6 }

  bgpRmAfiSafiLocRibBlocked OBJECT-TYPE
    SYNTAX      TruthValue
    MAX-ACCESS  read-only
    STATUS      current
    DESCRIPTION "This flag is set if the Loc-RIB for this <AFI, SAFI> is
                 currently blocked, in which case DC-BGP will not advertise
                 any routes of this <AFI, SAFI> to peers.  A Loc-RIB is
                 blocked either because RM is undergoing graceful restart, or
                 because bgpRmAfiSafiAfmRequired is set to AMB_TRUE and there
                 are no active AFM joins for this <AFI, SAFI>.  A Loc-RIB is
                 unblocked when graceful restart completes, or when an AFM
                 join becomes active.  This flag is only valid If both RM and
                 this <AFI, SAFI> are active."
    ::= { bgpRmAfiSafiEntry 7 }

  bgpRmAfiSafiAdvertiseInactive OBJECT-TYPE
    SYNTAX      TruthValue
    MAX-ACCESS  read-create
    STATUS      current
    DESCRIPTION "If set to 'true', the best route will be advertised to
                 peers, whether or not the route has been added to the
                 forwarding table by the AFM.

                 If set to 'false', then BGP will only advertise a route to
                 peers if the route has been installed in the forwarding
                 table, or if the route has been redistributed by the AFM
                 from another routing protocol instance.  It is the
                 responsibility of the AFM to determine whether to only
                 redistribute active routes to BGP.

                 This option requires an AFM to be present, and so
                 bgpRmAfiSafiAdvertiseInactive may only be set to 'false' if
                 bgpRmAfiSafiAfmRequired is set to 'true'.  In addition, this
                 option requires that an AFM be configured to inform BGP
                 whenever a route from BGP is successfully installed in the
                 forwarding table, or is removed from the forwarding table.
                 This is achieved by configuring an AFM to redistribute
                 routes from this instance of BGP back to this instance of
                 BGP.

                 Not all AFMs support this redistribution of routes.  For
                 such address families, an attempt to set
                 bgpRmAfiSafiAdvertiseInactive to 'false' will be rejected.

                 This field can only be modified while RM is admin down."
    DEFVAL { true }
    ::= { bgpRmAfiSafiEntry 8 }

  bgpRmAfiSafiUserData OBJECT-TYPE
    SYNTAX      OCTET STRING(SIZE (4))
    MAX-ACCESS  read-only
    STATUS      current
    DESCRIPTION "User data for this BGP AFI SAFI entry."
    ::= { bgpRmAfiSafiEntry 9 }

  bgpRmAfiSafiIbgpPrefixes OBJECT-TYPE
    SYNTAX      Gauge32
    MAX-ACCESS  read-only
    STATUS      current
    DESCRIPTION "The total number of iBGP routes received for this <AFI,
                 SAFI>."
    ::= { bgpRmAfiSafiEntry 10 }

  bgpRmAfiSafiEbgpPrefixes OBJECT-TYPE
    SYNTAX      Gauge32
    MAX-ACCESS  read-only
    STATUS      current
    DESCRIPTION "The total number of eBGP routes received for this <AFI,
                 SAFI>."
    ::= { bgpRmAfiSafiEntry 11 }

  bgpRmAfiSafiRedistPrefixes OBJECT-TYPE
    SYNTAX      Gauge32
    MAX-ACCESS  read-only
    STATUS      current
    DESCRIPTION "The total number of routes redistributed for this <AFI,
                 SAFI>."
    ::= { bgpRmAfiSafiEntry 12 }

  bgpRmAfiSafiInPrfxes OBJECT-TYPE
    SYNTAX      Gauge32
    MAX-ACCESS  read-only
    STATUS      current
    DESCRIPTION "The number of prefixes received for this <AFI, SAFI> that
                 are stored in an Adj-RIB-In."
    ::= { bgpRmAfiSafiEntry 13 }

  bgpRmAfiSafiInPrfxesAccepted OBJECT-TYPE
    SYNTAX      Gauge32
    MAX-ACCESS  read-only
    STATUS      current
    DESCRIPTION "The number of prefixes received for this <AFI, SAFI> that
                 are installed in an Adj-RIB-In and are eligible to become
                 active in the Loc-Rib."
    ::= { bgpRmAfiSafiEntry 14 }

  bgpRmAfiSafiInPrfxesRejected OBJECT-TYPE
    SYNTAX      Gauge32
    MAX-ACCESS  read-only
    STATUS      current
    DESCRIPTION "The number of prefixes received for this <AFI, SAFI> that
                 are installed in an Adj-RIB-In and are NOT eligible to
                 become active in the Loc-Rib."
    ::= { bgpRmAfiSafiEntry 15 }

  bgpRmAfiSafiOutPrfxes OBJECT-TYPE
    SYNTAX      Gauge32
    MAX-ACCESS  read-only
    STATUS      current
    DESCRIPTION "The number of prefixes for this <AFI, SAFI> that are
                 installed in an Adj-RIB-Out.  Note that this value is
                 affected by the bgpRmEntNonPersistentAros field since, if
                 that field is set to TRUE, routes are removed from the
                 Adj-RIB-Out to reduce occupancy."
    ::= { bgpRmAfiSafiEntry 16 }

  bgpRmAfiSafiOutPrfxesAdvertised OBJECT-TYPE
    SYNTAX      Gauge32
    MAX-ACCESS  read-only
    STATUS      current
    DESCRIPTION "The number of advertised prefixes for this <AFI, SAFI>
                 currently associated with any peer.  This field is not
                 affected by the bgpRmEntNonPersistentAros field.  Note that
                 even if bgpRmEntNonPersistentAros is FALSE the value of this
                 field may differ from bgpPrfxOutPrfxes since that field
                 includes recently withdrawn routes which are undergoing
                 suppression procedures."
    ::= { bgpRmAfiSafiEntry 17 }

  bgpRmAfiSafiInPrfxesActive OBJECT-TYPE
    SYNTAX      Gauge32
    MAX-ACCESS  read-only
    STATUS      current
    DESCRIPTION "The number of prefixes received for this <AFI, SAFI> that
                 are installed in the Adj-RIB-In and are active in the
                 Loc-Rib.

                 This field is set to zero if bgpRmAfiSafiAdvertiseInactive
                 is set to 'true'."
    ::= { bgpRmAfiSafiEntry 18 }

  bgpRmAfiSafiInPrfxesFlapped OBJECT-TYPE
    SYNTAX      Gauge32
    MAX-ACCESS  read-only
    STATUS      current
    DESCRIPTION "The number of prefixes received for this <AFI, SAFI> that
                 are installed in the Adj-RIB-In and for which RIB Manager is
                 tracking a route flap damping penalty."
    ::= { bgpRmAfiSafiEntry 19 }

  bgpRmAfiSafiInPrfxesFlapSuppr OBJECT-TYPE
    SYNTAX      Gauge32
    MAX-ACCESS  read-only
    STATUS      current
    DESCRIPTION "The number of prefixes received for this <AFI, SAFI> that
                 are installed in the Adj-RIB-In and that are suppressed as a
                 result of route flapping."
    ::= { bgpRmAfiSafiEntry 20 }

  bgpRmAfiSafiInPrfxesFlapHistory OBJECT-TYPE
    SYNTAX      Gauge32
    MAX-ACCESS  read-only
    STATUS      current
    DESCRIPTION "The number of prefixes received for this <AFI, SAFI> that
                 are not currently in the Adj-RIB-In, but which have an
                 associated route flap damping penalty."
    ::= { bgpRmAfiSafiEntry 21 }

  bgpRmAfiSafiDefaultImportRule OBJECT-TYPE
    SYNTAX      BgpPermitOrDeny
    MAX-ACCESS  read-create
    STATUS      current
    DESCRIPTION "The default behavior that BGP applies when it receives a
                 route of this address family for which an import policy has
                 not been configured."
    DEFVAL { permit }
    ::= { bgpRmAfiSafiEntry 22 }

  bgpRmAfiSafiInPrfxesDeniedByPol OBJECT-TYPE
    SYNTAX      Gauge32
    MAX-ACCESS  read-only
    STATUS      current
    DESCRIPTION "The number of prefixes received for this <AFI, SAFI> that
                 are stored, but failed import policy and so have not been
                 installed in the Adj-RIB-In.

                 Note that this count only applies to denied prefixes from
                 peers for which 'soft reset with stored routing information'
                 is enabled for this <AFI, SAFI>."
    ::= { bgpRmAfiSafiEntry 23 }

  bgpRmAfiSafiNumLocRibRoutes OBJECT-TYPE
    SYNTAX      Gauge32
    MAX-ACCESS  read-only
    STATUS      current
    DESCRIPTION "The number of routes installed in the Loc-RIB for this
                 <AFI, SAFI>."
    ::= { bgpRmAfiSafiEntry 24 }

  bgpRmAfiSafiNextHopSafi OBJECT-TYPE
    SYNTAX      BgpSafi
    MAX-ACCESS  read-create
    STATUS      current
    DESCRIPTION "Specifies the SAFI that will be used to resolve BGP next
                 hops for routes with this <AFI, SAFI>.
 
                 This may be set to none, unicast or multicast.
 
                 If set to none, BGP next hops are resolved using the
                 AFI/SAFI of the BGP next hop, subject to the
                 QBDC_USER_EXTRACT_BGP_NEXT_HOP user exit.
 
                 This field can only be modified while RM is admin down."
    DEFVAL { none  }
    ::= { bgpRmAfiSafiEntry 25 }

-------------------------------------------------------------------------------

-- Notifications.

-- The BGP Notification Table

-- The BGP Notification Table records fields that are
-- required for notifications

  bgpNotification OBJECT IDENTIFIER ::= { bgpMib 8 }

  bgpNotificationEntry OBJECT IDENTIFIER
      ::= { bgpNotification 1 }

  bgpNotifPeerLocalAddrType OBJECT-TYPE
      SYNTAX      InetAddressType
      MAX-ACCESS  accessible-for-notify
      STATUS      current
      DESCRIPTION "Version of bgpPeerLocalAddrType used for notifications."
  ::= { bgpNotificationEntry 1 }

  bgpNotifPeerLocalAddr OBJECT-TYPE
      SYNTAX      InetAddress (SIZE(0..32))
      MAX-ACCESS  accessible-for-notify
      STATUS      current
      DESCRIPTION "Version of bgpPeerLocalAddr used for notifications."
  ::= { bgpNotificationEntry 2 }

  bgpNotifPeerRemoteAddrType OBJECT-TYPE
      SYNTAX      InetAddressType
      MAX-ACCESS  accessible-for-notify
      STATUS      current
      DESCRIPTION "Version of bgpPeerRemoteAddrType used for notifications."
  ::= { bgpNotificationEntry 3 }

  bgpNotifPeerRemoteAddr OBJECT-TYPE
      SYNTAX      InetAddress (SIZE(0..32))
      MAX-ACCESS  accessible-for-notify
      STATUS      current
      DESCRIPTION "Version of bgpPeerRemoteAddr used for notifications."
  ::= { bgpNotificationEntry 4 }

  bgpNotifRmEntIndex OBJECT-TYPE
      SYNTAX      Unsigned32
      MAX-ACCESS  accessible-for-notify
      STATUS      current
      DESCRIPTION "Version of bgpRmEntIndex used for notifications."
  ::= { bgpNotificationEntry 5 }

  bgpNotifPeerLocalPort OBJECT-TYPE
      SYNTAX      InetPortNumber
      MAX-ACCESS  accessible-for-notify
      STATUS      current
      DESCRIPTION "Version of bgpPeerLocalPort used for notifications."
  ::= { bgpNotificationEntry 6 }

  bgpNotifPeerRemotePort OBJECT-TYPE
      SYNTAX      InetPortNumber
      MAX-ACCESS  accessible-for-notify
      STATUS      current
      DESCRIPTION "Version of bgpPeerRemotePort used for notifications."
  ::= { bgpNotificationEntry 7 }

  bgpPeerLastFailureCause OBJECT-TYPE
      SYNTAX BgpPeerLastFailure
      MAX-ACCESS accessible-for-notify
      STATUS current
      DESCRIPTION
          "The cause of a Backwards Transition trap.  If this is not
           a Backwards Transition trap this is set to zero."
  ::= { bgpNotificationEntry 8 }

  bgpNotifPeerLocalAddrScopeId OBJECT-TYPE
      SYNTAX      Unsigned32
      MAX-ACCESS  accessible-for-notify
      STATUS      current
      DESCRIPTION "Version of bgpPeerLocalAddrScopeId used for notifications."
  ::= { bgpNotificationEntry 9 }

-- Type definitions

  bgpBaseNotifications OBJECT IDENTIFIER ::= { bgpNotifications 0 }

  bgpTrapData NOTIFICATION-TYPE
    OBJECTS {
        bgpNotifPeerLocalAddr,
        bgpNotifPeerLocalAddrType,
        bgpNotifPeerRemoteAddr,
        bgpNotifPeerRemoteAddrType,
        bgpPeerLastError,
        bgpPeerState,
        bgpPeerLocalNm,
        bgpNotifRmEntIndex,
        bgpNotifPeerLocalPort,
        bgpNotifPeerRemotePort,
        bgpPeerLastFailureCause,
        bgpNotifPeerLocalAddrScopeId,
        bgpPeerRstrStatus
     }
    STATUS  current
    DESCRIPTION "Structure used to send trap data to the MIB Manager.  DC-BGP
                 will send a trap in the following circumstances:

                 -  When a BGP peer's FSM enters the established state, if
                    bgpPeerTrapEstab is set to 'true' for the peer
                 -  When a BGP peer's FSM moves from a higher numbered state
                    to a lower numbered state, if bgpPeerTrapBackw is set to
                    'true' for the peer
                 -  When the local device changes Graceful Restart helper
                    state for a peer, if bgpPeerTrapGrHelperState is set to
                    'true' for the peer
                 -  When the maximum numbers of prefixes is reached for an
                    AFI/SAFI for a peer, if bgpPeerTrapPrefix is set to
                    'true' for the peer and bgpPeerAfiSafiTrapPrefix is set
                    to 'true' for the AFI/SAFI
                 -  When the prefix threshold is breached for an AFI/SAFI for
                    a peer, if bgpPeerTrapPrefix is set to 'true' for the
                    peer and bgpPeerAfiSafiTrapPrefix is set to 'true' for
                    the AFI/SAFI."
    ::= { bgpBaseNotifications 1 }

  bgpEntTrapData NOTIFICATION-TYPE
    OBJECTS {
        bgpNotifRmEntIndex,
        bgpRmEntOperStatus
     }
    STATUS  current
    DESCRIPTION "Structure used to send trap data to the MIB Manager.  If
                 bgpRmEntTrapOperState is set to 'true', DC-BGP will send a
                 trap when the local device enters RM operational state 'up',
                 'down' or 'actFailed'."
     ::= { bgpBaseNotifications 2 }

  bgpPeerSessionEstablished NOTIFICATION-TYPE
    OBJECTS {
        bgpNotifPeerLocalAddr,
        bgpNotifPeerLocalAddrType,
        bgpNotifPeerRemoteAddr,
        bgpNotifPeerRemoteAddrType,
        bgpPeerLastError,
        bgpPeerState,
        bgpPeerLocalNm,
        bgpNotifRmEntIndex,
        bgpNotifPeerLocalPort,
        bgpNotifPeerRemotePort,
        bgpPeerLastFailureCause,
        bgpNotifPeerLocalAddrScopeId,
        bgpPeerRstrStatus
     }
    STATUS  current
    DESCRIPTION "Structure used to send trap data to the MIB Manager.  DC-BGP
                will send a trap when a BGP peer's FSM enters the established
                state, if bgpPeerTrapEstab is set to 'true' for the peer."
    ::= { bgpBaseNotifications 3 }

  bgpPeerSessionBackward NOTIFICATION-TYPE
    OBJECTS {
        bgpNotifPeerLocalAddr,
        bgpNotifPeerLocalAddrType,
        bgpNotifPeerRemoteAddr,
        bgpNotifPeerRemoteAddrType,
        bgpPeerLastError,
        bgpPeerState,
        bgpPeerLocalNm,
        bgpNotifRmEntIndex,
        bgpNotifPeerLocalPort,
        bgpNotifPeerRemotePort,
        bgpPeerLastFailureCause,
        bgpNotifPeerLocalAddrScopeId,
        bgpPeerRstrStatus
     }
    STATUS  current
    DESCRIPTION "Structure used to send trap data to the MIB Manager.  DC-BGP
                will send a trap when a BGP peer's FSM moves from a higher
                numbered state to a lower numbered state, if bgpPeerTrapBackw
                is set to 'true' for the peer."
    ::= { bgpBaseNotifications 4 }

  bgpPeerAfiSafiMaxPrefix NOTIFICATION-TYPE
    OBJECTS {
        bgpNotifPeerLocalAddr,
        bgpNotifPeerLocalAddrType,
        bgpNotifPeerRemoteAddr,
        bgpNotifPeerRemoteAddrType,
        bgpPeerLastError,
        bgpPeerState,
        bgpPeerLocalNm,
        bgpNotifRmEntIndex,
        bgpNotifPeerLocalPort,
        bgpNotifPeerRemotePort,
        bgpPeerLastFailureCause,
        bgpNotifPeerLocalAddrScopeId,
        bgpPeerRstrStatus
     }
    STATUS  current
    DESCRIPTION "Structure used to send trap data to the MIB Manager.  DC-BGP
                will send a trap when the maximum numbers of prefixes is
                reached for an AFI/SAFI for a peer, if bgpPeerTrapPrefix is set
                to 'true' for the peer and bgpPeerAfiSafiTrapPrefix is set to
                'true' for the AFI/SAFI."
    ::= { bgpBaseNotifications 5 }

  bgpPeerAfiSafiPrefixThreshold NOTIFICATION-TYPE
    OBJECTS {
        bgpNotifPeerLocalAddr,
        bgpNotifPeerLocalAddrType,
        bgpNotifPeerRemoteAddr,
        bgpNotifPeerRemoteAddrType,
        bgpPeerLastError,
        bgpPeerState,
        bgpPeerLocalNm,
        bgpNotifRmEntIndex,
        bgpNotifPeerLocalPort,
        bgpNotifPeerRemotePort,
        bgpPeerLastFailureCause,
        bgpNotifPeerLocalAddrScopeId,
        bgpPeerRstrStatus
     }
    STATUS  current
    DESCRIPTION "Structure used to send trap data to the MIB Manager.  DC-BGP
                will send a trap when the prefix threshold is breached for an
                AFI/SAFI for a peer, if bgpPeerTrapPrefix is set to 'true' for
                the peer and bgpPeerAfiSafiTrapPrefix is set to 'true' for the
                AFI/SAFI."
    ::= { bgpBaseNotifications 6 }

  bgpEntOperStatusChange NOTIFICATION-TYPE
    OBJECTS {
        bgpNotifRmEntIndex,
        bgpRmEntOperStatus
     }
    STATUS  current
    DESCRIPTION "Structure used to send trap data to the MIB Manager.  If
                 bgpRmEntTrapOperState is set to 'true', DC-BGP will send a
                 trap when the local device enters RM operational state 'up',
                 'down' or 'actFailed'."
     ::= { bgpBaseNotifications 7 }

  bgpEntRestartHelperChange NOTIFICATION-TYPE
    OBJECTS {
        bgpNotifPeerLocalAddr,
        bgpNotifPeerLocalAddrType,
        bgpNotifPeerRemoteAddr,
        bgpNotifPeerRemoteAddrType,
        bgpPeerLastError,
        bgpPeerState,
        bgpPeerLocalNm,
        bgpNotifRmEntIndex,
        bgpNotifPeerLocalPort,
        bgpNotifPeerRemotePort,
        bgpPeerLastFailureCause,
        bgpNotifPeerLocalAddrScopeId,
        bgpPeerRstrStatus
     }
    STATUS  current
    DESCRIPTION "Structure used to send trap data to the MIB Manager.  DC-BGP
                will send a trap when the local device changes Graceful Restart
                helper state for a peer, if bgpPeerTrapGrHelperState is set to
                'true' for the peer."
    ::= { bgpBaseNotifications 8 }

-- End of notifications.

-------------------------------------------------------------------------------


-- Conformance information

  bgpConformance OBJECT IDENTIFIER ::= { bgpMib 9 }

  bgpCompliances OBJECT IDENTIFIER ::= { bgpConformance 1 }
  bgpGroups      OBJECT IDENTIFIER ::= { bgpConformance 2 }

  bgpCompliance MODULE-COMPLIANCE
    STATUS  current
    DESCRIPTION
        "The compliance statement for entities which implement the DC-BGP mib."
     MODULE
     MANDATORY-GROUPS {
        bgpRmEntityGroup,
        bgpRmAfmJoinGroup,
        bgpRmNmGroup,
        bgpNmMjGroup,
        bgpNmEntGroup,
        bgpNmListenGroup,
        bgpPeerGroup,
        bgpPathAttributesGroup,
        bgpPolicyGroup,
        bgpRmAfiSafiGroup,
        bgpOrfCapabilityGroup,
        bgpPeerOrfCapabilityGroup,
        bgpRmArinhJoinGroup
        }

    GROUP bgpRmEntityGroup
    DESCRIPTION
        "This group is mandatory for all agent implementations.  It contains
         mandatory, non-defaultable or read-only objects in the RIB Manager
         Entity Table."

    GROUP bgpRmAfmJoinGroup
    DESCRIPTION
        "This group is mandatory for all agent implementations.  It contains
         mandatory, non-defaultable or read-only objects in the RM AFM join
         table."

    GROUP bgpRmNmGroup
    DESCRIPTION
        "This group is mandatory for all agent implementations.  It contains
         mandatory, non-defaultable or read-only objects in the RM NM join
         table."

    GROUP bgpNmMjGroup
    DESCRIPTION
        "This group is mandatory for all agent implementations.  It contains
         mandatory, non-defaultable or read-only objects in the NM master join
         table."

    GROUP bgpNmEntGroup
    DESCRIPTION
        "This group is mandatory for all agent implementations.  It contains
         mandatory, non-defaultable or read-only objects in the Neighbor
         Manager Entity table."

    GROUP bgpNmListenGroup
    DESCRIPTION
        "This group is mandatory for all agent implementations.  It contains
         mandatory, non-defaultable or read-only objects in the Neighbor
         Manager Listen table."

    GROUP bgpPeerGroup
    DESCRIPTION
        "This group is mandatory for all agent implementations.  It contains
         mandatory, non-defaultable or read-only objects in the Peer tables."

    GROUP bgpPathAttributesGroup
    DESCRIPTION
        "This group is mandatory for all agent implementations.  It contains
         mandatory, non-defaultable or read-only objects in the Nlri tables."

    GROUP bgpPolicyGroup
    DESCRIPTION
        "This group is mandatory for all agent implementations.  It contains
         mandatory, non-defaultable or read-only objects in the Policy tables."

    GROUP bgpRmAfiSafiGroup
    DESCRIPTION
        "This group is mandatory for all agent implementations.  It contains
         mandatory, non-defaultable or read-only objects in the AFI SAFI
         tables."

    GROUP bgpOrfCapabilityGroup
    DESCRIPTION
        "This group is mandatory for all agent implementations.  It contains
         mandatory, non-defaultable or read-only objects in the ORF Capability
         table."

    GROUP bgpPeerOrfCapabilityGroup
    DESCRIPTION
        "This group is mandatory for all agent implementations.  It contains
         mandatory, non-defaultable or read-only objects in the Peer ORF
         Capability table."

    GROUP bgpRmEntityOptionalGroup
    DESCRIPTION
        "This group contains objects that are defaultable and can optionally be
         configured in the RIB Manager Entity table."

    GROUP bgpRmAfmJoinOptionalGroup
    DESCRIPTION
        "This group contains objects that are defaultable and can optionally be
         configured in the AFM table."

    GROUP bgpRmAfiSafiOptionalGroup
    DESCRIPTION
        "This group contains objects that are defaultable and can optionally be
         configured in the AFI/SAFI table."

    GROUP bgpNmListenOptionalGroup
    DESCRIPTION
        "This group contains objects that are defaultable and can optionally be
         configured in the AFM table."

    GROUP bgpPeerOptionalGroup
    DESCRIPTION
        "This group contains objects that are defaultable and can optionally be
         configured in the Peer table."

    GROUP bgpPathAttributesOptionalGroup
    DESCRIPTION
        "This group contains objects that are defaultable and can optionally be
         configured in the path attributes tables."

    GROUP bgpPolicyOptionalGroup
    DESCRIPTION
        "This group contains objects that are defaultable and can optionally be
         configured in the policy tables."

    GROUP bgpNotificationsGroup
    DESCRIPTION
        "The notifications group is completely optional."

    GROUP bgpAdjRibOutGroup
    DESCRIPTION
        "This group contains objects that are read-only, and is
         completely optional."

    GROUP bgpOrfCapabilityOptionalGroup
    DESCRIPTION
        "This group contains objects that are defaultable and can optionally be
         configured in the ORF Capability table."

    GROUP bgpPeerAfiSafiOptionalGroup
    DESCRIPTION
        "This group contains objects that are defaultable and can optionally be
         configured in the peer AFI/SAFI table."

    GROUP bgpPeergrAfiSafiOptionalGroup
    DESCRIPTION
        "This group contains objects that are defaultable and can optionally be
         configured in the peer group AFI/SAFI table."

    GROUP bgpPeerOrfCapabilityOptionalGrp
    DESCRIPTION
        "This group contains objects that are defaultable and can optionally be
         configured in the Peer ORF Capability table."

    GROUP bgpRmArinhJoinGroup
    DESCRIPTION
        "This group is mandatory for all agent implementations.  It contains
         mandatory, non-defaultable or read-only objects in the ARI join
         tables."

    GROUP bgpNmEntOptionalGroup
    DESCRIPTION
        "This group contains objects that are defaultable and can optionally be
         configured in the Neighbor Manager Entity table."

    GROUP bgpNotificationObjectGroup
    DESCRIPTION
        "The objects used to record notification parameters.  This group is
         completely optional."

    ::= { bgpCompliances 1 }

-- Units of Conformance (Groups)

    bgpRmEntityGroup OBJECT-GROUP
        OBJECTS {
            bgpRmEntRowStatus,
            bgpRmEntAdminStatus,
            bgpRmEntOperStatus,
            bgpRmEntAsSize,
            bgpRmEntLocalAs,
            bgpRmEntLocalIdentifier,
            bgpRmEntI3JoinStatus,
            bgpRmEntI3EntIndex,
            bgpRmEntLocalMbrAs,
            bgpRmEntIpv4ArinhJoinStatus,
            bgpRmEntIpv4ArinhEntIndex,
            bgpRmEntIpv6ArinhJoinStatus,
            bgpRmEntIpv6ArinhEntIndex,
            bgpRmEntNumAroRoutes,
            bgpRmEntPeakNumAroRoutes
        }
        STATUS current
        DESCRIPTION
            "This group is mandatory for all agent implementations.  It
             contains mandatory, non-defaultable or read-only objects in the
             RIB Manager Entity table."
        ::= { bgpGroups 1 }

    bgpRmAfmJoinGroup OBJECT-GROUP
        OBJECTS {
            bgpRmAfmRowStatus,
            bgpRmAfmAdminStatus,
            bgpRmAfmOperStatus,
            bgpRmAfmJoinStatus,
            bgpRmAfmRestartTime
        }
        STATUS current
        DESCRIPTION
            "This group is mandatory for all agent implementations.  It
             contains mandatory, non-defaultable or read-only objects in the
             RM AFM Join table."
        ::= { bgpGroups 2 }

    bgpRmNmGroup OBJECT-GROUP
        OBJECTS {
            bgpRmNmJoinStatus
        }
        STATUS current
        DESCRIPTION
            "This group is mandatory for all agent implementations.  It
             contains mandatory, non-defaultable or read-only objects in the
             RM NM Join table."
        ::= { bgpGroups 3 }

    bgpNmMjGroup OBJECT-GROUP
        OBJECTS {
            bgpNmMjJoinPartner,
            bgpNmMjPartnerIndex,
            bgpNmMjJoinStatus
        }
        STATUS current
        DESCRIPTION
            "This group is mandatory for all agent implementations.  It
             contains mandatory, non-defaultable or read-only objects in the
             NM Master Join table."
        ::= { bgpGroups 4 }

    bgpNmEntGroup OBJECT-GROUP
        OBJECTS {
            bgpNmEntRowStatus,
            bgpNmEntAdminStatus,
            bgpNmEntOperStatus,
            bgpNmEntRmIndex,
            bgpNmEntSckIndex
        }
        STATUS current
        DESCRIPTION
            "This group is mandatory for all agent implementations.  It
             contains mandatory, non-defaultable or read-only objects in the
             Neighbor Manager Entity table."
        ::= { bgpGroups 5 }

    bgpNmListenGroup OBJECT-GROUP
        OBJECTS {
            bgpNmListenRowStatus,
            bgpNmListenAdminStatus,
            bgpNmListenOperStatus,
            bgpNmListenAddrType,
            bgpNmListenAddr
        }
        STATUS current
        DESCRIPTION
            "This group is mandatory for all agent implementations.  It
             contains mandatory, non-defaultable or read-only objects in the
             Neighbor Manager Listen table."
        ::= { bgpGroups 6 }

    bgpPeerGroup OBJECT-GROUP
        OBJECTS {
            bgpPeerIdentifier,
            bgpPeerState,
            bgpPeerRowStatus,
            bgpPeerAdminStatus,
            bgpPeerOperStatus,
            bgpPeerLocalNm,
            bgpPeerRemoteAs,
            bgpPeerIndex,
            bgpPeerCapsSupport,
            bgpPeerLastError,
            bgpPeerLastErrorDataLen,
            bgpPeerLastErrorData,
            bgpPeerFsmEstablishedTime,
            bgpPeerInUpdatesElapsedTime,
            bgpPeerHoldTime,
            bgpPeerKeepAlive,
            bgpPeerInUpdates,
            bgpPeerOutUpdates,
            bgpPeerInTotalMessages,
            bgpPeerOutTotalMessages,
            bgpPeerFsmEstablishedTransitions,
            bgpPeerConnectRetryCount,
            bgpPeerCapRcvdValue,
            bgpPeerCapSentValue,
            bgpPeerSelectedLocalAddrType,
            bgpPeerSelectedLocalAddr,
            bgpPeerSelectedLocalPort,
            bgpPeerSelectedRemotePort,
            bgpPeerBfdStatus,
            bgpPrfxInPrfxes,
            bgpPrfxInPrfxesAccepted,
            bgpPrfxInPrfxesRejected,
            bgpPrfxOutPrfxes,
            bgpPrfxOutPrfxesAdvertised,
            bgpPrfxInPrfxesFlapped,
            bgpPrfxInPrfxesFlapSuppressed,
            bgpPrfxInPrfxesFlapHistory,
            bgpPrfxInPrfxesActive,
            bgpPrfxCntrsUserData,
            bgpPrfxInPrfxesDeniedByPol,
            bgpPrfxNumLocRibRoutes
        }
        STATUS current
        DESCRIPTION
            "This group is mandatory for all agent implementations.  It
             contains mandatory, non-defaultable or read-only objects in the
             Peer tables."
        ::= { bgpGroups 7 }

    bgpPathAttributesGroup OBJECT-GROUP
        OBJECTS {
            bgpNlriBest,
            bgpNlriAsSize,
            bgpNlriASPathStr,
            bgpPathAttrOrigin,
            bgpPathAttrNextHop,
            bgpPathAttrMultiExitDisc,
            bgpPathAttrLocalPref,
            bgpPathAttrAtomicAggregate,
            bgpPathAttrAggregatorAS,
            bgpPathAttrAggregatorAddr,
            bgpPathAttrCalcLocalPref,
            bgpPathAttrOrigId,
            bgpPathAttrWeight,
            bgpFlapStatsConfig,
            bgpFlapStatsPenalty,
            bgpFlapStatsFlapcnt,
            bgpFlapStatsSupprsd,
            bgpFlapStatsTimeleft,
            bgpPathAttrUnknownValue,
            bgpPathAttrUnknownUserData,
            bgpPathAttrClusterValue,
            bgpPathAttrClusterUserData,
            bgpPathAttrCommValue,
            bgpPathAttrCommUserData,
            bgpPathAttrExtCommValue,
            bgpPathAttrExtCommUserData,
            bgpNlriEcmp,
            bgpPathAttrAsPathLimAs,
            bgpPathAttrAsPathLimUpper,
            bgpNlriIsActive,
            bgpNlriStale,
            bgpNlriFlapStartTime,
            bgpNlriLinkLocalNextHop,
            bgpNlriUserData,
            bgpNlriPrefixBest,
            bgpNlriPrefixAsSize,
            bgpNlriPrefixASPathStr,
            bgpNlriPrefixPathAttrOrigin,
            bgpNlriPrefixPathAttrNextHop,
            bgpNlriPrefixPathAttrMultExtDisc,
            bgpNlriPrefixPathAttrLocalPref,
            bgpNlriPrefixPathAttrAtomicAgg,
            bgpNlriPrefixPathAttrAggAS,
            bgpNlriPrefixPathAttrAggAddr,
            bgpNlriPrefixPathAttrCalcLclPref,
            bgpNlriPrefixPathAttrOrigId,
            bgpNlriPrefixPathAttrWeight,
            bgpNlriPrefixFlapStatsConfig,
            bgpNlriPrefixFlapStatsPenalty,
            bgpNlriPrefixFlapStatsFlapcnt,
            bgpNlriPrefixFlapStatsSupprsd,
            bgpNlriPrefixFlapStatsTimeleft,
            bgpNlriPrefixFlapStatsCleardamp,
            bgpNlriPrefixFlapStatsClearstat,
            bgpNlriPrefixEcmp,
            bgpNlriPrefixPathAttrAsPathLimAs,
            bgpNlriPrefixPthAttAsPthLimUpper,
            bgpNlriPrefixIsActive,
            bgpNlriPrefixStale,
            bgpNlriPrefixFlapStartTime,
            bgpNlriPrefixUserData,
            bgpNlriPrefixLinkLocalNextHop
        }
        STATUS current
        DESCRIPTION
            "This group is mandatory for all agent implementations.  It
             contains mandatory, non-defaultable or read-only objects in the
             Nlri tables."
        ::= { bgpGroups 8 }

    bgpPolicyGroup OBJECT-GROUP
        OBJECTS {
            bgpRouteMapRowStatus,
            bgpRouteMapMaAs,
            bgpRouteMapMaComm,
            bgpRouteMapMaExtComm,
            bgpRouteMapMaAddr,
            bgpRouteMapMaNext,
            bgpRouteMapMaSource,
            bgpRouteMapHitcnt,
            bgpIpPreRowStatus,
            bgpPeergrRowStatus,
            bgpPeergrConfig,
            bgpConfigRowStatus,
            bgpFlapConfigRowStatus,
            bgpAggrRowStatus
        }
        STATUS current
        DESCRIPTION
            "This group is mandatory for all agent implementations.  It
             contains mandatory, non-defaultable or read-only objects in the
             Policy tables."
        ::= { bgpGroups 9 }

    bgpRmEntityOptionalGroup OBJECT-GROUP
        OBJECTS {
            bgpRmEntAsSize,
            bgpRmEntClusterId,
            bgpRmEntFlapDeltat,
            bgpRmEntFlapReusemax,
            bgpRmEntFlapReusesize,
            bgpRmEntFlapReusearray,
            bgpRmEntFlapFreemax,
            bgpRmEntNoRefresh,
            bgpRmEntDefLocalPref,
            bgpRmEntAlwaysCompMed,
            bgpRmEntPauseThreshold,
            bgpRmEntAggregateMed,
            bgpRmEntDeterministicMed,
            bgpRmEntMaxIBgpEcmpRoutes,
            bgpRmEntMaxEBgpEcmpRoutes,
            bgpRmEntRestartSupported,
            bgpRmEntMaxRestartTime,
            bgpRmEntRecoveryTime,
            bgpRmEntRestarting,
            bgpRmEntSupportIpv6,
            bgpRmEntStrictConfed,
            bgpRmEntOrfSupported,
            bgpRmEntCiscoPrefixSupported,
            bgpRmEntSelectDeferTime,
            bgpRmEntStalePathTime,
            bgpRmEntNonPersistentAros,
            bgpRmEntAroRouteThreshold,
            bgpRmEntMaxActiveAroGroups,
            bgpRmEntNumArosInGroup,
            bgpRmEntClearStats,
            bgpRmEntFastExtFallover,
            bgpRmEntRemainDelayTime,
            bgpRmEntPathAttrs,
            bgpRmEntAggSplitHorizon,
            bgpRmEntAggAdvSuppr,
            bgpRmEntUpdateGroups,
            bgpRmEntPhase3DelayTime,
            bgpRmEntTrapOperState
        }
        STATUS current
        DESCRIPTION
            "This group contains objects that are defaultable and can
             optionally be configured in the RIB Manager Entity table."
        ::= { bgpGroups 10 }

    bgpRmAfmJoinOptionalGroup OBJECT-GROUP
        OBJECTS {
            bgpRmAfmPartnerIndex,
            bgpRmAfmAfi,
            bgpRmAfmSafi
        }
        STATUS current
        DESCRIPTION
            "This group contains objects that are defaultable and can
             optionally be configured in the AFM table."
        ::= { bgpGroups 11 }

    bgpNmListenOptionalGroup OBJECT-GROUP
        OBJECTS {
            bgpNmListenPort,
            bgpNmListenAcceptAll,
            bgpNmListenAddrScopeId
        }
        STATUS current
        DESCRIPTION
            "This group contains objects that are defaultable and can
             optionally be configured in the Listen table."
        ::= { bgpGroups 12 }

    bgpPeerOptionalGroup OBJECT-GROUP
        OBJECTS {
            bgpPeerReflectorClient,
            bgpPeerTrapEstab,
            bgpPeerTrapBackw,
            bgpPeerConnectRetryInterval,
            bgpPeerHoldTimeConfigd,
            bgpPeerKeepAliveConfigd,
            bgpPeerMinASOriginationInterval,
            bgpPeerMinRouteAdvertiseInterval,
            bgpPeerClearCnts,
            bgpPeerConfigPeergr,
            bgpPeerConfigIndex,
            bgpPeerConfigRtRefresh,
            bgpPeerConfigMaxPrfx,
            bgpPeerConfigDropWarn,
            bgpPeerPassword,
            bgpPeerTtl,
            bgpPeerConfedMember,
            bgpPeerConfigPassive,
            bgpPeerConfigOpenDelay,
            bgpPeerConfigIdleHold,
            bgpPeerCheckFirstAsNum,
            bgpPeerAggrInclConfedAS,
            bgpPeerMinRouteWithdrawInterval,
            bgpPeerStalePathTime,
            bgpPeerCheckNextHop,
            bgpPeerMaxOrfEntries,
            bgpPeerOrfEntryCount,
            bgpPeerPeeringType,
            bgpPeerSoftResetWithStoredInfo,
            bgpPeerAllowLocalAs,
            bgpPeerDisableSenderLoopDetect,
            bgpPeerDisableRouteRefresh,
            bgpPeerFlapStatsClearStat,
            bgpPeerFlapStatsClearMap,
            bgpPeerLastErrorRcvd,
            bgpPeerLastErrorRcvdTime,
            bgpPeerLastErrorSent,
            bgpPeerLastErrorSentTime,
            bgpPeerLastState,
            bgpPeerLastEvent,
            bgpPeerCapsSent,
            bgpPeerCapsRcvd,
            bgpPeerCapsNegotiated,
            bgpPeerRstrSupport,
            bgpPeerRstrFamily,
            bgpPeerRstrRestarting,
            bgpPeerRstrStatus,
            bgpPeerRstrRemTime,
            bgpPeerRcvdMsgElapsedTime,
            bgpPeerIdleHoldRemTime,
            bgpPeerRouteRefrSent,
            bgpPeerRouteRefrRcvd,
            bgpPeerLastFailureCause,
            bgpPeerNxtHopSlf,
            bgpPeerThirdPtyNxtHop,
            bgpPeerNxtHopPeer,
            bgpPeerTrapPrefix,
            bgpPeerConfigThreshold,
            bgpPeerMaxPrfxHold,
            bgpPeerBfdDesired,
            bgpPeerCeaseErrorSubcode,
            bgpPeerConfAltLocalAs,
            bgpPeerSelectedLocalAs,
            bgpPeerSelectedRemoteAs,
            bgpPeerInPrfxes,
            bgpPeerOutPrfxes,
            bgpPeerOutPrfxesAdvertised,
            bgpPeerTrapGrHelperState,
            bgpPeerEnableAttributeDiscard
        }
        STATUS current
        DESCRIPTION
            "This group contains objects that are defaultable and can
             optionally be configured in the Peer table."
        ::= { bgpGroups 13 }

    bgpPathAttributesOptionalGroup OBJECT-GROUP
        OBJECTS {
            bgpFlapStatsCleardamp,
            bgpFlapStatsClearstat
        }
        STATUS current
        DESCRIPTION
            "This group contains objects that are defaultable and can
             optionally be configured in the path attributes tables."
        ::= { bgpGroups 14 }

    bgpPolicyOptionalGroup OBJECT-GROUP
        OBJECTS {
            bgpRouteMapMaAfi,
            bgpRouteMapMaAfiDef,
            bgpRouteMapMaSafi,
            bgpRouteMapMaSafiDef,
            bgpRouteMapMaMed,
            bgpRouteMapMaMedDef,
            bgpRouteMapMaUser,
            bgpRouteMapSeAs,
            bgpRouteMapSeAsAct,
            bgpRouteMapSeComm,
            bgpRouteMapSeCommAct,
            bgpRouteMapSeExtComm,
            bgpRouteMapSeExtCommAct,
            bgpRouteMapSeLocPref,
            bgpRouteMapSeLocPrefDef,
            bgpRouteMapSeMed,
            bgpRouteMapSeMedDef,
            bgpRouteMapSeNext,
            bgpRouteMapSeOrigin,
            bgpRouteMapSeOriginDef,
            bgpRouteMapSeWeight,
            bgpRouteMapSeWeightDef,
            bgpRouteMapSeFlap,
            bgpRouteMapSeUser,
            bgpRouteMapClearcnt,
            bgpRouteMapUserInfo,
            bgpRouteMapType,
            bgpRouteMapContinue,
            bgpRouteMapOrfAssoc,
            bgpRouteMapSeAsLimUpper,
            bgpRouteMapSeAsLimDef,
            bgpRouteMapMaOrigin,
            bgpRouteMapMaOriginDef,
            bgpRouteMapSeMedDelta,
            bgpRouteMapSeMedDeltaTyp,
            bgpRouteMapSeMedIgp,
            bgpRouteMapSeAsPrependCount,
            bgpRouteMapSeAsPrependSize,
            bgpRouteMapSeAsPrependAsVals,
            bgpRouteMapMaAnd,
            bgpIpPreAfi,
            bgpIpPreSafi,
            bgpIpPreAddr,
            bgpIpPreLen,
            bgpIpPreGe,
            bgpIpPreLe,
            bgpIpPreType,
            bgpPeergrArea,
            bgpPeergrAggrConfedAS,
            bgpPeergrSoftResetWithStoredInfo,
            bgpPeergrAllowLocalAs,
            bgpPeergrDisableSenderLoopDetect,
            bgpPeergrNxtHopSlf,
            bgpPeergrThirdPtyNxtHop,
            bgpPeergrNxtHopPeer,
            bgpPeergrEnableAttributeDiscard,
            bgpConfigImportMap,
            bgpConfigExportMap,
            bgpConfigAdvertiseMap,
            bgpConfigNonExistMap,
            bgpConfigBlockCondAdv,
            bgpConfigRemove,
            bgpConfigCondAdvOn,
            bgpFlapConfigCut,
            bgpFlapConfigReuse,
            bgpFlapConfigThold,
            bgpFlapConfigDecayok,
            bgpFlapConfigDecayng,
            bgpFlapConfigTmaxok,
            bgpFlapConfigTmaxng,
            bgpAggrOptions,
            bgpAggrSuppressMap,
            bgpAggrAdvertiseMap,
            bgpAggrAttributeMap,
            bgpAggrPermanent
        }
        STATUS current
        DESCRIPTION
            "This group contains objects that are defaultable and can
             optionally be configured in the policy tables."
        ::= { bgpGroups 15 }

    bgpNotificationsGroup NOTIFICATION-GROUP
        NOTIFICATIONS {
            bgpTrapData,
            bgpEntTrapData,
            bgpPeerSessionEstablished,
            bgpPeerSessionBackward,
            bgpPeerAfiSafiMaxPrefix,
            bgpPeerAfiSafiPrefixThreshold,
            bgpEntOperStatusChange,
            bgpEntRestartHelperChange
        }
        STATUS  current
        DESCRIPTION
            "The notifications group is completely optional."
        ::= { bgpGroups 16 }

    bgpObsoleteGroup OBJECT-GROUP
        OBJECTS {
            bgpConfigRtgrimpe,
            bgpConfigRtgrimde,
            bgpConfigRtgrexpe,
            bgpConfigRtgrexde,
            bgpConfigDefImport,
            bgpConfigDefExport,
            bgpConfigNxtHopSlf,
            bgpConfigThirdPtyNxtHop,
            bgpConfigNxtHopPeer,
            bgpRmEntNhrJoinStatus,
            bgpRmEntNhrEntIndex,
            bgpRmEntIpv4UniFwdPrsrvd,
            bgpRmEntIpv4MultiFwdPrsrvd,
            bgpRmEntVpnIpv4FwdPrsrvd,
            bgpRmEntIpv4MultiSupport,
            bgpRmEntVpnIpv4Support
        }
        STATUS obsolete
        DESCRIPTION
            "This group contains obsolete objects."
        ::= { bgpGroups 17 }

    bgpRmAfiSafiGroup OBJECT-GROUP
        OBJECTS {
            bgpRmAfiSafiAdminStatus,
            bgpRmAfiSafiLocRibBlocked,
            bgpRmAfiSafiAdvertiseInactive,
            bgpRmAfiSafiIbgpPrefixes,
            bgpRmAfiSafiEbgpPrefixes,
            bgpRmAfiSafiRedistPrefixes,
            bgpRmAfiSafiInPrfxes,
            bgpRmAfiSafiInPrfxesAccepted,
            bgpRmAfiSafiInPrfxesRejected,
            bgpRmAfiSafiOutPrfxes,
            bgpRmAfiSafiOutPrfxesAdvertised,
            bgpRmAfiSafiInPrfxesActive,
            bgpRmAfiSafiInPrfxesFlapped,
            bgpRmAfiSafiInPrfxesFlapSuppr,
            bgpRmAfiSafiInPrfxesFlapHistory,
            bgpRmAfiSafiDefaultImportRule,
            bgpRmAfiSafiUserData,
            bgpRmAfiSafiInPrfxesDeniedByPol,
            bgpRmAfiSafiNumLocRibRoutes,
            bgpRmAfiSafiNextHopSafi
        }
        STATUS current
        DESCRIPTION
            "This group is mandatory for all agent implementations.  It
             contains mandatory, non-defaultable or read-only objects in the
             AFI SAFI tables."
        ::= { bgpGroups 18 }

    bgpRmAfiSafiOptionalGroup OBJECT-GROUP
        OBJECTS {
            bgpRmAfiSafiStateKept,
            bgpRmAfiSafiAfmRequired
        }
        STATUS current
        DESCRIPTION
            "This group contains objects that are defaultable and can
             optionally be configured in the AFI SAFI table."
        ::= { bgpGroups 19 }

    bgpAdjRibOutGroup OBJECT-GROUP
        OBJECTS {
            bgpAdjRibOutAdvertStatus,
            bgpAdjRibOutLocalAggrType,
            bgpAdjRibOutAsSize,
            bgpAdjRibOutASPathStr,
            bgpAdjRibOutOrigin,
            bgpAdjRibOutNextHop,
            bgpAdjRibOutMultiExitDisc,
            bgpAdjRibOutLocalPref,
            bgpAdjRibOutAtomicAggregate,
            bgpAdjRibOutAggregatorAS,
            bgpAdjRibOutAggregatorAddr,
            bgpAdjRibOutOrigId,
            bgpAdjRibOutAsLimAs,
            bgpAdjRibOutAsLimUpper,
            bgpAdjRibOutUserData,
            bgpAdjRibOutEcmp,
            bgpAdjRibOutStale,
            bgpAdjRibOutLinkLocalNextHop
        }
        STATUS current
        DESCRIPTION
            "This group contains objects that are read-only, and is
             completely optional."
        ::= { bgpGroups 20 }

    bgpOrfCapabilityGroup OBJECT-GROUP
        OBJECTS {
            bgpOrfCapabilityAdminStatus
        }
        STATUS current
        DESCRIPTION
            "This group is mandatory for all agent implementations.  It
             contains mandatory, non-defaultable or read-only objects in the
             ORF Capability table."
        ::= { bgpGroups 21 }

    bgpOrfCapabilityOptionalGroup OBJECT-GROUP
        OBJECTS {
            bgpOrfCapabilitySendReceive
        }
        STATUS current
        DESCRIPTION
            "This group contains objects that are defaultable and can
             optionally be configured in the ORF Capability table."
        ::= { bgpGroups 22 }

    bgpPeerAfiSafiOptionalGroup OBJECT-GROUP
        OBJECTS {
            bgpPeerAfiSafiDisable,
            bgpPeerAfiSafiConfigRtRefresh,
            bgpPeerAfiSafiAllowLocalAs,
            bgpPeerAfiSafiDisableSndLpDetect,
            bgpPeerAfiSafiNxtHopSlf,
            bgpPeerAfiSafiOrigDefault,
            bgpPeerAfiSafiOrigDefaultRtMap,
            bgpPeerAfiSafiSoftResetStore,
            bgpPeerAfiSafiConfigMaxPrfx,
            bgpPeerAfiSafiConfigDropWarn,
            bgpPeerAfiSafiTrapPrefix,
            bgpPeerAfiSafiConfigThreshold,
            bgpPeerAfiSafiMaxPrfxHold,
            bgpPeerAfiSafiMaxOrfEntries
        }
        STATUS current
        DESCRIPTION
            "This group contains objects that are defaultable and can
             optionally be configured in the peer AFI/SAFI table."
        ::= { bgpGroups 23 }

    bgpPeergrAfiSafiOptionalGroup OBJECT-GROUP
        OBJECTS {
            bgpPeergrAfiSafiAllowLocalAs,
            bgpPeergrAfiSafiDisSndLpDetect,
            bgpPeergrAfiSafiNxtHopSlf,
            bgpPeergrAfiSafiOrigDefault,
            bgpPeergrAfiSafiOrigDefaultRtMap,
            bgpPeergrAfiSafiSoftResetStore
        }
        STATUS current
        DESCRIPTION
            "This group contains objects that are defaultable and can
             optionally be configured in the peer group AFI/SAFI table."
        ::= { bgpGroups 24 }

    bgpPeerOrfCapabilityGroup OBJECT-GROUP
        OBJECTS {
            bgpPeerOrfCapabilityAdminStatus
        }
        STATUS current
        DESCRIPTION
            "This group is mandatory for all agent implementations.  It
             contains mandatory, non-defaultable or read-only objects in the
             Peer ORF Capability table."
        ::= { bgpGroups 25 }

    bgpPeerOrfCapabilityOptionalGrp OBJECT-GROUP
        OBJECTS {
            bgpPeerOrfCapabilitySendReceive
        }
        STATUS current
        DESCRIPTION
            "This group contains objects that are defaultable and can
             optionally be configured in the Peer ORF Capability table."
        ::= { bgpGroups 26 }

    bgpRmArinhJoinGroup OBJECT-GROUP
        OBJECTS {
            bgpRmArinhJoinStatus,
            bgpRmArinhEntIndex
        }
        STATUS current
        DESCRIPTION
            "This group is mandatory for all agent implementations.  It
             contains mandatory, non-defaultable or read-only objects in the
             RM ARI Join table."
        ::= { bgpGroups 27 }

    bgpNmEntOptionalGroup OBJECT-GROUP
        OBJECTS {
            bgpNmEntBfdEntityIndex
        }
        STATUS current
        DESCRIPTION
            "This group contains objects that are defaultable and can
             optionally be configured in the Neighbor Manager Entity table."
        ::= { bgpGroups 28 }

    bgpNotificationObjectGroup OBJECT-GROUP
        OBJECTS {
            bgpNotifPeerLocalAddr,
            bgpNotifPeerLocalAddrType,
            bgpNotifPeerRemoteAddr,
            bgpNotifPeerRemoteAddrType,
            bgpNotifRmEntIndex,
            bgpNotifPeerLocalPort,
            bgpNotifPeerRemotePort,
            bgpNotifPeerLocalAddrScopeId
        }
        STATUS current
        DESCRIPTION
            "The objects used to record notification parameters.  This group
             is completely optional."
        ::= { bgpGroups 29 }

END
